;;; ==========================================================================
;;;  SHOPDRAWING TOOLS for AutoCAD  (AutoLISP / Visual LISP)
;;;  Bo cong cu ve shop drawing: ket cau BTCT + ket cau thep
;;;
;;;  Nap:   APPLOAD -> chon dist/ShopDrawing.lsp  (hoac them vao Startup Suite)
;;;  Lenh:  go SDHELP de xem danh sach lenh
;;;
;;;  LUU Y: day la file NGUON (UTF-8, co dau tieng Viet trong chuoi ghi len
;;;  ban ve). Chay "python3 build.py" de sinh dist/ShopDrawing.lsp (ASCII,
;;;  ky tu co dau duoc doi thanh ma \U+XXXX ma AutoCAD hieu duoc).
;;;  Chuoi nhac lenh (prompt) viet KHONG DAU de hien thi dung o moi phien ban.
;;; ==========================================================================

(vl-load-com)
(setq *SD:VER* "2.59.0")

;;; --------------------------------------------------------------------------
;;;  Thiet lap mac dinh (luu kem trong ban ve bang LDATA)
;;; --------------------------------------------------------------------------
(setq *SD:SCALE*    (cond ((vlax-ldata-get "SD" "SCALE")) (*SD:SCALE*) (100)))
(setq *SD:DETSCALE* (cond ((vlax-ldata-get "SD" "DETSCALE")) (*SD:DETSCALE*) (25)))
(or *SD:MARK* (setq *SD:MARK* 1))

;; Danh sach layer: (ten mau linetype lineweight[1/100 mm])
(setq *SD:LAYERS*
  '(("SD-TRUC"      1 "CENTER"     13)
    ("SD-KHUNG"     7 "Continuous" 50)
    ("SD-BANG"      7 "Continuous" 18)
    ("SD-BETONG"    7 "Continuous" 35)
    ("SD-THEP-CHU"  2 "Continuous" 40)
    ("SD-THEP-DAI"  3 "Continuous" 25)
    ("SD-THEP-HINH" 5 "Continuous" 35)
    ("SD-BULONG"    6 "Continuous" 25)
    ("SD-KICHTHUOC" 4 "Continuous" 18)
    ("SD-CHU"       7 "Continuous" 18)
    ("SD-KYHIEU"    6 "Continuous" 25)
    ("SD-KHUAT"     8 "HIDDEN"     18)
    ("SD-HATCH"     8 "Continuous" 13)
    ("SD-GACH"      8 "Continuous" 13)
    ("SD-GACH-CAT" 30 "Continuous" 13)
    ("SD-PAT"       1 "Continuous" 25)
    ("SD-OP-LOP"    7 "Continuous" 25)
    ("SD-GACH-VIEN" 40 "Continuous" 18)
    ("SD-GACH-DOC"   3 "Continuous" 13)
    ("SD-GACH-VAN"   8 "Continuous" 13)
    ("SD-GACH-ANH"   7 "Continuous" 13)
    ("SD-DUONG-CAT"  1 "Continuous" 18)
    ("SD-GACH-NEST"  3 "Continuous" 18)
    ("SD-NEST-TAM"   7 "Continuous" 50)
    ("SD-NEST-LE"    8 "DASHED" 13)
    ("SD-NEST-VIEN"  3 "Continuous" 35)
    ("SD-NEST-VUN"   9 "Continuous" 13)
    ("SD-NEST-TO"    9 "Continuous" 13)
    ("SD-NEST-CHU"   7 "Continuous" 18)
    ("SD-PANEL"      7 "Continuous" 25)
    ("INFILL-TIMBER" 30 "Continuous" 25)
    ("SD-LEN-CHAN" 140 "Continuous" 18)
    ("SD-GIACONG"   7 "Continuous" 35)
    ("SD-CF-VAN"   41 "Continuous" 25)
    ("SD-CF-SUON"   3 "Continuous" 18)
    ("SD-CF-GONG"   5 "Continuous" 25)
    ("SD-CF-TY"     1 "Continuous" 25)
    ("SD-CF-CHONG"  6 "Continuous" 25)
    ("SD-GIAO"    140 "Continuous" 25)
    ("SD-GIANG"     2 "Continuous" 18)
    ("SD-OSAN"      8 "Continuous" 13)))

;;; --------------------------------------------------------------------------
;;;  Ham tien ich chung
;;; --------------------------------------------------------------------------
;; Sap xep KHONG bo phan tu trung khoa (vl-sort bo cac phan tu "bang nhau" theo ham so sanh -> mat ban ghi)
(defun sd:sort (lst f)
  (if lst (mapcar '(lambda (k) (nth k lst)) (vl-sort-i lst f))))

(defun sd:doc () (vla-get-ActiveDocument (vlax-get-acad-object)))
(defun sd:sc () (float *SD:SCALE*))

;; Bat dau / ket thuc lenh: luu bien he thong, undo mark, bat loi
(defun sd:begin ()
  (setq *SD:NOLBLC* nil)
  (setq *SD:OLDERR* *error*
        *SD:VARS*   (mapcar '(lambda (v) (cons v (getvar v)))
                            '("CMDECHO" "OSMODE" "CLAYER")))
  (setq *error* sd:error *SD:IMCLIPS* nil)
  (vla-StartUndoMark (sd:doc))
  (setvar "CMDECHO" 0)
  (sd:ensure))

(defun sd:finish ()
  (setq *SD:CKNAME* nil *SD:VKID* nil)
  ;; bang thong ke tu cap nhat (neu co): ve lai khi lenh vua chay lam doi so lieu thep
  (if (and (not *SD:NBRUN*) (vlax-ldata-get "SD" "TKAUTO")) (vl-catch-all-apply 'sd:tk-refresh '(nil)))
  ;; xoa doi tuong tam (offset...) neu con
  (foreach o *SD:TMP* (vl-catch-all-apply 'vla-Delete (list o)))
  (setq *SD:TMP* nil)
  (foreach p *SD:VARS* (vl-catch-all-apply 'setvar (list (car p) (cdr p))))
  (vl-catch-all-apply 'vla-EndUndoMark (list (sd:doc)))
  (setq *error* *SD:OLDERR*)
  (princ))

(defun sd:error (msg)
  (if (not (wcmatch (strcase msg t) "*cancel*,*quit*,*exit*,*break*"))
    (princ (strcat "\n[SD] Loi: " msg)))
  (sd:finish))

;; Toa do: UCS <-> WCS, cong toa do
(defun sd:w (p) (trans p 1 0))
(defun sd:p+ (p dx dy) (list (+ (car p) dx) (+ (cadr p) dy) 0.0))
(defun sd:getpt (msg base / p)
  (if *SD:BPT* ; che do lo (SDNHAPBANG): diem chen dat san, dung 1 lan
    (progn (setq p *SD:BPT* *SD:BPT* nil) p)
    (progn
      (setq p (if base (getpoint (trans base 0 1) msg) (getpoint msg)))
      (if (listp p) (if p (sd:w p))))))

;; Dinh dang so (khong bi anh huong DIMZIN)
(defun sd:rtos (x p / dz r)
  (setq dz (getvar "DIMZIN"))
  (setvar "DIMZIN" 0)
  (setq r (rtos x 2 p))
  (setvar "DIMZIN" dz)
  r)
(defun sd:num (x)
  (if (equal x (fix x) 1e-6)
    (sd:rtos x 0)
    (vl-string-right-trim "." (vl-string-right-trim "0" (sd:rtos x 3)))))

;; Nhap lieu co gia tri mac dinh
(defun sd:getreal (msg def / v)
  (initget 6)
  (setq v (getreal (strcat msg " <" (sd:num def) ">: ")))
  (if v v def))
(defun sd:getint (msg def / v)
  (initget 6)
  (setq v (getint (strcat msg " <" (itoa def) ">: ")))
  (if v v def))
(defun sd:getstr (msg def / v)
  (setq v (getstring t (strcat msg " <" def ">: ")))
  (if (= v "") def v))

;;; --------------------------------------------------------------------------
;;;  HOP THOAI NHAP LIEU (DCL sinh tu dong) - dung chung cho moi lenh
;;;  Truong: (khoa nhan kieu mac-dinh [lua-chon] [dieu-kien])
;;;    kieu : real (> 0), real0 (so bat ky, >= 0 neu can), int (> 0), int0 (>= 0), str, kw (danh sach), tog (Co/Khong), note
;;;    lua-chon (kw): ("Thang" "Sole" ...) hoac (("Thang" . "Lat thang") ...)
;;;    dieu-kien: ("khoa" "gia-tri1" ...) -> truong chi dung khi truong khoa co mot trong cac gia tri
;;;  (sd:dlg tieu-de truong) -> T (OK, gia tri trong *SD:FV*, doc bang sd:v) hoac nil (Huy)
;;;  Tat hop thoai (lenh SDDLG) -> hoi lan luot tren dong lenh voi cung danh sach truong.
;;; --------------------------------------------------------------------------
(defun sd:v (k) (cdr (assoc k *SD:FV*)))
(defun sd:dlg-on () (/= (vlax-ldata-get "SD" "DLG") "Khong"))
(defun sd:kv (c) (if (listp c) (car c) c))
(defun sd:kl (c) (if (listp c) (cdr c) c))
(defun sd:fok (f vals / c)
  (setq c (nth 5 f))
  (or (null c) (member (cdr (assoc (car c) vals)) (cdr c))))
(defun sd:fstr (f v)
  (cond ((member (nth 2 f) '(real real0)) (sd:num v))
        ((member (nth 2 f) '(int int0)) (itoa v))
        ((= (nth 2 f) 'tog) (if v "1" "0"))
        ((= (nth 2 f) 'kw) (itoa (max 0 (cond ((vl-position v (mapcar 'sd:kv (nth 4 f)))) (0)))))
        (t (if v v ""))))

;; Hoi 1 truong tren dong lenh
(defun sd:ask (f / k lb tp d v)
  (setq lb (strcat "\n" (nth 1 f)) tp (nth 2 f) d (nth 3 f))
  (cond
    ((= tp 'real) (sd:getreal lb d))
    ((= tp 'real0) (initget 0) (cond ((getreal (strcat lb " <" (sd:num d) ">: "))) (d)))
    ((= tp 'int) (sd:getint lb d))
    ((= tp 'int0) (initget 4) (cond ((getint (strcat lb " <" (itoa d) ">: "))) (d)))
    ((= tp 'str) (sd:getstr lb d))
    ((= tp 'bar) (sd:getbar lb d))
    ((= tp 'tog) (initget "Co Khong")
                 (= "Co" (cond ((getkword (strcat lb " [Co/Khong] <" (if d "Co" "Khong") ">: ")))
                               ((if d "Co" "Khong")))))
    ((= tp 'kw) (initget (sd:join (mapcar 'sd:kv (nth 4 f)) " "))
                (cond ((getkword (strcat lb " [" (sd:join (mapcar 'sd:kv (nth 4 f)) "/") "] <" d ">: "))) (d)))
    (t (princ lb) nil)))

;; Ghi DCL tam
;; Ghi 1 dong vao file
(defun sd:wl (f s) (write-line s f))

(defun sd:dlg-dcl (title fields / fn f n half i lb)
  (setq fn (vl-filename-mktemp "sdform" nil ".dcl") n (length fields)
        half (if (> n 12) (/ (1+ n) 2) n) i 0)
  (if (setq f (open fn "w"))
    (progn
      (sd:wl f (strcat "sdform : dialog { label = \"" (vl-string-translate "\"" "'" title) "\";"))
      (if *SD:DPIC*
        (sd:wl f ": image { key = \"img\"; width = 50; height = 17; color = 250; fixed_width = true; fixed_height = true; alignment = centered; }"))
      (sd:wl f ": row { : column {")
      (foreach fd fields
        (if (= i half) (sd:wl f "} : column {"))
        (setq lb (vl-string-translate "\"" "'" (nth 1 fd)))
        (cond
          ((= (nth 2 fd) 'note) (sd:wl f (strcat ": text { label = \"" lb "\"; }")))
          ((= (nth 2 fd) 'tog) (sd:wl f (strcat ": toggle { key = \"f" (itoa i) "\"; label = \"" lb "\"; }")))
          ((= (nth 2 fd) 'kw)
           (sd:wl f (strcat ": row { : text { label = \"" lb "\"; width = 36; } : popup_list { key = \"f" (itoa i)
                        "\"; width = 24; } }")))
          (t (sd:wl f (strcat ": row { : text { label = \"" lb "\"; width = 36; } : edit_box { key = \"f" (itoa i)
                          "\"; edit_width = " (if (member (nth 2 fd) '(str bar)) "22" "12") "; } }"))))
        (setq i (1+ i)))
      (sd:wl f "} }")
      (sd:wl f ": text { key = \"err\"; width = 60; }")
      (sd:wl f ": row { : button { key = \"cmdline\"; label = \"Nhap tren dong lenh\"; } ok_cancel; }")
      (sd:wl f "}")
      (close f)
      fn)))

;; Doc gia tri hien tai trong hop thoai -> ((khoa . gia-tri) ...) hoac chuoi loi
(defun sd:dlg-read (/ i vals s v err)
  (setq i 0)
  (foreach f *SD:DF*
    (setq s (get_tile (strcat "f" (itoa i))))
    (setq v (cond
              ((member (nth 2 f) '(real real0))
               (if (setq v (distof s 2)) v (progn (setq err (cond (err) ((strcat "So khong hop le: " (nth 1 f))))) (nth 3 f))))
              ((member (nth 2 f) '(int int0))
               (if (wcmatch s "#*") (atoi s) (progn (setq err (cond (err) ((strcat "So nguyen khong hop le: " (nth 1 f))))) (nth 3 f))))
              ((= (nth 2 f) 'tog) (= s "1"))
              ((= (nth 2 f) 'kw) (sd:kv (nth (atoi s) (nth 4 f))))
              ((= (nth 2 f) 'note) nil)
              ((= (nth 2 f) 'bar)
               (cond ((sd:parse-bar s))
                     (t (setq err (cond (err) ((strcat "Sai dinh dang (vd 3d20): " (nth 1 f))))) (sd:parse-bar (nth 3 f)))))
              (t s)))
    (if (and (sd:fok f vals) (member (nth 2 f) '(real int)) (numberp v) (<= v 0) (not err))
      (setq err (strcat "Phai lon hon 0: " (nth 1 f))))
    (setq vals (append vals (list (cons (car f) v))) i (1+ i)))
  (if err err vals))

;; Bat / tat cac truong theo dieu kien
(defun sd:dlg-modes (/ vals i)
  (setq vals (sd:dlg-read) i 0)
  (if (listp vals)
    (foreach f *SD:DF*
      (if (nth 5 f) (mode_tile (strcat "f" (itoa i)) (if (sd:fok f vals) 0 1)))
      (setq i (1+ i))))
  (if (listp vals) (sd:pic-draw vals)))

(defun sd:dlg-ok (/ r)
  (setq r (sd:dlg-read))
  (if (= (type r) 'STR)
    (set_tile "err" r)
    (progn (setq *SD:FV* (vl-remove-if '(lambda (x) (null (car x))) r)) (done_dialog 1))))

(defun sd:dlg (title fields)
  (cond
    ;; SDNHAPBANG lay danh sach truong cua lenh (tao file mau): khong hien hop thoai, lenh dung lai
    ((= *SD:BATCH* 'SCHEMA) (setq *SD:BATCH* nil *SD:SCHEMA* (list title fields)) nil)
    ;; che do lo: gia tri lay tu dong bang (o trong = mac dinh)
    (*SD:BATCH* (setq *SD:DF* fields *SD:FV* (sd:nb-fv fields *SD:BATCH*) *SD:BATCH* nil) t)
    (t (sd:dlg-ui title fields))))

(defun sd:dlg-ui (title fields / fn id res i vals)
  (setq *SD:DF* fields *SD:FV* nil res nil *SD:DPIC* (sd:pic-for title))
  (if (and (sd:dlg-on) (setq fn (sd:dlg-dcl title fields))
           (setq id (load_dialog fn)) (> id 0) (new_dialog "sdform" id))
    (progn
      (setq i 0)
      (foreach f fields
        (if (= (nth 2 f) 'kw)
          (progn (start_list (strcat "f" (itoa i))) (mapcar 'add_list (mapcar 'sd:kl (nth 4 f))) (end_list)))
        (if (/= (nth 2 f) 'note) (set_tile (strcat "f" (itoa i)) (sd:fstr f (nth 3 f))))
        (if (/= (nth 2 f) 'note) (action_tile (strcat "f" (itoa i)) "(sd:dlg-modes)"))
        (setq i (1+ i)))
      (sd:dlg-modes)
      (action_tile "accept" "(sd:dlg-ok)")
      (action_tile "cmdline" "(done_dialog 2)")
      (setq res (start_dialog))
      (unload_dialog id)
      (vl-file-delete fn)))
  (setq *SD:DPIC* nil)
  (cond
    ((= res 1) t)
    ((= res 0) (princ "\n[SD] Da huy.") nil)
    (t ; tat hop thoai / DCL loi / chon "Nhap tren dong lenh"
     (foreach f fields
       (setq vals (append vals (list (cons (car f) (if (sd:fok f vals) (sd:ask f) (nth 3 f)))))))
     (setq *SD:FV* vals)
     t)))

;;; SDDLG - bat / tat hop thoai nhap lieu
(defun c:SDDLG (/ v)
  (initget "Co Khong")
  (setq v (cond ((getkword (strcat "\nDung hop thoai nhap lieu [Co/Khong] <" (if (sd:dlg-on) "Co" "Khong") ">: ")))
                ((if (sd:dlg-on) "Co" "Khong"))))
  (vlax-ldata-put "SD" "DLG" v)
  (princ (strcat "\n[SD] Hop thoai nhap lieu: " (if (= v "Co") "BAT" "TAT (hoi tren dong lenh)") "."))
  (princ))

;;; --------------------------------------------------------------------------
;;;  HINH MINH HOA TRONG HOP THOAI (image tile, ve vector khi chay)
;;;  Toa do thiet ke: khung 100 x 75, goc trai duoi. Nguyen to:
;;;   ("L" x1 y1 x2 y2 mau)   ("P" mau kin? (x y x y ...))   ("C" x y r mau)   ("D" x y r mau) cham dac
;;;   ("T" x y "CHU" cao mau can-le)   ("H" x1 x2 y "nhan" mau) kich thuoc ngang
;;;   ("V" x y1 y2 "nhan" mau ["L"]) kich thuoc dung (chu ben phai, "L" = ben trai)
;;; --------------------------------------------------------------------------
;; Font net 4 x 6
(setq *SD:FONT*
  '(("A" (0 0 0 4 2 6 4 4 4 0) (0 3 4 3)) ("B" (0 0 0 6 3 6 4 5 3 3 0 3) (3 3 4 2 4 1 3 0 0 0))
    ("C" (4 1 3 0 1 0 0 1 0 5 1 6 3 6 4 5)) ("D" (0 0 0 6 3 6 4 5 4 1 3 0 0 0))
    ("E" (4 0 0 0 0 6 4 6) (0 3 3 3)) ("F" (0 0 0 6 4 6) (0 3 3 3))
    ("G" (4 5 3 6 1 6 0 5 0 1 1 0 3 0 4 1 4 3 2 3)) ("H" (0 0 0 6) (4 0 4 6) (0 3 4 3))
    ("I" (1 0 3 0) (2 0 2 6) (1 6 3 6)) ("J" (0 1 1 0 3 0 4 1 4 6)) ("K" (0 0 0 6) (4 6 0 2) (1 3 4 0))
    ("L" (0 6 0 0 4 0)) ("M" (0 0 0 6 2 3 4 6 4 0)) ("N" (0 0 0 6 4 0 4 6))
    ("O" (1 0 0 1 0 5 1 6 3 6 4 5 4 1 3 0 1 0)) ("P" (0 0 0 6 3 6 4 5 4 4 3 3 0 3))
    ("Q" (1 0 0 1 0 5 1 6 3 6 4 5 4 1 3 0 1 0) (2 2 4 0)) ("R" (0 0 0 6 3 6 4 5 4 4 3 3 0 3) (2 3 4 0))
    ("S" (4 5 3 6 1 6 0 5 0 4 1 3 3 3 4 2 4 1 3 0 1 0 0 1)) ("T" (0 6 4 6) (2 6 2 0))
    ("U" (0 6 0 1 1 0 3 0 4 1 4 6)) ("V" (0 6 2 0 4 6)) ("W" (0 6 1 0 2 3 3 0 4 6))
    ("X" (0 0 4 6) (0 6 4 0)) ("Y" (0 6 2 3 4 6) (2 3 2 0)) ("Z" (0 6 4 6 0 0 4 0))
    ("0" (1 0 0 1 0 5 1 6 3 6 4 5 4 1 3 0 1 0)) ("1" (1 5 2 6 2 0) (1 0 3 0))
    ("2" (0 5 1 6 3 6 4 5 4 4 0 0 4 0)) ("3" (0 5 1 6 3 6 4 5 4 4 3 3 4 2 4 1 3 0 1 0 0 1) (1 3 3 3))
    ("4" (3 0 3 6 0 2 4 2)) ("5" (4 6 0 6 0 3 3 3 4 2 4 1 3 0 0 0))
    ("6" (4 5 3 6 1 6 0 5 0 1 1 0 3 0 4 1 4 2 3 3 0 3)) ("7" (0 6 4 6 1 0))
    ("8" (1 3 0 4 0 5 1 6 3 6 4 5 4 4 3 3 1 3 0 2 0 1 1 0 3 0 4 1 4 2 3 3))
    ("9" (0 1 1 0 3 0 4 1 4 5 3 6 1 6 0 5 0 4 1 3 4 3))
    ("-" (1 3 3 3)) ("=" (1 2 3 2) (1 4 3 4)) ("/" (0 0 4 6)) ("." (2 0 2 1)) ("+" (2 1 2 5) (0 3 4 3))
    ("(" (3 6 2 5 2 1 3 0)) (")" (1 6 2 5 2 1 1 0)) (":" (2 1 2 2) (2 4 2 5)) ("@" (4 1 3 0 1 0 0 1 0 5 1 6 3 6 4 5 4 2 2 2 2 4 4 4))))

(defun sd:pv (v k) (cdr (assoc k v)))
(defun sd:pnum (v k def / x) (setq x (sd:pv v k)) (if (numberp x) x def))

;; Doi nguyen to -> danh sach doan thang (x1 y1 x2 y2 mau) trong toa do thiet ke
(defun sd:pic-segs (prims / r e x y s h c w k g pts i a)
  (foreach e prims
    (cond
      ((= (car e) "L") (setq r (cons (cdr e) r)))
      ((= (car e) "P")
       (setq pts (nth 3 e) c (cadr e))
       (if (caddr e) (setq pts (append pts (list (car pts) (cadr pts)))))
       (while (cdddr pts)
         (setq r (cons (list (car pts) (cadr pts) (caddr pts) (cadddr pts) c) r) pts (cddr pts))))
      ((member (car e) '("C" "D"))
       (foreach rr (if (= (car e) "D") (list (nth 3 e) (* 0.66 (nth 3 e)) (* 0.33 (nth 3 e))) (list (nth 3 e)))
         (setq i 0)
         (repeat 12
           (setq a (* i (/ pi 6)))
           (setq r (cons (list (+ (nth 1 e) (* rr (cos a))) (+ (nth 2 e) (* rr (sin a)))
                               (+ (nth 1 e) (* rr (cos (+ a (/ pi 6))))) (+ (nth 2 e) (* rr (sin (+ a (/ pi 6)))))
                               (nth 4 e))
                         r)
                 i (1+ i)))))
      ((= (car e) "T")
       (setq s (strcase (nth 3 e)) h (nth 4 e) c (nth 5 e) k (/ h 6.0) w (* k (- (* 5 (strlen s)) 1))
             x (cond ((= (nth 6 e) "C") (- (nth 1 e) (/ w 2))) ((= (nth 6 e) "R") (- (nth 1 e) w)) (t (nth 1 e)))
             y (- (nth 2 e) (/ h 2.0)) i 0)
       (repeat (strlen s)
         (foreach st (cdr (assoc (substr s (1+ i) 1) *SD:FONT*))
           (setq g st)
           (while (cddr g)
             (setq r (cons (list (+ x (* k (+ (* 5 i) (car g)))) (+ y (* k (cadr g)))
                                 (+ x (* k (+ (* 5 i) (caddr g)))) (+ y (* k (cadddr g))) c)
                           r)
                   g (cddr g))))
         (setq i (1+ i))))
      ((= (car e) "H")
       (setq x (nth 1 e) w (nth 2 e) y (nth 3 e) c (nth 5 e))
       (setq r (append (list (list x y w y c) (list x (- y 1.5) x (+ y 1.5) c) (list w (- y 1.5) w (+ y 1.5) c)) r)
             r (append (sd:pic-segs (list (list "T" (/ (+ x w) 2.0) (if (> y 68) (- y 3.5) (+ y 3.5)) (nth 4 e) 4.0 c "C"))) r)))
      ((= (car e) "V")
       (setq x (nth 1 e) y (nth 2 e) w (nth 3 e) c (nth 5 e))
       (setq r (append (list (list x y x w c) (list (- x 1.5) y (+ x 1.5) y c) (list (- x 1.5) w (+ x 1.5) w c)) r)
             r (append (sd:pic-segs (list (if (= (nth 6 e) "L")
                                              (list "T" (- x 2.0) (/ (+ y w) 2.0) (nth 4 e) 4.0 c "R")
                                              (list "T" (+ x 2.0) (/ (+ y w) 2.0) (nth 4 e) 4.0 c "L")))) r)))))
  r)

;; Ve len image tile "img"
(defun sd:pic-draw (vals / prims segs w h k ox oy)
  (if (and *SD:DPIC* (setq prims (vl-catch-all-apply *SD:DPIC* (list vals))) (listp prims)
           (setq segs (vl-catch-all-apply 'sd:pic-segs (list prims))) (listp segs))
    (progn
      (setq w (dimx_tile "img") h (dimy_tile "img") k (min (/ w 100.0) (/ h 75.0))
            ox (/ (- w (* 100 k)) 2.0) oy (/ (- h (* 75 k)) 2.0))
      (start_image "img")
      (fill_image 0 0 w h 250)
      (foreach s segs
        (vector_image (fix (+ ox (* k (nth 0 s)))) (fix (+ oy (* k (- 75 (nth 1 s)))))
                      (fix (+ ox (* k (nth 2 s)))) (fix (+ oy (* k (- 75 (nth 3 s))))) (nth 4 s)))
      (end_image))))

;; Hang cham (thanh thep) n thanh tu x1 den x2 tai y
(defun sd:pic-bars (n x1 x2 y r c / i l)
  (setq n (max 1 (min n 8)) i 0)
  (repeat n
    (setq l (cons (list "D" (if (= n 1) (/ (+ x1 x2) 2.0) (+ x1 (* i (/ (- x2 x1) (1- n))))) y r c) l) i (1+ i)))
  l)
(defun sd:rectp (x y w h c) (list "P" c t (list x y (+ x w) y (+ x w) (+ y h) x (+ y h))))

;;; ---- Hinh cho tung lenh (v = gia tri hien tai trong hop thoai) -------------
(defun sd:pic-dam (v / top bot)
  (setq top (sd:pv v "top") bot (sd:pv v "bot"))
  (append
    (list (sd:rectp 35 12 30 50 7) (sd:rectp 38.5 15.5 23 43 3)
          (list "L" 38.5 55 42 51.5 3) (list "L" 41 58.5 44.5 55 3)
          (list "H" 35 65 6 "B" 4) (list "V" 70 12 62 "H" 4)
          (list "T" 22 57 (if (listp top) (strcat (itoa (car top)) "D" (sd:num (cadr top))) "TOP") 4 2 "C")
          (list "T" 22 19 (if (listp bot) (strcat (itoa (car bot)) "D" (sd:num (cadr bot))) "BOT") 4 2 "C")
          (list "T" 22 37 "DAI" 4 3 "C") (list "L" 27 37 38 37 3))
    (sd:pic-bars (if (listp top) (car top) 2) 42 58 54.5 1.6 1)
    (sd:pic-bars (if (listp bot) (car bot) 3) 42 58 19 1.8 1)))

(defun sd:pic-cot (v / nb nh l i)
  (setq nb (max 2 (min 6 (fix (sd:pnum v "nb" 3)))) nh (max 2 (min 6 (fix (sd:pnum v "nh" 3)))))
  (setq l (append (list (sd:rectp 30 8 40 56 7) (sd:rectp 33.5 11.5 33 49 3)
                        (list "H" 30 70 3 "B" 4) (list "V" 74 8 64 "H" 4) (list "T" 15 36 "DAI" 4 3 "C"))
                  (sd:pic-bars nb 37 63 15 1.6 1) (sd:pic-bars nb 37 63 57 1.6 1)))
  (if (/= (sd:pv v "dp") "Khong")
    (progn
      (if (> nb 2) (setq l (cons (list "P" 6 nil (list 52 18 50 15 50 57 48 54)) l)))
      (if (> nh 2) (setq l (cons (list "P" 6 nil (list 40 38 37 36 63 36 60 34)) l)))
      (setq l (cons (list "T" 15 28 (if (= (sd:pv v "lp") "Kin") "DAI KIN" "MOC C") 3 6 "C") l))))
  (setq i 1)
  (repeat (- nh 2)
    (setq l (append l (list (list "D" 37 (+ 15 (* i (/ 42.0 (1- nh)))) 1.6 1) (list "D" 63 (+ 15 (* i (/ 42.0 (1- nh)))) 1.6 1)))
          i (1+ i)))
  l)

(defun sd:pic-banma (v / nx ny l x y xs ys)
  (setq nx (max 1 (min 5 (fix (sd:pnum v "nx" 2)))) ny (max 1 (min 5 (fix (sd:pnum v "ny" 2))))
        xs (if (= nx 1) '(50.0) (mapcar '(lambda (i) (+ 33 (* i (/ 34.0 (1- nx))))) (sd:range 0 (1- nx))))
        ys (if (= ny 1) '(37.5) (mapcar '(lambda (i) (+ 17 (* i (/ 41.0 (1- ny))))) (sd:range 0 (1- ny))))
        l (list (sd:rectp 25 9 50 57 5) (list "H" 25 75 3 "B" 4) (list "V" 79 9 66 "H" 4)
                (list "H" 25 (car xs) 70 "EX" 4) (list "V" 18 9 (car ys) "EY" 4)))
  (foreach x xs (foreach y ys (setq l (cons (list "C" x y 2.5 6) l))))
  (cons (list "T" (+ (last xs) 4) (+ (last ys) 4) "D0" 3.5 6 "L") l))

(defun sd:pic-ih (v)
  (list (list "P" 5 t '(30 10 70 10 70 16 53 16 53 58 70 58 70 64 30 64 30 58 47 58 47 16 30 16))
        (list "H" 30 70 4 "B" 4) (list "V" 76 10 64 "H" 4)
        (list "L" 53 37 62 37 4) (list "T" 63 37 "TW" 4 4 "L")
        (list "L" 30 61 22 61 4) (list "T" 21 61 "TF" 4 4 "R")
        (list "T" 50 70 (if (= (sd:pv v "typ") "I") "I" "H") 5 7 "C")))

(defun sd:pic-thep (v / sh pts l c)
  (setq sh (assoc (cond ((sd:pv v "shp")) ("Thang")) *SD:SHAPES*))
  (setq pts (mapcar '(lambda (p) (list (+ 15 (* 70 (car p))) (+ 15 (* 45 (cadr p))))) (nth 3 sh)))
  (setq l (list (list "P" 1 nil (apply 'append pts))))
  (foreach s (nth 4 sh)
    (setq l (cons (list "L" (+ 15 (* 70 (car (car s)))) (+ 15 (* 45 (cadr (car s))))
                        (+ 15 (* 70 (car (cadr s)))) (+ 15 (* 45 (cadr (cadr s)))) 1)
                  l)))
  (foreach lb (nth 5 sh)
    (setq l (cons (list "T" (+ 15 (* 70 (nth 1 lb))) (+ 15 (* 45 (nth 2 lb))) (nth (car lb) '("A" "B" "C")) 5 2
                        (cond ((= (nth 3 lb) "ML") "L") ((= (nth 3 lb) "MR") "R") (t "C")))
                  l)))
  (cons (list "T" 50 68 (strcat (itoa (fix (sd:pnum v "n" 2))) " D" (sd:num (sd:pnum v "d" 16)) " X " (itoa (fix (sd:pnum v "k" 1))) " CK") 4 7 "C") l))

(defun sd:pic-gach (v / pat W H a l sz tiles e ok)
  (setq pat (cond ((sd:pv v "pat")) ("Thang")) W (sd:pnum v "W" 600) H (sd:pnum v "H" 600))
  (if (and (member pat '("Xuongca" "Chevron")) (< (abs (- W H)) 1)) (setq W (* 3 H)))
  (setq a (max 0.25 (min 4.0 (/ W H))) sz 9.0
        tiles (cond ((= pat "Xuongca") (sd:gen-herring 0 100 0 75 (* sz (max a (/ 1 a))) sz 1.0))
                    ((= pat "Chevron") (sd:gen-chevron 0 100 0 75 (* sz (max a (/ 1 a))) sz 1.0 (* pi (/ (max 20.0 (min 65.0 (sd:pnum v "cva" 45.0))) 180.0))))
                    (t (sd:gen-grid 0 100 0 75 (* sz a) sz 1.0 "Goc" (if (= pat "Sole") (sd:pnum v "off" 0.5) 0.0)))))
  (foreach tl tiles
    (setq e (mapcar '(lambda (p) (list (+ 8 (* 0.84 (car p))) (+ 6 (* 0.84 (cadr p))))) (car tl))
          ok (vl-every '(lambda (p) (and (<= 8 (car p) 92) (<= 6 (cadr p) 69))) e))
    (if ok (setq l (cons (list "P" 30 t (apply 'append e)) l))))
  (setq l (cons (sd:rectp 8 6 84 63 7) l))
  (if (sd:pv v "bord") (setq l (cons (sd:rectp 4 2 92 71 40) l)))
  l)

(defun sd:pic-len (v / l x)
  (setq l (list (list "L" 14 15 95 15 7) (list "L" 14 70 14 15 7) (list "T" 34 45 "TUONG" 5 8 "C")
                (sd:rectp 55 15 14 40 8) (list "T" 62 35 "CUA" 4 8 "C")) x 14)
  (while (< x 54) (setq l (cons (sd:rectp x 15 (min 15 (- 54 x)) 7 30) l) x (+ x 16)))
  (setq x 70)
  (while (< x 95) (setq l (cons (sd:rectp x 15 (min 15 (- 95 x)) 7 30) l) x (+ x 16)))
  (append l (list (list "H" 14 29 9 "LC" 4) (list "V" 10 15 22 "HC" 4 "L"))))

(defun sd:pic-lop (v / lays n tot y l i th)
  (setq lays (sd:parse-layers (cond ((sd:pv v "lop")) (""))) n (length lays)
        tot (apply '+ (cons 0.0 (mapcar 'cadr lays))) i 0)
  (if (= n 0) (setq lays '(("1" 20.0) ("2" 30.0) ("3" 150.0)) n 3 tot 200.0))
  (if (= (sd:pv v "ori") "Tuong")
    (progn (setq y 20)
      (foreach ly lays
        (setq th (max 5.0 (* 45.0 (/ (cadr ly) tot))) l (cons (sd:rectp y 8 th 60 (nth (rem i 4) '(30 7 3 8))) l)
              l (cons (list "T" (+ y (/ th 2)) 72 (itoa (1+ i)) 4 7 "C") l) y (+ y th) i (1+ i))))
    (progn (setq y 65)
      (foreach ly lays
        (setq th (max 5.0 (* 45.0 (/ (cadr ly) tot))) l (cons (sd:rectp 10 (- y th) 70 th (nth (rem i 4) '(30 7 3 8))) l)
              l (cons (list "T" 88 (- y (/ th 2)) (itoa (1+ i)) 4 7 "C") l) y (- y th) i (1+ i)))))
  l)

(defun sd:pic-khung (v / w h x y)
  (if (= (sd:pv v "ori") "Dung") (setq w 48.0 h 68.0) (setq w 90.0 h 64.0))
  (setq x (/ (- 100 w) 2) y (/ (- 75 h) 2))
  (list (sd:rectp x y w h 8) (sd:rectp (+ x 4) (+ y 2) (- w 6) (- h 4) 7)
        (sd:rectp (- (+ x w) 2 22) (+ y 2) 22 8 7) (list "L" (- (+ x w) 24) (+ y 6) (- (+ x w) 2) (+ y 6) 7)
        (list "T" (+ x (/ w 2)) (+ y (/ h 2) 4) (cond ((sd:pv v "sz")) ("A1")) 8 2 "C")
        (list "T" (+ x (/ w 2)) (+ y (/ h 2) -8) (strcat "1/" (itoa (fix (sd:pnum v "sc" 100)))) 4 4 "C")))

(defun sd:pic-truc (v / l)
  (foreach x '(20 45 70)
    (setq l (append l (list (list "L" x 8 x 62 1) (list "C" x 67 4 6)
                            (list "T" x 67 (itoa (/ (+ x 5) 25)) 4 7 "C")))))
  (foreach y '(15 50)
    (setq l (append l (list (list "L" 10 y 80 y 1) (list "C" 86 y 4 6)
                            (list "T" 86 y (if (= y 15) "A" "B") 4 7 "C")))))
  (append l (list (list "H" 20 45 3 "GX" 4) (list "V" 93 15 50 "GY" 4))))

(defun sd:pic-cfcot (v)
  (append (list (sd:rectp 40 25 20 25 7) (sd:rectp 37 22 26 31 30) (sd:rectp 31 16 38 43 5) (sd:rectp 29 14 42 47 5)
                (list "D" 27 12 1.5 6) (list "D" 73 12 1.5 6) (list "D" 27 63 1.5 6) (list "D" 73 63 1.5 6)
                (list "H" 40 60 5 "B" 4) (list "V" 80 25 50 "H" 4) (list "T" 50 68 "VAN SUON GONG TY" 3.5 7 "C"))
          (mapcar '(lambda (x) (sd:rectp x 19 3 3 3)) '(41 48.5 56)) (mapcar '(lambda (x) (sd:rectp x 53 3 3 3)) '(41 48.5 56))))

(defun sd:pic-cfvach (v / two l)
  (setq two (/= (sd:pv v "two") "Motmat")
        l (list (sd:rectp 45 8 10 60 7) (list "L" 43 8 43 68 30) (list "L" 40 8 40 68 3)
                (list "V" 60 8 68 "HC" 4) (list "H" 45 55 72 "TW" 4)))
  (if two
    (append l (list (list "L" 57 8 57 68 30) (list "L" 60 8 60 68 3))
            (apply 'append (mapcar '(lambda (y) (list (sd:rectp 36 (- y 2) 4 4 5) (sd:rectp 60 (- y 2) 4 4 5)
                                                      (list "L" 33 y 67 y 6))) '(18 38 58))))
    (append l (apply 'append (mapcar '(lambda (y) (list (sd:rectp 36 (- y 2) 4 4 5) (list "L" 36 y (- 36 (* 0.6 y)) 8 6)))
                                     '(28 52)))
            (list (list "T" 84 40 "1 MAT" 4 7 "C")))))

(defun sd:pic-cftm (v / ds l)
  (setq ds (atoi (cond ((sd:pv v "dside")) ("1")))
        l (list (sd:rectp 25 10 50 55 7) (sd:rectp 31 16 38 43 7) (sd:rectp 33 18 34 39 30) (sd:rectp 23 8 54 59 30)
                (list "T" 50 13 "1" 4 7 "C") (list "T" 72 37 "2" 4 7 "C") (list "T" 50 62 "3" 4 7 "C") (list "T" 28 37 "4" 4 7 "C")
                (list "H" 31 69 4 "LX" 4) (list "V" 82 16 59 "LY" 4)))
  (cons (cond ((= ds 2) (sd:rectp 66 30 12 14 1)) ((= ds 3) (sd:rectp 43 56 14 12 1)) ((= ds 4) (sd:rectp 22 30 12 14 1))
              (t (sd:rectp 43 7 14 12 1)))
        l))

(defun sd:pic-cfmong (v)
  (list (sd:rectp 30 15 40 20 7) (list "L" 28 15 28 35 30) (list "L" 72 15 72 35 30)
        (list "L" 26 15 26 35 3) (list "L" 74 15 74 35 3)
        (list "L" 26 30 12 12 6) (list "L" 74 30 88 12 6) (list "L" 12 8 12 16 6) (list "L" 88 8 88 16 6)
        (list "L" 5 12 95 12 8) (list "V" 92 15 35 "HM" 4) (list "H" 30 70 42 (if (= (sd:pv v "typ") "Bang") "LY" "BX") 4)))

(defun sd:pic-cfthang (v / l i x y)
  (setq l (list (list "L" 5 8 95 8 8)) i 0 x 15 y 8)
  (repeat 6 (setq l (cons (list "P" 7 nil (list x y x (+ y 7) (+ x 9) (+ y 7))) l) x (+ x 9) y (+ y 7) i (1+ i)))
  (setq l (append l (list (list "L" x y 92 y 7) (list "L" 92 y 92 (- y 6) 7) (list "L" 92 (- y 6) 76 (- y 6) 7)
                          (list "L" 76 (- y 6) 20 5 7) (list "L" 76 (- y 8) 20 3 30)
                          (list "V" 12 8 15 "R" 4 "L") (list "H" 24 33 27 "G" 4) (list "H" 76 92 54 "LC" 4))))
  (foreach px '(30 45 60 82) (setq l (cons (list "L" px 8 px (if (= px 82) (- y 9) (+ 3 (* 0.8 (- px 20)))) 6) l)))
  l)

(defun sd:pic-cfdam (v)
  (list (list "P" 7 t '(42 25 58 25 58 50 90 50 90 57 10 57 10 50 42 50)) (sd:rectp 41 23 18 2 30)
        (list "L" 40 23 40 50 30) (list "L" 60 23 60 50 30) (sd:rectp 30 20 40 2 5)
        (list "L" 33 20 33 5 140) (list "L" 67 20 67 5 140) (list "L" 33 10 67 10 2) (list "L" 33 10 67 18 2)
        (list "L" 5 5 95 5 8) (list "H" 42 58 62 "B" 4) (list "V" 93 25 57 "H" 4) (list "V" 5 5 50 "HS" 4)))

(defun sd:pic-giao (v / typ l x)
  (setq typ (cond ((sd:pv v "TYPE")) ((sd:gi "TYPE")))
        l (list (sd:rectp 5 63 90 6 7) (sd:rectp 5 61 90 2 30) (list "L" 5 58 95 58 5) (list "L" 5 5 95 5 8)
                (list "V" 97 5 63 "HS" 4)))
  (foreach x '(15 38 61 84)
    (setq l (append l (if (= typ "Chong")
                        (list (list "L" x 6 x 58 140) (list "L" (- x 2) 6 (+ x 2) 6 140))
                        (list (list "L" x 6 x 12 7) (list "L" (- x 3) 6 (+ x 3) 6 7) (list "L" x 12 x 52 140)
                              (list "L" x 52 x 58 7) (list "L" (- x 2) 58 (+ x 2) 58 7))))))
  (if (/= typ "Chong")
    (foreach y '(14 32 50)
      (setq l (append l (list (list "L" 15 y 84 y 2))))))
  (if (/= typ "Chong") (setq l (append l (list (list "L" 15 14 38 32 2) (list "L" 15 32 38 50 2) (list "L" 61 14 84 32 2)))))
  (if (= typ "Khung") (setq l (cons (list "T" 50 40 "KHUNG" 4 7 "C") l)))
  (cons (list "T" 50 72 (cond ((= typ "Khung") "GIAO KHUNG") ((= typ "Chong") "CAY CHONG") (t "GIAO NEM")) 4 7 "C") l))

(defun sd:pic-cfset (v)
  (list (sd:rectp 55 8 20 60 7) (list "L" 53 8 53 68 30) (sd:rectp 48 8 4 60 3)
        (sd:rectp 42 20 6 4 5) (sd:rectp 42 46 6 4 5) (list "L" 30 22 82 22 6) (list "L" 30 48 82 48 6)
        (list "T" 53 72 "VAN" 3.5 30 "C") (list "T" 46 3 "SUON" 3.5 3 "C") (list "T" 30 30 "GONG" 3.5 5 "C")
        (list "T" 25 48 "TY" 3.5 6 "R")))

(defun sd:pic-thepset (v)
  (list (list "L" 5 40 60 40 1) (list "L" 40 43 95 43 1) (list "H" 40 60 30 "LAP" 4)
        (list "P" 2 nil '(10 10 10 25 30 25 30 10 10 10 14 14)) (list "T" 40 15 "MOC 135" 4 2 "L")
        (list "T" 50 62 (strcat "CAY " (sd:num (sd:pnum v "STOCK" 11700))) 4 7 "C")))

(defun sd:pic-datho (v)
  (list (sd:rectp 5 5 90 65 7) (sd:rectp 9 9 82 57 8)
        (sd:rectp 10 10 25 25 30) (sd:rectp 36 10 25 25 30) (sd:rectp 62 10 25 25 30) (sd:rectp 10 36 25 12 30)
        (sd:rectp 36 36 25 12 30) (sd:rectp 62 36 12 28 30)
        (list "H" 5 95 2 "SL" 4) (list "V" 97 5 70 "SB" 4) (list "T" 45 58 "XEN BIEN" 3.5 8 "C")))

(defun sd:pic-giacong (v)
  (list (sd:rectp 5 5 90 65 8) (list "T" 8 64 "G1-C3" 4 7 "L")
        (list "P" 30 t '(25 15 75 15 75 40 55 50 25 50)) (list "H" 25 75 9 "W" 4) (list "V" 18 15 50 "H" 4)
        (list "T" 70 50 "CANH XIEN" 3 4 "L")))

(defun sd:pic-toiuu (v)
  (list (sd:rectp 5 40 90 6 7) (list "L" 35 40 35 46 1) (list "L" 60 40 60 46 1) (list "L" 82 40 82 46 1)
        (list "L" 84 40 95 46 8) (list "L" 88 40 95 44 8) (list "H" 5 95 32 (sd:num (sd:pnum v "cap" 11700)) 4)
        (list "T" 20 52 "3600" 3.5 2 "C") (list "T" 47 52 "3000" 3.5 2 "C") (list "T" 71 52 "2600" 3.5 2 "C")
        (list "T" 90 52 "DU" 3.5 8 "C")))

(defun sd:pic-mc (v)
  (list (list "L" 10 40 90 40 8) (list "P" 6 nil '(10 40 22 40)) (list "P" 6 nil '(78 40 90 40))
        (list "L" 10 40 10 55 6) (list "L" 90 40 90 55 6) (list "T" 10 62 (cond ((sd:pv v "lab")) ("1")) 6 7 "C")
        (list "T" 90 62 (cond ((sd:pv v "lab")) ("1")) 6 7 "C")))

;; Cung tron (do) -> da tuyen
(defun sd:pic-arc (x y r a1 a2 c / l i n a)
  (setq n 8 i 0)
  (repeat (1+ n)
    (setq a (* pi (/ (+ a1 (* i (/ (- a2 a1) (float n)))) 180.0))
          l (append l (list (+ x (* r (cos a))) (+ y (* r (sin a))))) i (1+ i)))
  (list "P" c nil l))

(defun sd:pic-set (v / sc ds)
  (setq sc (itoa (fix (sd:pnum v "sc" 100))) ds (itoa (fix (sd:pnum v "ds" 25))))
  (list (sd:rectp 4 6 56 60 8) (sd:rectp 10 18 38 38 7) (list "L" 10 37 48 37 7) (list "L" 29 18 29 56 7)
        (list "H" 10 48 60 "3800" 4) (list "T" 32 11 (strcat "MAT BANG 1/" sc) 3.5 7 "C")
        (list "C" 48 37 6 2) (list "L" 54 37 66 42 2)
        (list "C" 82 42 15 2) (sd:rectp 72 36 20 12 7) (list "L" 72 42 92 42 4)
        (list "T" 82 22 (strcat "CHI TIET 1/" ds) 3.5 7 "C")
        (list "T" 82 15 "LAYER DIM TEXT" 2.5 8 "C")))

(defun sd:pic-gachtk (v / l x y)
  (setq y 50)
  (repeat 3
    (setq x 6)
    (repeat 4 (setq l (cons (sd:rectp x y 9 9 (if (< x 30) 30 7)) l) x (+ x 10)))
    (setq y (- y 10)))
  (setq l (append l (list (sd:rectp 6 20 40 40 7) (list "T" 26 14 "VIEN CAT" 3.5 1 "C")
                          (list "T" 26 66 (strcat "HAO HUT " (sd:num (sd:pnum v "loss" 3)) "/100") 3.5 2 "C"))))
  (foreach r '(55 47 39 31 23)
    (setq l (cons (list "L" 54 r 96 r 8) l)))
  (append l (list (sd:rectp 54 15 42 48 7) (list "L" 64 15 64 63 8) (list "L" 80 15 80 63 8)
                  (list "T" 59 59 "MA" 3 4 "C") (list "T" 72 59 "SL" 3 4 "C") (list "T" 88 59 "M2" 3 4 "C")
                  (list "T" 59 51 "G1" 3 7 "C") (list "T" 72 51 "124" 3 7 "C") (list "T" 88 51 "44.6" 3 7 "C")
                  (list "T" 59 43 "G1" 3 1 "C") (list "T" 72 43 "18" 3 1 "C")
                  (list "T" 75 8 (strcat "MACH CAT " (sd:num (sd:pnum v "kerf" 3))) 3.5 4 "C"))))

(defun sd:pic-khoda (v / op l)
  (setq op (sd:pv v "op")
        l (list (list "P" 8 t '(14 10 70 10 74 14 18 14)) (sd:rectp 10 14 60 36 30) (sd:rectp 14 18 60 36 30)
                (sd:rectp 18 22 60 36 7) (list "T" 48 46 (cond ((= (type (sd:pv v "id")) 'STR) (sd:pv v "id")) ("T01")) 5 7 "C")
                (list "H" 18 78 64 (sd:num (sd:pnum v "L" 2700)) 4) (list "V" 82 22 58 (sd:num (sd:pnum v "B" 1800)) 4)
                (list "T" 48 32 (strcat "SL " (itoa (fix (sd:pnum v "n" 3)))) 4 2 "C")))
  (cond
    ((= op "Them") (append l (list (list "L" 4 64 14 64 3) (list "L" 9 59 9 69 3))))
    ((= op "Xoa") (append l (list (list "L" 20 24 76 56 1) (list "L" 20 56 76 24 1))))
    ((member op '("Nhap" "Xuat"))
     (append l (list (sd:rectp 84 4 14 16 7) (list "T" 91 12 "CSV" 3 7 "C")
                     (if (= op "Nhap") (list "P" 4 nil '(84 12 74 12 77 14 74 12 77 10)) (list "P" 4 nil '(74 12 84 12 81 14 84 12 81 10))))))
    ((sd:pv v "mode") (append l (list (sd:rectp 84 4 14 16 7) (list "T" 91 12 "CSV" 3 7 "C"))))
    (t l)))

(defun sd:pic-giaotk (v / mode l y i)
  (setq mode (cond ((sd:pv v "mode")) ((sd:pv v "hl") "Dinhmuc")) i 0)
  (cond
    ((= mode "Dinhmuc")
     (setq l (list (sd:rectp 8 8 84 58 7) (list "L" 26 8 26 66 7) (list "L" 8 56 92 56 7)
                   (list "L" 8 66 26 56 8) (list "T" 12 58 "H" 3 4 "C") (list "T" 22 63 "T" 3 4 "C")))
     (foreach x '(39 52 65 78) (setq l (cons (list "L" x 8 x 66 8) l)))
     (foreach yy '(46 36 26 16) (setq l (cons (list "L" 8 yy 92 yy 8) l)))
     (foreach s '(("3000" 51) ("3300" 41) ("3600" 31) ("4200" 21) ("4500" 11))
       (setq l (cons (list "T" 17 (cadr s) (car s) 3 4 "C") l)))
     (foreach s '(("120" 32) ("150" 45) ("180" 58) ("200" 71) ("250" 85))
       (setq l (cons (list "T" (cadr s) 61 (car s) 3 4 "C") l)))
     (cons (list "T" 50 71 "DINH MUC / 100 M2" 3.5 2 "C") l))
    (t
     (setq y 8 l (list (list "L" 5 8 60 8 8)))
     (repeat 3
       (setq l (append l (list (sd:rectp 8 (+ y 17) 50 3 7)
                               (list "L" 14 y 14 (+ y 17) 140) (list "L" 26 y 26 (+ y 17) 140)
                               (list "L" 38 y 38 (+ y 17) 140) (list "L" 50 y 50 (+ y 17) 140)
                               (list "T" 4 (+ y 10) (itoa (setq i (1+ i))) 3.5 2 "C")))
             y (+ y 20)))
     (setq l (append l (list (list "V" 62 8 25 "HT" 4))))
     (if (= mode "Csv")
       (append l (list (sd:rectp 74 46 20 22 7) (list "T" 84 57 "CSV" 4 7 "C") (list "P" 4 nil '(84 46 84 36 82 39 84 36 86 39))
                       (sd:rectp 70 8 26 24 7) (list "L" 70 24 96 24 8) (list "L" 70 16 96 16 8) (list "T" 83 28 "TONG" 3 2 "C")))
       (append l (list (sd:rectp 70 8 26 24 7) (list "L" 70 24 96 24 8) (list "L" 70 16 96 16 8) (list "L" 83 8 83 32 8)
                       (list "T" 83 40 "SAN DAM" 3.5 2 "C") (list "T" 83 28 "TANG" 3 7 "C")))))))

(defun sd:pic-so (v / pre suf n st l i s)
  (setq pre (cond ((= (type (sd:pv v "pre")) 'STR) (sd:pv v "pre")) ("C")) suf (cond ((= (type (sd:pv v "suf")) 'STR) (sd:pv v "suf")) (""))
        n (fix (sd:pnum v "n" 1)) st (fix (sd:pnum v "st" 1)) i 0)
  (foreach x '(18 50 82)
    (setq s (strcat pre (itoa (+ n (* i st))) suf) i (1+ i))
    (if (= (sd:pv v "mode") "Sua")
      (setq l (append l (list (list "T" x 52 "TEXT" 4 8 "C") (list "P" 4 nil (list x 45 x 33 (- x 2) 36 x 33 (+ x 2) 36))
                              (list "T" x 24 s 5 2 "C"))))
      (setq l (append l (list (list "D" x 20 1.2 1) (list "L" x 20 (+ x 5) 30 8) (list "T" (+ x 6) 34 s 5 2 "L"))))))
  (append l (list (list "L" 30 62 70 62 8) (list "T" 50 68 (strcat "BUOC " (itoa st)) 4 4 "C"))))

(defun sd:pic-rev (v / rv l x y)
  (setq rv (cond ((= (type (sd:pv v "rv")) 'STR) (sd:pv v "rv")) ("1")))
  (setq l (list (sd:rectp 22 22 40 26 7) (list "L" 22 35 62 35 7) (list "T" 42 41 "SUA" 4 8 "C")))
  (if (sd:pv v "cloud")
    (progn
      (setq x 17)
      (while (< x 67) (setq l (cons (sd:pic-arc (+ x 2.5) 15 2.5 180 360 1) l) l (cons (sd:pic-arc (+ x 2.5) 55 2.5 0 180 1) l) x (+ x 5)))
      (setq y 15)
      (while (< y 55) (setq l (cons (sd:pic-arc 17 (+ y 2.5) 2.5 90 270 1) l) l (cons (sd:pic-arc 67 (+ y 2.5) 2.5 -90 90 1) l) y (+ y 5)))))
  (append l (list (list "P" 2 t '(72 56 88 56 80 70)) (list "T" 80 61 rv 5 2 "C")
                  (list "T" 80 10 "REV" 4 2 "C"))))

;; Ky hieu cao do: tam giac dinh o (x, y), chu ghi phia tren
(defun sd:pic-lv (x y s c)
  (list (list "P" c t (list x y (- x 3) (+ y 5) (+ x 3) (+ y 5))) (list "L" (- x 3) (+ y 5) (+ x 26) (+ y 5) c)
        (list "T" (+ x 1) (+ y 9.5) s 4 2 "L")))

(defun sd:pic-fmtlv (v)
  (cond ((< (abs v) 0.0005) "0.000") ((> v 0) (strcat "+" (sd:rtos v 3))) (t (sd:rtos v 3))))

(defun sd:pic-caodo (v / v0 l)
  (setq v0 (sd:pnum v "v0" 0.0)
        l (list (list "L" 5 12 62 12 8) (list "L" 5 47 62 47 8) (sd:rectp 5 47 57 4 7) (sd:rectp 5 8 57 4 7)
                (list "L" 12 12 12 47 7) (list "L" 55 12 55 47 7) (list "L" 62 12 65 12 8) (list "L" 62 51 65 51 8)))
  (if (= (sd:pv v "mode") "Tay")
    (append l (sd:pic-lv 68 12 (sd:pic-fmtlv (sd:pnum v "vt" 0.0)) 4) (sd:pic-lv 68 51 "NHAP" 4)
            (list (list "T" 34 30 "NHAP TAY" 4 7 "C")))
    (append l (sd:pic-lv 68 12 (sd:pic-fmtlv v0) 3) (sd:pic-lv 68 51 (sd:pic-fmtlv (+ v0 3.6)) 4)
            (list (list "D" 30 12 1.8 1) (list "T" 30 4 "GOC" 3.5 1 "C") (list "V" 34 12 51 "3600" 4)
                  (list "T" 50 70 "CAO DO = GOC + DY" 3.5 7 "C")))))

;; Thep thong minh: dam, thanh thep polyline, mui ten co keo, ghi chu tu cap nhat
(defun sd:pic-theptm (v / op l x n)
  (setq op (sd:pv v "op"))
  (cond
    ((= op "Capnhat") (sd:pic-tkthep (list (cons "auto" t))))
    (t
     (setq l (list (sd:rectp 8 30 72 26 8) (list "L" 80 43 94 43 2) (list "P" 2 nil '(90 46 94 43 90 40))
                   (list "T" 87 50 "KEO" 3.5 2 "C")))
     (if (= (sd:pv v "nm") "Rai")
       (progn
         (setq x 14 n 0)
         (while (<= x 74) (setq l (cons (list "L" x 33 x 53 1) l) x (+ x 6) n (1+ n)))
         (setq l (append l (list (list "L" 14 26 74 26 3) (list "H" 14 20 60 (strcat "A" (sd:num (sd:pnum v "a" 200))) 4)
                                 (list "T" 62 21 "N = LR/A + 1" 3.5 3 "C")))))
       (setq l (append l (list (list "P" 1 nil '(12 52 12 34 76 34 76 52)) (list "P" 1 nil '(12 50 76 50))))))
     (append l (list (list "D" 40 (if (= (sd:pv v "nm") "Rai") 53 34) 1 7) (list "L" 40 (if (= (sd:pv v "nm") "Rai") 53 34) 34 12 7)
                     (list "C" 30 12 4 7) (list "T" 30 12 (cond ((= (type (sd:pv v "mk")) 'STR) (sd:pv v "mk")) ("1")) 4 7 "C")
                     (list "L" 34 12 80 12 7)
                     (list "T" 36 16 (strcat (if (= (sd:pv v "nm") "Rai") "N" (itoa (fix (sd:pnum v "n" 2))))
                                             "D" (sd:num (sd:pnum v "d" 16)) " L=TU DONG") 3.5 2 "L")
                     (list "T" 50 70 (if (= op "Bo") "BO LIEN KET" "POLYLINE = THANH THEP") 4 (if (= op "Bo") 1 7) "C"))))))

;; Bang thong ke: luoi bang + mui ten vong neu tu cap nhat
(defun sd:pic-tkthep (v / l)
  (setq l (list (sd:rectp 6 8 60 56 7) (list "L" 6 56 66 56 7) (list "T" 36 68 "THONG KE THEP" 3.5 7 "C")))
  (foreach y '(48 40 32 24 16) (setq l (cons (list "L" 6 y 66 y 8) l)))
  (foreach x '(14 34 42 54) (setq l (cons (list "L" x 8 x 64 8) l)))
  (setq l (append l (list (list "P" 2 nil '(17 51 17 53 31 53 31 51)) (list "P" 2 nil '(17 43 31 43)) (list "P" 2 nil '(17 37 17 34 31 34))
                          (list "T" 10 52 "1" 3 7 "C") (list "T" 10 44 "2" 3 7 "C") (list "T" 10 36 "3" 3 7 "C"))))
  (if (and (/= (sd:pv v "pv") "Chon") (sd:pv v "auto"))
    (append l (list (sd:pic-arc 83 36 10 30 330 3) (list "P" 3 nil '(90 30 91.7 31 94 28))
                    (list "T" 83 36 "TU" 3.5 3 "C") (list "T" 83 18 "CAP NHAT" 3 3 "C")))
    l))

;; Mat dung dam 2 nhip: cot, thep suot (moc / thang), thep mu goi, dai day vung goi
(defun sd:pic-damdung (v / moc l x top bot hk)
  (setq moc (/= (sd:pv v "neo") "Thang") hk (if moc 6 0)
        l (list (sd:rectp 6 12 6 46 7) (sd:rectp 47 12 6 46 7) (sd:rectp 88 12 6 46 7)
                (list "L" 12 26 47 26 7) (list "L" 12 44 47 44 7) (list "L" 53 26 88 26 7) (list "L" 53 44 88 44 7)
                (list "L" 9 8 9 62 1) (list "L" 50 8 50 62 1) (list "L" 91 8 91 62 1)
                (list "C" 9 66 3 7) (list "C" 50 66 3 7) (list "C" 91 66 3 7)))
  (foreach x '(14 16 18 20 22 34 39 44 45 55 56 61 66 72 78 80 82 84 86) (setq l (cons (list "L" x 28 x 42 3) l)))
  (setq l (append l (list (list "P" 1 nil (list 8 (- 41 hk) 8 41 92 41 92 (- 41 hk)))
                          (list "P" 1 nil (list 8 (+ 29 hk) 8 29 92 29 92 (+ 29 hk)))
                          (list "P" 30 nil (list 37 39 63 39)) (list "P" 30 nil (list 8 (- 39 hk) 8 39 22 39))
                          (list "P" 30 nil (list 78 39 92 39 92 (- 39 hk)))
                          (list "H" 53 61 50 (cond ((= (sd:pv v "lt") "1/4") "LN/4") ("LN/3")) 4)
                          (list "H" 12 22 4 "LN/4" 4)
                          (list "T" 17 20 (strcat "A" (sd:num (sd:pnum v "a1" 100))) 3 3 "C")
                          (list "T" 31 20 (strcat "A" (sd:num (sd:pnum v "a2" 200))) 3 3 "C"))))
  (if (sd:pv v "mc")
    (append l (list (list "T" 97 4 "+ MAT CAT" 3.5 7 "R")))
    l))

;; Mong: mat bang luoi thep + mat cat (moc, thep cho)
(defun sd:pic-mongthep (v / l x hk)
  (setq hk (if (sd:pv v "moc") 4 0)
        l (list (sd:rectp 4 18 36 30 7) (sd:rectp 17 28 10 10 7) (list "T" 22 54 "MAT BANG" 3 7 "C")
                (if (> (sd:pnum v "hv" 0) 0) (list "P" 7 t '(50 18 94 18 94 26 80 32 64 32 50 26)) (sd:rectp 50 18 44 14 7))
                (sd:rectp 48 15 48 3 8) (list "L" 66 32 66 64 7) (list "L" 78 32 78 64 7)
                (list "P" 1 nil (list 53 (+ 21 hk) 53 21 91 21 91 (+ 21 hk)))
                (list "P" 2 nil '(64 24 69 24 69 62)) (list "P" 2 nil '(80 24 75 24 75 62))
                (list "L" 66 29 78 29 3) (list "L" 66 26.5 78 26.5 3)
                (list "H" 50 94 10 "A" 4) (list "V" 96 18 32 "H" 4) (list "T" 72 68 "MAT CAT A-A" 3 7 "C")))
  (setq x 7)
  (while (< x 39) (setq l (cons (list "L" x 20 x 46 3) l) x (+ x 4)))
  (setq x 21)
  (while (< x 47) (setq l (cons (list "L" 6 x 38 x 1) l) x (+ x 4)))
  (setq x 55)
  (while (< x 91) (setq l (cons (list "D" x 23 0.8 3) l) x (+ x 4)))
  l)

;; Mong bang: mat cat chu T nguoc (ban vat + suon), thep ngang chu U, thep doc cham, dai suon
(defun sd:pic-mongbang (v / l x hk hv hs)
  (setq hk (if (> (sd:pnum v "hb" 300) 0) 4 0)
        hv (if (> (sd:pnum v "hv" 150) 0) 6 0) hs (if (> (sd:pnum v "hs" 900) 0) 58 (+ 24 hv))
        l (list (list "P" 7 t (list 8 14 92 14 92 24 60 (+ 24 hv) 60 hs 40 hs 40 (+ 24 hv) 8 24))
                (sd:rectp 4 10 92 4 8)
                (list "P" 1 nil (list 11 (+ 17 hk) 11 17 89 17 89 (+ 17 hk)))
                (list "H" 8 92 6 "B" 4) (list "V" 96 14 24 "HB" 4) (list "T" 50 70 "MAT CAT A-A" 3.5 7 "C")))
  (setq x 13)
  (while (< x 88) (setq l (cons (list "D" x 19.5 0.8 3) l) x (+ x 6)))
  (if (> (sd:pnum v "hs" 900) 0)
    (setq l (append l (list (sd:rectp 43 19 14 (- hs 22) 3) (list "D" 45.5 (- hs 5.5) 1 1) (list "D" 54.5 (- hs 5.5) 1 1)
                            (list "D" 45.5 21.5 1 1) (list "D" 54.5 21.5 1 1) (list "V" 30 14 hs "HS" 4 "L")))))
  l)

;; Dai coc: mat bang luoi coc + mat cat (coc ngam, luoi day tren dau coc, thep cho)
(defun sd:pic-daicoc (v / l nx ny i j x y hk)
  (setq nx (max 1 (min 4 (fix (sd:pnum v "nx" 2)))) ny (max 1 (min 4 (fix (sd:pnum v "ny" 2))))
        hk (if (= (sd:pv v "moc") "Het") 22 5)
        l (list (sd:rectp 4 22 36 36 7) (sd:rectp 18 36 8 8 7) (list "T" 22 64 "MAT BANG" 3 7 "C")
                (sd:rectp 52 26 40 26 7) (sd:rectp 50 23 44 3 8)
                (list "P" 1 nil (list 55 (+ 33 hk) 55 33 89 33 89 (+ 33 hk)))
                (list "L" 68 52 68 70 7) (list "L" 76 52 76 70 7)
                (list "P" 2 nil '(66 36 70 36 70 68)) (list "P" 2 nil '(78 36 74 36 74 68))
                (list "V" 96 26 52 "H" 4) (list "T" 72 72 "MAT CAT A-A" 3 7 "C")))
  (if (sd:pv v "trn") (setq l (cons (list "P" 1 nil '(55 49 89 49)) l)))
  (foreach x '(58 86)
    (setq l (append l (list (list "L" (- x 3) 30 (- x 3) 8 8) (list "L" (+ x 3) 30 (+ x 3) 8 8) (list "L" (- x 3) 30 (+ x 3) 30 8)))))
  (setq i 0)
  (repeat nx
    (setq j 0 x (if (= nx 1) 22 (+ 10 (* i (/ 24.0 (1- nx))))))
    (repeat ny
      (setq y (if (= ny 1) 40 (+ 28 (* j (/ 24.0 (1- ny))))))
      (setq l (cons (if (= (sd:pv v "hinh") "Tron") (list "C" x y 2.5 8) (sd:rectp (- x 2.5) (- y 2.5) 5 5 8)) l) j (1+ j)))
    (setq i (1+ i)))
  (setq x 56)
  (while (< x 89) (setq l (cons (list "D" x 35 0.8 3) l) x (+ x 4)))
  l)

;; Cot: mat dung (dai day vung toi han + nut), noi chong, mat cat
(defun sd:pic-cotthep (v / l y)
  (setq l (list (list "L" 30 4 30 50 7) (list "L" 44 4 44 50 7) (list "L" 18 50 56 50 7) (list "L" 18 60 56 60 7)
                (list "L" 30 60 30 72 7) (list "L" 44 60 44 72 7) (list "L" 18 8 30 8 7) (list "L" 44 8 56 8 7)
                (list "L" 33 8 33 (if (sd:pv v "noi") 70 58) 1) (list "L" 41 8 41 (if (sd:pv v "noi") 70 58) 1)
                (list "L" 34.5 2 34.5 16 2) (list "L" 39.5 2 39.5 16 2)
                (list "V" 58 8 18 "LZ" 4) (list "V" 58 40 50 "LZ" 4) (list "V" 22 8 60 "H" 4 "L")
                (sd:rectp 72 26 16 20 7) (sd:rectp 74 28 12 16 3)))
  (if (/= (sd:pv v "dp") "Khong")
    (setq l (cons (if (= (sd:pv v "lp") "Kin") (sd:rectp 74.8 34 10.4 4 6) (list "P" 6 nil '(76.5 34.5 75.5 36 84.5 36 83.5 37.5))) l)))
  (foreach y '(10 12 14 16 18 22 27 32 37 42 44 46 48 50 52 54 56 58)
    (setq l (cons (list "L" 31 y 43 y 3) l)))
  (foreach y '(30 36 42) (setq l (cons (list "D" 75.5 y 0.9 1) (cons (list "D" 84.5 y 0.9 1) l))))
  (append l (list (list "T" 80 20 (strcat (itoa (fix (sd:pnum v "nb" 3))) "X" (itoa (fix (sd:pnum v "nh" 3)))) 3 7 "C"))))

;; San: dam bao quanh, thep duoi 2 phuong, thep mu co chan theo tung canh
(defun sd:pic-santhep (v / l e)
  (setq l (list (sd:rectp 8 8 84 58 8) (sd:rectp 12 12 76 50 8)
                (list "L" 10 34 90 34 1) (list "L" 56 10 56 64 1)
                (list "L" 26 14 26 60 3) (list "L" 14 22 86 22 3)))
  (foreach e (list (list "eT" '(4 40 4 44 22 44 22 40)) (list "eP" '(78 40 78 44 96 44 96 40))
                   (list "eD" '(38 4 42 4 42 20 38 20)) (list "eN" '(38 54 42 54 42 70 38 70)))
    (if (/= (sd:pv v (car e)) "Khong") (setq l (cons (list "P" 30 nil (cadr e)) l))))
  (append l (list (list "T" 50 2 (strcat "MU " (cond ((sd:pv v "lt")) ("1/4"))) 3 30 "C"))))

;; Cau thang: mat cat bac + ban nghieng, thep chiu luc co de, thep mu 2 gay khuc
;; Bac thang so do: n bac tu (x, y), buoc dx / dy
(defun sd:pic-steps (x y n dx dy / l)
  (repeat n (setq l (cons (list "P" 7 nil (list x y x (+ y dy) (+ x dx) (+ y dy))) l) x (+ x dx) y (+ y dy)))
  l)
(defun sd:pic-thangthep (v / l i x y nv)
  (setq nv (cond ((sd:pv v "nv")) ("10")))
  (if (or (vl-string-search "," nv) (vl-string-search "*" nv))
    (if (= (sd:pv v "kieu") "Gap")
      (append (sd:pic-steps 12 16 5 5 4) (sd:pic-steps 62 30 5 5 4)
              (list (list "P" 7 nil '(4 16 12 16)) (list "P" 7 nil '(37 36 48 36)) (list "P" 7 nil '(54 30 62 30)) (list "P" 7 nil '(87 50 96 50))
                    (list "P" 1 nil '(5 12 14 12 36 31 47 31)) (list "P" 1 nil '(55 26 64 26 86 45 95 45))
                    (list "T" 26 44 "VE 1" 3 7 "C") (list "T" 76 58 "VE 2" 3 7 "C") (list "T" 50 68 "GAP CHU U" 3.5 7 "C")
                    (list "T" 50 22 "CN GIUA" 2.5 3 "C") (list "L" 44 28 54 26 3)))
      (append (sd:pic-steps 12 12 5 5 4) (sd:pic-steps 54 32 5 5 4)
              (list (list "P" 7 nil '(4 12 12 12)) (list "P" 7 nil '(37 32 54 32)) (list "P" 7 nil '(79 52 96 52))
                    (list "P" 1 nil '(5 8 14 8 36 27 56 27 78 47 95 47))
                    (list "H" 37 54 22 "LM" 4) (list "T" 50 68 "VE NOI TIEP" 3.5 7 "C"))))
    (sd:pic-thang1 v)))
(defun sd:pic-thang1 (v / l i x y)
  (setq l (list (list "P" 7 nil '(4 20 24 20)) (list "P" 7 nil '(4 14 26 14 64 46 96 46)) (list "P" 7 nil '(72 52 96 52))
                (list "P" 1 nil '(6 16 27 16 63 48 94 48)) (list "P" 30 nil '(12 18 26 18 34 25))
                (list "P" 30 nil '(58 42 66 49 82 49)) (list "T" 50 66 "BAN THANG" 3.5 7 "C")))
  (setq i 0 x 24 y 20)
  (repeat 8
    (setq l (cons (list "P" 7 nil (list x y x (+ y 4) (+ x 6) (+ y 4))) l) x (+ x 6) y (+ y 4) i (1+ i)))
  (foreach x '(32 40 48 56) (setq l (cons (list "D" x (+ 18 (* 0.84 (- x 27))) 0.8 3) l)))
  l)

;; Cau kien khac: khoi hop + kich thuoc / polyline
(defun sd:pic-ck (v)
  (if (= (sd:pv v "cach") "Polyline")
    (list (list "P" 7 t '(15 15 70 15 85 35 60 60 20 50)) (list "T" 48 36 "A X H" 5 2 "C")
          (list "T" 50 68 (cond ((sd:pv v "typ")) ("San")) 4 7 "C"))
    (list (sd:rectp 20 12 45 30 7) (list "P" 7 nil '(20 42 35 55 80 55 65 42)) (list "L" 80 55 80 25 7) (list "L" 80 25 65 12 7)
          (list "H" 20 65 6 "L1" 4) (list "V" 86 25 55 "H" 4) (list "T" 74 16 "L2" 4 4 "C")
          (list "T" 42 27 (cond ((sd:pv v "typ")) ("San")) 4 2 "C"))))

;; Xuat Excel: bang tinh 3 sheet
(defun sd:pic-kl (v / l)
  (setq l (list (sd:rectp 8 10 70 52 7) (sd:rectp 8 54 70 8 5) (list "T" 43 66 "KHOI LUONG" 3.5 7 "C")))
  (foreach y '(46 38 30 22) (setq l (cons (list "L" 8 y 78 y 8) l)))
  (foreach x '(20 34 48 62) (setq l (cons (list "L" x 10 x 62 8) l)))
  (append l (list (list "T" 14 58 "CK" 3 7 "C") (list "T" 27 58 "BT" 3 7 "C") (list "T" 41 58 "VK" 3 7 "C")
                  (list "T" 55 58 "THEP" 3 7 "C") (sd:rectp 8 3 18 6 3) (list "T" 17 6 "TONGHOP" 2.5 3 "C")
                  (sd:rectp 28 3 14 6 8) (sd:rectp 44 3 14 6 8)
                  (list "T" 90 36 (if (sd:pv v "xl") "XLSX" "XML") 5 3 "C"))))

;; Don rac: thung rac + cac loai rac duoc don
(defun sd:pic-purge (v / l y)
  (setq l (list (list "P" 7 t '(30 12 70 12 74 52 26 52)) (list "L" 22 56 78 56 7) (list "P" 7 nil '(42 56 42 61 58 61 58 56))
                (list "L" 40 18 38 46 8) (list "L" 50 18 50 46 8) (list "L" 60 18 62 46 8)
                (list "T" 50 68 "PURGE SAU" 3.5 7 "C")))
  (setq y 46)
  (foreach x (list (if (sd:pv v "dgn") "DGN" "") "REGAPP" "BLOCK" (if (sd:pv v "zero") "L=0" "") (if (sd:pv v "scale") "SCALE" ""))
    (if (/= x "") (setq l (cons (list "T" 90 y x 2.8 1 "R") l) y (- y 8))))
  l)

;; So sanh: ban cu / ban moi, khung xanh (them), do (xoa), mui ten (dich chuyen)
(defun sd:pic-sosanh (v)
  (if (= (sd:pv v "op") "Xoa")
    (list (sd:rectp 30 18 40 36 8) (list "L" 30 18 70 54 1) (list "L" 30 54 70 18 1) (list "T" 50 64 "XOA KET QUA" 3.5 7 "C"))
    (list (sd:rectp 4 14 42 44 7) (sd:rectp 54 14 42 44 7) (list "T" 25 64 "BAN CU" 3 7 "C") (list "T" 75 64 "BAN MOI" 3 7 "C")
          (sd:rectp 10 40 10 10 8) (sd:rectp 28 22 12 8 8) (list "C" 15 26 4 8)
          (sd:rectp 60 40 10 10 7) (list "C" 81 34 4 7) (sd:rectp 78 46 12 6 7)
          (sd:rectp 76 30 10 8 5) (list "L" 65 26 81 34 5) (sd:rectp 76 44 16 10 3) (sd:rectp 9 20 12 12 1)
          (list "T" 50 6 "XANH: THEM  DO: XOA  LAM: DICH" 2.6 7 "C"))))

;; In hang loat: cac khung ten xep hang, so thu tu in + may in
(defun sd:pic-in (v / l r c x y)
  (setq r 0)
  (repeat 2
    (setq c 0 y (if (= r 0) 46 26))
    (repeat 3
      (setq x (+ 6 (* c 26))
            l (append l (list (sd:rectp x y 22 15 7) (sd:rectp (+ x 14) y 8 4 8)
                              (list "T" (+ x 7) (+ y 8) (itoa (if (= (sd:pv v "order") "Cot") (+ (* c 2) r 1) (+ (* r 3) c 1))) 3.5 3 "C")))
            c (1+ c)))
    (setq r (1+ r)))
  (append l (list (sd:rectp 84 30 14 12 7) (sd:rectp 86 42 10 5 8) (sd:rectp 86 22 10 8 7)
                  (list "T" 50 70 (if (= (sd:pv v "order") "Cot") "THU TU: COT" "THU TU: HANG") 3.5 7 "C")
                  (list "T" 91 14 (if (sd:pv v "file") "PDF" "IN") 3 3 "C"))))

;; Cat noi thep: dam 2 nhip, vung noi (xanh), 2 nhom thanh so le
(defun sd:pic-noithep (v / l tren cot)
  (setq tren (/= (sd:pv v "loai") "Duoi") cot (= (sd:pv v "loai") "Cot"))
  (setq l (list (list "L" 4 36 96 36 8) (sd:rectp 6 34 4 4 7) (sd:rectp 48 34 4 4 7) (sd:rectp 90 34 4 4 7)
                (list "T" 50 70 (cond (cot "COT: NUA GIUA HN") (tren "TREN: 1/3 GIUA NHIP") ("DUOI: GAN GOI")) 3.2 7 "C")))
  (foreach z (if tren '((22 36) (64 78)) '((2 16) (40 60) (84 98)))
    (setq l (cons (sd:rectp (car z) 33 (- (cadr z) (car z)) 6 3) l)))
  (setq l (append l (if tren
                      (list (list "L" 4 46 32 46 2) (list "L" 26 48 96 48 2) (list "L" 4 26 70 26 2) (list "L" 64 24 96 24 2)
                            (list "T" 4 52 "A" 3 7 "L") (list "T" 4 18 "B" 3 7 "L"))
                      (list (list "L" 4 46 58 46 2) (list "L" 42 48 96 48 2) (list "L" 4 26 14 26 2) (list "L" 6 24 96 24 2)
                            (list "T" 4 52 "A" 3 7 "L") (list "T" 4 18 "B" 3 7 "L")))))
  (append l (list (list "T" 50 8 (if (= (sd:pv v "noi") "Coupler") "COUPLER, SO LE A/B" "NOI CHONG SO LE A/B") 2.8 3 "C"))))

;; Danh so thep: cac bong so + bang
(defun sd:pic-bongthep (v / l)
  (setq l (list (list "T" 50 70 (if (= (sd:pv v "op") "Kiemtra") "KIEM TRA TRUNG / LECH" "DANH SO DONG BO") 3.2 7 "C")
                (list "L" 6 50 50 50 2) (list "L" 6 38 50 38 2) (list "L" 6 26 50 26 2)
                (list "C" 56 50 4 6) (list "C" 56 38 4 6) (list "C" 56 26 4 6)
                (list "T" 56 50 "1" 3 7 "C") (list "T" 56 38 (if (= (sd:pv v "pv") "Caukien") "1" "2") 3 7 "C") (list "T" 56 26 "1" 3 7 "C")
                (sd:rectp 70 14 28 44 7) (list "L" 70 46 98 46 8) (list "L" 70 34 98 34 8) (list "L" 70 22 98 22 8)
                (list "T" 84 52 "BANG" 2.6 7 "C") (list "T" 50 8 "CUNG QUY CACH = CUNG SO HIEU" 2.6 3 "C")))
  l)
;; Tao layout: khung trong Model -> cac layout
(defun sd:pic-taolayout (v)
  (list (sd:rectp 4 30 26 18 7) (sd:rectp 4 8 26 18 7) (list "T" 17 52 "MODEL" 3 7 "C")
        (list "L" 34 39 46 39 3) (list "L" 34 17 46 17 3)
        (sd:rectp 50 30 22 16 7) (sd:rectp 52 32 18 12 5) (sd:rectp 76 30 22 16 7) (sd:rectp 78 32 18 12 5)
        (list "T" 61 50 "BV-01" 2.6 3 "C") (list "T" 87 50 "BV-02" 2.6 3 "C")
        (list "T" 74 18 (if (= (sd:pv v "lam") "Layout") "" "SO TO 01/12") 3 1 "C")
        (list "T" 50 70 "TAO LAYOUT + SO TO" 3.2 7 "C")))
;; Nhan lien ket: polyline + nhan FIELD
(defun sd:pic-nhanlk (v)
  (list (list "P" 7 (= (sd:pv v "kind") "Dientich") '(12 16 70 16 88 40 30 52))
        (list "T" 42 22 (if (= (sd:pv v "kind") "Dientich") "S = 12.50 M2" "L = 6.25 m") 3.2 3 "C")
        (list "T" 50 66 "FIELD TU CAP NHAT" 3.2 7 "C")))
;; Kiem tra MB <-> khai trien
(defun sd:pic-lienket (v)
  (list (sd:rectp 4 12 44 46 7) (list "T" 26 62 "MAT BANG" 3 7 "C")
        (list "T" 14 46 "D1" 3 7 "C") (list "T" 36 46 "D2" 3 7 "C") (list "T" 14 24 "C1" 3 7 "C") (list "C" 36 24 5 1) (list "T" 36 24 "C2" 3 1 "C")
        (sd:rectp 56 12 40 46 7) (list "T" 76 62 "KHAI TRIEN" 3 7 "C")
        (list "T" 76 46 "D1  D2" 3 7 "C") (list "T" 76 24 "C1" 3 7 "C")
        (list "T" 50 4 "DO = CHUA KHAI TRIEN / THUA" 2.6 1 "C")))

;; CDE: 4 thu muc trang thai WIP -> SHARED -> PUBLISHED -> ARCHIVED
(defun sd:pic-cde (v / st)
  (setq st (cond ((sd:pv v "st")) ("S2")))
  (list (sd:rectp 4 30 20 16 (if (= st "S0") 1 7)) (sd:rectp 28 30 20 16 (if (wcmatch st "S[1-4]") 1 7))
        (sd:rectp 52 30 20 16 (if (wcmatch st "A*,CR") 1 7)) (sd:rectp 76 30 20 16 8)
        (list "T" 14 38 "WIP" 2.8 7 "C") (list "T" 38 38 "SHARED" 2.4 7 "C") (list "T" 62 38 "PUBL" 2.6 7 "C") (list "T" 86 38 "ARCH" 2.6 8 "C")
        (list "L" 24 38 28 38 3) (list "L" 48 38 52 38 3) (list "L" 72 38 76 38 3)
        (list "T" 50 58 "ISO 19650 CDE" 3.5 7 "C") (list "T" 50 18 (strcat "DA-ORG-ZZ-ZZ-DR-S-0001 " st) 2.4 3 "C")))

;; Chuan ban ve: layer + file mau
(defun sd:pic-chuan (v)
  (list (sd:rectp 6 14 40 44 7) (list "L" 10 48 20 48 1) (list "L" 10 40 20 40 2) (list "L" 10 32 20 32 3) (list "L" 10 24 20 24 4)
        (list "T" 24 48 "SD-TRUC" 2.4 7 "L") (list "T" 24 40 "SD-THEP" 2.4 7 "L") (list "T" 24 32 "SD-DAI" 2.4 7 "L") (list "T" 24 24 "SD-DIM" 2.4 7 "L")
        (list "L" 50 36 60 36 3) (sd:rectp 64 22 30 28 (if (= (sd:pv v "op") "Xuatdwt") 1 7)) (list "T" 79 36 "DWT" 4 7 "C")
        (list "T" 50 66 "CHUAN BAN VE" 3.5 7 "C")))
;; Block dong + thuoc tinh -> bang
(defun sd:pic-tkblock (v)
  (list (sd:rectp 6 36 18 14 7) (list "C" 15 43 4 2) (sd:rectp 6 14 26 14 7) (list "C" 19 21 4 2)
        (list "T" 15 54 "V1" 2.6 3 "C") (list "T" 19 32 "V2" 2.6 3 "C") (list "L" 40 32 50 32 3)
        (sd:rectp 54 12 42 42 7) (list "L" 54 44 96 44 8) (list "L" 54 34 96 34 8) (list "L" 54 24 96 24 8) (list "L" 86 12 86 54 8)
        (list "T" 75 49 "THONG KE" 2.6 7 "C") (list "T" 50 66 (if (= (sd:pv v "op") "Gan") "GAN GIA TRI" "BLOCK + THUOC TINH") 3.2 7 "C")))
;; Xref: ban ve chinh + 2 xref
(defun sd:pic-xref (v)
  (list (sd:rectp 34 20 32 30 7) (list "T" 50 35 "DWG" 4 7 "C") (sd:rectp 4 40 22 16 5) (list "T" 15 48 "KT" 3 5 "C")
        (sd:rectp 74 40 22 16 1) (list "T" 85 48 "?" 4 1 "C") (list "L" 26 46 34 40 5) (list "L" 74 46 66 40 1)
        (list "T" 50 8 (if (sd:pv v "rel") "..\\XREF\\A.DWG" "XREF") 2.6 3 "C") (list "T" 50 66 "QUAN LY XREF" 3.5 7 "C")))
;; Danh muc ban ve
(defun sd:pic-dmbv (v / l)
  (setq l (list (sd:rectp 14 8 72 50 7) (list "L" 14 50 86 50 7) (list "L" 24 8 24 58 8) (list "L" 46 8 46 58 8) (list "L" 76 8 76 58 8)
                (list "T" 50 66 "DANH MUC BAN VE" 3.5 7 "C") (list "T" 19 54 "TT" 2.4 7 "C") (list "T" 35 54 "SO" 2.4 7 "C") (list "T" 61 54 "TEN" 2.4 7 "C")))
  (foreach y '(44 36 28 20) (setq l (cons (list "L" 14 (- y 2) 86 (- y 2) 8) l)))
  l)

;; Loc: pheu loc + bieu thuc
(defun sd:pic-loc (v)
  (list (list "P" 7 t '(14 56 86 56 58 30 58 12 42 6 42 30)) (list "C" 24 62 3 2) (list "C" 40 64 3 3) (list "C" 60 63 3 1) (list "C" 76 62 3 2)
        (list "C" 50 4 3 2) (list "T" 50 44 "VA & HOAC |" 2.6 7 "C") (list "T" 50 70 "LOC DOI TUONG" 3.5 7 "C")))

;; Tong dien tich
(defun sd:pic-dientich (v)
  (list (list "P" 7 t '(10 14 46 14 46 50 10 50)) (list "C" 66 32 16 7) (list "T" 28 32 "S1" 3.5 3 "C") (list "T" 66 32 "S2" 3.5 3 "C")
        (list "T" 50 66 "TONG DIEN TICH" 3.5 7 "C") (list "T" 50 6 "S = S1 + S2" 3 2 "C")))
;; Chu giua 2 diem
(defun sd:pic-chugiua (v)
  (list (list "L" 12 16 88 52 8) (list "C" 12 16 1.5 2) (list "C" 88 52 1.5 2) (list "C" 50 34 1.5 1)
        (list "T" 50 (if (= (sd:pv v "vt") "Giua") 34 44) "TEXT" 4 7 "C") (list "T" 50 66 "CHU GIUA 2 DIEM" 3.5 7 "C")))
;; Kich thuoc ghi tay
(defun sd:pic-dimtay (v)
  (list (list "L" 14 20 14 46 7) (list "L" 86 20 86 46 7) (list "L" 14 40 86 40 1) (list "T" 50 46 "1200" 3.5 1 "C")
        (list "T" 50 30 "DO THAT 1185" 2.8 8 "C") (list "T" 50 66 "KICH THUOC GHI TAY" 3.5 7 "C")))
;; Thu tu ve theo layer
(defun sd:pic-thutu (v)
  (list (list "P" 8 t '(20 14 60 14 74 26 34 26)) (list "P" 2 t '(24 26 64 26 78 38 38 38)) (list "P" 7 t '(28 38 68 38 82 50 42 50))
        (list "T" 88 20 "HATCH" 2.6 8 "L") (list "T" 88 32 "THEP" 2.6 2 "L") (list "T" 88 44 "CHU" 2.6 7 "L")
        (list "T" 50 66 "THU TU VE" 3.5 7 "C")))
;; Quan ly layout
(defun sd:pic-layout (v / l)
  (setq l (list (sd:rectp 10 8 50 52 7) (list "T" 50 66 "QUAN LY LAYOUT" 3.5 7 "C")))
  (foreach y '(52 44 36 28 20) (setq l (cons (list "L" 14 y 56 y 8) l)))
  (append l (list (sd:rectp 66 46 26 8 3) (sd:rectp 66 34 26 8 7) (sd:rectp 66 22 26 8 7) (sd:rectp 66 10 26 8 1))))

;; Coffa nhom: luoi tam + ma
(defun sd:pic-nhom (v / l)
  (setq l (list (sd:rectp 10 10 80 48 7) (list "T" 50 66 "COFFA NHOM" 3.5 7 "C")))
  (foreach x '(26 42 58 74) (setq l (cons (list "L" x 10 x 58 3) l)))
  (setq l (cons (list "L" 10 34 90 34 3) l))
  (foreach x '(26 42 58 74) (setq l (cons (list "C" x 22 1.5 1) (cons (list "C" x 46 1.5 1) l))))
  (append l (list (list "T" 18 46 "W600" 2.4 7 "C") (list "T" 50 4 "IC / EC / SC / D / MB / PH" 2.4 2 "C"))))

(defun sd:pic-raitam (v / l x y)
  (setq l (list (sd:rectp 10 10 80 48 7) (list "T" 50 66 "RAI TAM" 3.5 7 "C")))
  (foreach x '(10 28 46 64)
    (foreach y '(10 34) (setq l (cons (sd:rectp x y 18 24 3) l))))
  (setq l (cons (sd:rectp 82 10 8 24 4) (cons (sd:rectp 82 34 8 24 30) (cons (list "L" 82 34 90 58 1) (cons (list "L" 82 58 90 34 1) l)))))
  (append l (list (list "T" 50 4 "TAM LON / TAM BU / GO" 2.4 2 "C"))))

(defun sd:pic-kiemtra (v / l)
  (setq l (list (sd:rectp 10 10 80 48 7) (list "T" 50 66 "KIEM TRA" 3.5 7 "C")))
  (foreach y '(48 38 28 18)
    (setq l (cons (list "L" 18 y 32 y 3) (cons (list "L" 36 y 82 y 7) l))))
  (setq l (cons (list "L" 18 48 22 44 1) (cons (list "L" 22 44 28 52 1) l)))
  (append l (list (list "T" 50 4 "CAO / TB / THAP + GOI Y LENH" 2.4 2 "C"))))

;; Hinh theo ma lenh trong tieu de hop thoai
(setq *SD:PICS*
  (list (cons "SDDAM" 'sd:pic-dam) (cons "SDCOT" 'sd:pic-cot) (cons "SDBANMA" 'sd:pic-banma) (cons "SDIH" 'sd:pic-ih)
        (cons "SDTHEP" 'sd:pic-thep) (cons "SDTHEPSET" 'sd:pic-thepset) (cons "SDTOIUU" 'sd:pic-toiuu)
        (cons "SDGACH" 'sd:pic-gach) (cons "SDCHANTUONG" 'sd:pic-len) (cons "SDLOP" 'sd:pic-lop)
        (cons "SDDATHO" 'sd:pic-datho) (cons "SDGIACONG" 'sd:pic-giacong)
        (cons "SDKHUNG" 'sd:pic-khung) (cons "SDTRUC" 'sd:pic-truc) (cons "SDMC" 'sd:pic-mc)
        (cons "SDCOFFASET" 'sd:pic-cfset) (cons "SDCOFFACOT" 'sd:pic-cfcot) (cons "SDCOFFAVACH" 'sd:pic-cfvach)
        (cons "SDCOFFATM" 'sd:pic-cftm) (cons "SDCOFFAMONG" 'sd:pic-cfmong) (cons "SDCOFFATHANG" 'sd:pic-cfthang)
        (cons "SDCOFFADAM" 'sd:pic-cfdam) (cons "SDCOFFASAN" 'sd:pic-giao) (cons "SDGIAOTANG" 'sd:pic-giao) (cons "SDGIAOH" 'sd:pic-giao)
        (cons "SDGIAOSET" 'sd:pic-giao) (cons "SDSET" 'sd:pic-set) (cons "SDGACHTK" 'sd:pic-gachtk)
        (cons "SDKHODA" 'sd:pic-khoda) (cons "SDGIAOTK" 'sd:pic-giaotk) (cons "SDSO" 'sd:pic-so) (cons "SDREV" 'sd:pic-rev)
        (cons "SDCAODO" 'sd:pic-caodo) (cons "SDTHEPTM" 'sd:pic-theptm) (cons "SDTKTHEP" 'sd:pic-tkthep)
        (cons "SDDAMDUNG" 'sd:pic-damdung) (cons "SDMONGTHEP" 'sd:pic-mongthep) (cons "SDMONGBANG" 'sd:pic-mongbang) (cons "SDDAICOC" 'sd:pic-daicoc) (cons "SDCOTTHEP" 'sd:pic-cotthep)
        (cons "SDSANTHEP" 'sd:pic-santhep) (cons "SDTHANGTHEP" 'sd:pic-thangthep) (cons "SDCK" 'sd:pic-ck) (cons "SDKL" 'sd:pic-kl)
        (cons "SDNOITHEP" 'sd:pic-noithep) (cons "SDIN" 'sd:pic-in) (cons "SDPURGE" 'sd:pic-purge) (cons "SDSOSANH" 'sd:pic-sosanh)
        (cons "SDBONGTHEP" 'sd:pic-bongthep) (cons "SDTAOLAYOUT" 'sd:pic-taolayout) (cons "SDNHANLK" 'sd:pic-nhanlk) (cons "SDLIENKET" 'sd:pic-lienket) (cons "SDCDE" 'sd:pic-cde)
        (cons "SDCHUAN" 'sd:pic-chuan) (cons "SDTKBLOCK" 'sd:pic-tkblock) (cons "SDXREF" 'sd:pic-xref) (cons "SDDMBV" 'sd:pic-dmbv) (cons "SDLOC" 'sd:pic-loc)
        (cons "SDDIENTICH" 'sd:pic-dientich) (cons "SDCHUGIUA" 'sd:pic-chugiua) (cons "SDDIMTAY" 'sd:pic-dimtay) (cons "SDTHUTU" 'sd:pic-thutu) (cons "SDLAYOUT" 'sd:pic-layout)
        (cons "SDRAITAM" 'sd:pic-raitam) (cons "SDVANDA" 'sd:pic-raitam) (cons "SDANHDA" 'sd:pic-raitam) (cons "SDTKDA" 'sd:pic-gachtk) (cons "SDKIEMTRA" 'sd:pic-kiemtra) (cons "SDNHOMSET" 'sd:pic-nhom) (cons "SDNHOMVACH" 'sd:pic-nhom) (cons "SDNHOMSAN" 'sd:pic-nhom) (cons "SDNHOMDAM" 'sd:pic-nhom) (cons "SDNHOMKHO" 'sd:pic-nhom)))

(defun sd:pic-for (title / p)
  (if (and (setq p (vl-string-position (ascii "(") title nil t)) (wcmatch title "*)"))
    (cdr (assoc (substr title (+ p 2) (- (strlen title) p 2)) *SD:PICS*))))

;; Tach chuoi
(defun sd:split (s d / p r)
  (while (setq p (vl-string-search d s))
    (setq r (cons (substr s 1 p) r)
          s (substr s (+ p 1 (strlen d)))))
  (reverse (cons s r)))
(defun sd:join (lst d / r)
  (setq r (car lst))
  (foreach s (cdr lst) (setq r (strcat r d s)))
  r)

;; "3*6000,4500 4500" -> (6000 6000 6000 4500 4500)
(defun sd:parse-spacing (s / res pos n v)
  (setq s (vl-string-translate " ;" ",," (strcase s t)))
  (foreach tok (sd:split s ",")
    (if (/= tok "")
      (if (setq pos (cond ((vl-string-search "*" tok)) ((vl-string-search "x" tok))))
        (progn
          (setq n (atoi (substr tok 1 pos))
                v (atof (substr tok (+ pos 2))))
          (repeat (max n 0) (setq res (cons v res))))
        (setq res (cons (atof tok) res)))))
  (vl-remove-if '(lambda (x) (<= x 0.0)) (reverse res)))

;; Cong don: (a b c) -> (0 a a+b a+b+c)
(defun sd:cumul (lst / s r)
  (setq s 0.0 r (list 0.0))
  (foreach d lst (setq s (+ s d) r (cons s r)))
  (reverse r))

;; "3d20" / "3D20" / "3-20" / "3%%c20" -> (3 20.0)
(defun sd:parse-bar (s / i n d)
  (setq s (strcase s) i 1)
  (while (and (<= i (strlen s)) (wcmatch (substr s i 1) "#")) (setq i (1+ i)))
  (setq n (atoi (substr s 1 (1- i))))
  (while (and (<= i (strlen s)) (not (wcmatch (substr s i 1) "#"))) (setq i (1+ i)))
  (setq d (atof (substr s i)))
  (if (and (> n 0) (> d 0.0)) (list n d)))

(defun sd:getbar (msg def / r)
  (while (not (setq r (sd:parse-bar (sd:getstr msg def))))
    (princ "\nSai dinh dang. Vi du: 3d20"))
  r)

;; Chieu dai doi tuong cong (line, pline, arc, circle, spline...)
(defun sd:len (e / r)
  (setq r (vl-catch-all-apply
            '(lambda (x) (vlax-curve-getDistAtParam x (vlax-curve-getEndParam x)))
            (list e)))
  (if (numberp r) r 0.0))

(defun sd:today () (menucmd "M=$(edtime,$(getvar,date),DD/MO/YYYY)"))

;;; --------------------------------------------------------------------------
;;;  Layer, text style, dimstyle
;;; --------------------------------------------------------------------------
(defun sd:ltype (lt)
  (if (not (tblsearch "LTYPE" lt))
    (vl-catch-all-apply 'vla-Load
      (list (vla-get-Linetypes (sd:doc)) lt
            (if (= (getvar "MEASUREMENT") 1) "acadiso.lin" "acad.lin"))))
  (if (tblsearch "LTYPE" lt) lt "Continuous"))

(defun sd:make-layer (name col lt lw)
  (if (not (tblsearch "LAYER" name))
    (entmake (list '(0 . "LAYER") '(100 . "AcDbSymbolTableRecord")
                   '(100 . "AcDbLayerTableRecord") (cons 2 name) '(70 . 0)
                   (cons 62 col) (cons 6 (sd:ltype lt)) (cons 370 lw))))
  name)

(defun sd:tstyle ()
  (if (not (tblsearch "STYLE" "SD-TEXT"))
    (entmake '((0 . "STYLE") (100 . "AcDbSymbolTableRecord")
               (100 . "AcDbTextStyleTableRecord") (2 . "SD-TEXT") (70 . 0)
               (40 . 0.0) (41 . 1.0) (50 . 0.0) (71 . 0) (42 . 2.5)
               (3 . "arial.ttf") (4 . ""))))
  (if (tblsearch "STYLE" "SD-TEXT") "SD-TEXT" "Standard"))

(defun sd:ensure ()
  (foreach l *SD:LAYERS* (apply 'sd:make-layer l))
  (sd:tstyle)
  (regapp "SD_REBAR")
  (regapp "SD_KL")
  (regapp "SD_CK")
  (regapp "SD_VK")
  (regapp "SD_SAN")
  (regapp "SD_NOI")
  (regapp "SD_TILE")
  (regapp "SD_ANH")
  (regapp "SD_MAVIEN")
  t)

;; Tao / kich hoat dimstyle "SD-1-<ty le>"
(defun sd:use-dimstyle (sc / name)
  (setq sc (fix sc) name (strcat "SD-1-" (itoa sc)))
  (if (tblsearch "DIMSTYLE" name)
    (if (/= (strcase (getvar "DIMSTYLE")) (strcase name))
      (command "_.-DIMSTYLE" "_R" name))
    (progn
      (foreach p (list (cons "DIMSCALE" (float sc))
                       '("DIMTXT" . 2.5) '("DIMASZ" . 1.2) '("DIMEXO" . 1.5)
                       '("DIMEXE" . 1.5) '("DIMDLE" . 1.0) '("DIMGAP" . 0.8)
                       '("DIMCEN" . 0.0)
                       '("DIMTAD" . 1) '("DIMJUST" . 0) '("DIMTIH" . 0)
                       '("DIMTOH" . 0) '("DIMDEC" . 0) '("DIMLUNIT" . 2)
                       '("DIMZIN" . 8) '("DIMATFIT" . 3) '("DIMTMOVE" . 2))
        (setvar (car p) (cdr p)))
      (setvar "DIMTXSTY" (sd:tstyle))
      (setvar "DIMBLK" "_ARCHTICK")
      (command "_.-DIMSTYLE" "_S" name)))
  name)

;;; --------------------------------------------------------------------------
;;;  Tao doi tuong (entmake, toa do WCS)
;;; --------------------------------------------------------------------------
(defun sd:line (p1 p2 lay)
  (entmake (list '(0 . "LINE") (cons 8 lay) (cons 10 p1) (cons 11 p2))))

(defun sd:circle (c r lay)
  (entmake (list '(0 . "CIRCLE") (cons 8 lay) (cons 10 c) (cons 40 r))))

(defun sd:clean-pts (pts closed / r p)
  ;; bo diem hong (nil / khong phai so), diem trung lien tiep va diem dong trung diem dau
  (foreach p pts
    (if (and (listp p) (numberp (car p)) (numberp (cadr p))
             (not (and r (< (distance (list (car p) (cadr p) 0.0) (list (car (car r)) (cadr (car r)) 0.0)) 1e-6))))
      (setq r (cons (list (car p) (cadr p)) r))))
  (setq r (reverse r))
  (if (and closed (cdr r) (< (distance (list (car (car r)) (cadr (car r)) 0.0) (list (car (last r)) (cadr (last r)) 0.0)) 1e-6))
    (setq r (reverse (cdr (reverse r)))))
  r)

(defun sd:plinew (pts closed w lay / q)
  (setq q (sd:clean-pts pts closed))
  (cond
    ((< (length q) (if closed 3 2))
     (princ "\n[SD] Bo qua polyline suy bien (it hon 2-3 dinh sau khi loai diem trung).") nil)
    ((entmake (append (list '(0 . "LWPOLYLINE") '(100 . "AcDbEntity") (cons 8 lay)
                            '(100 . "AcDbPolyline") (cons 90 (length q))
                            (cons 70 (if closed 1 0)) (cons 43 w))
                      (mapcar '(lambda (p) (list 10 (car p) (cadr p))) q))))
    (t (princ "\n[SD] Khong tao duoc polyline (entmake loi).") nil)))
;; Polyline vien/tam kem du lieu mo rong xd; tra nil neu hinh suy bien
(defun sd:mk-tile-poly (lay cs xd / q)
  (setq q (sd:clean-pts cs t))
  (if (>= (length q) 3)
    (entmake (append (list '(0 . "LWPOLYLINE") '(100 . "AcDbEntity") (cons 8 lay)
                           '(100 . "AcDbPolyline") (cons 90 (length q)) '(70 . 1))
                     (mapcar '(lambda (p) (list 10 (car p) (cadr p))) q)
                     (list xd)))
    (progn (princ "\n[SD] Bo qua vien suy bien (dien tich bang 0).") nil)))
(defun sd:pline (pts closed lay) (sd:plinew pts closed 0.0 lay))

(defun sd:rect (o w h lay)
  (sd:pline (list o (sd:p+ o w 0) (sd:p+ o w h) (sd:p+ o 0 h)) t lay))

;; Cham tron dac (thanh thep) duong kinh d
(defun sd:dot (c d lay / r)
  (setq r (/ d 4.0))
  (entmake (list '(0 . "LWPOLYLINE") '(100 . "AcDbEntity") (cons 8 lay)
                 '(100 . "AcDbPolyline") '(90 . 2) '(70 . 1) (cons 43 (/ d 2.0))
                 (list 10 (- (car c) r) (cadr c)) '(42 . 1.0)
                 (list 10 (+ (car c) r) (cadr c)) '(42 . 1.0))))

(defun sd:solid3 (a b c lay)
  (entmake (list '(0 . "SOLID") (cons 8 lay) (cons 10 a) (cons 11 b)
                 (cons 12 c) (cons 13 c))))

;; Text: j = L C R ML MC MR TL TC TR
(defun sd:text (pt str h j lay / h72 v73)
  (setq h72 (cond ((wcmatch j "*C") 1) ((wcmatch j "*R") 2) (t 0))
        v73 (cond ((wcmatch j "M?") 2) ((wcmatch j "T?") 3) (t 0)))
  (entmake (list '(0 . "TEXT") (cons 8 lay) (cons 7 (sd:tstyle)) (cons 10 pt)
                 (cons 11 pt) (cons 40 h) (cons 1 str) (cons 72 h72) (cons 73 v73))))

;; Kich thuoc thang: dir "H" ngang / "V" dung; pd = vi tri duong kich thuoc
(defun sd:dim (p1 p2 dir pd / os cl df dx dm)
  (if (> (abs (if (= dir "V") (- (cadr p2) (cadr p1)) (- (car p2) (car p1)))) 1e-6)
    (progn
      (setq os (getvar "OSMODE") cl (getvar "CLAYER") df (getvar "DIMATFIT") dx (getvar "DIMTIX") dm (getvar "DIMTMOVE"))
      (setvar "OSMODE" 0)
      (setvar "CLAYER" "SD-KICHTHUOC")
      (sd:dimchu-apply)   ;; quy tac dim ron: chu canh duong dim (tuy chon chu dim, goc/DGD)
      (command "_.DIMLINEAR" (trans p1 0 1) (trans p2 0 1)
               (if (= dir "V") "_V" "_H") (trans pd 0 1))
      (setvar "DIMATFIT" df) (setvar "DIMTIX" dx) (setvar "DIMTMOVE" dm)
      (setvar "CLAYER" cl)
      (setvar "OSMODE" os))))

(defun sd:dimchain (pts dir pd)
  (while (cadr pts)
    (sd:dim (car pts) (cadr pts) dir pd)
    (setq pts (cdr pts))))

;; Ghi chu dang duong dan sang trai: p (diem tren doi tuong) -> q (goi) -> duoi ngang
(defun sd:tagL (p q txt ts / tl)
  (setq tl (* ts (max 12.0 (* 1.8 (strlen txt)))))
  (sd:line p q "SD-KYHIEU")
  (sd:line q (sd:p+ q (- tl) 0.0) "SD-KYHIEU")
  (sd:text (sd:p+ q (- tl) (* 0.8 ts)) txt (* 2.5 ts) "L" "SD-CHU"))

;;; --------------------------------------------------------------------------
;;;  SDSET - Thiet lap ty le, layer, text style, dimstyle
;;; --------------------------------------------------------------------------
(defun c:SDSET (/ sc)
  (sd:begin)
  (if (not (sd:dlg "Thiet lap ban ve (SDSET)"
                   (list (list "sc" "Ty le ban ve chinh 1/" 'int *SD:SCALE*)
                         (list "ds" "Ty le chi tiet (mat cat, ban ma...) 1/" 'int *SD:DETSCALE*))))
    (exit))
  (setq sc (sd:v "sc"))
  (setq *SD:SCALE* sc)
  (setq *SD:DETSCALE* (sd:v "ds"))
  (vlax-ldata-put "SD" "SCALE" *SD:SCALE*)
  (vlax-ldata-put "SD" "DETSCALE" *SD:DETSCALE*)
  (sd:use-dimstyle *SD:DETSCALE*)
  (sd:use-dimstyle sc)
  (setvar "LTSCALE" (* sc 0.25))
  (princ (strcat "\n[SD] Da thiet lap: ty le 1/" (itoa sc)
                 ", chi tiet 1/" (itoa *SD:DETSCALE*)
                 ", layer SD-*, text style SD-TEXT, dimstyle SD-1-" (itoa sc) "."))
  (sd:finish))

;;; --------------------------------------------------------------------------
;;;  SDKHUNG - Khung ban ve + khung ten (block co thuoc tinh)
;;; --------------------------------------------------------------------------
(defun sd:def-frame (bname w h m / x0 y0 x1 y1 tb)
  (entmake (list '(0 . "BLOCK") (cons 2 bname) '(70 . 2) '(10 0.0 0.0 0.0)))
  (sd:pline (list '(0 0) (list w 0) (list w h) (list 0 h)) t "SD-KHUNG")
  (setq x0 25.0 y0 m x1 (- w m) y1 (- h m))
  (sd:plinew (list (list x0 y0) (list x1 y0) (list x1 y1) (list x0 y1)) t 0.7 "SD-KHUNG")
  ;; Khung ten 180 x 56 o goc phai duoi
  (setq tb (list (- x1 180.0) y0 0.0))
  (sd:plinew (list tb (sd:p+ tb 180 0) (sd:p+ tb 180 56) (sd:p+ tb 0 56)) t 0.5 "SD-KHUNG")
  (foreach l '((0 8 180 8) (0 16 180 16) (0 32 180 32) (0 40 180 40) (0 48 180 48)
               (35 0 35 56) (90 0 90 16) (115 0 115 16) (140 8 140 16)
               (155 8 155 16) (150 0 150 8) (160 0 160 8))
    (sd:line (sd:p+ tb (nth 0 l) (nth 1 l)) (sd:p+ tb (nth 2 l) (nth 3 l)) "SD-BANG"))
  (foreach s '((2 51 "\\U+0110\\U+01A0N V\\U+1ECA THI C\\U+00D4NG") (2 43 "C\\U+00D4NG TR\\U+00CCNH") (2 35 "H\\U+1EA0NG M\\U+1EE4C")
               (2 23 "T\\U+00CAN B\\U+1EA2N V\\U+1EBC") (2 11 "NG\\U+01AF\\U+1EDCI V\\U+1EBC") (2 3 "KI\\U+1EC2M TRA")
               (92 11 "T\\U+1EF6 L\\U+1EC6") (142 11 "NG\\U+00C0Y") (92 3 "S\\U+1ED0 B\\U+1EA2N V\\U+1EBC") (152 3 "REV"))
    (sd:text (sd:p+ tb (nth 0 s) (nth 1 s)) (nth 2 s) 2.0 "L" "SD-CHU"))
  ;; Thuoc tinh: (tag prompt default x y h)
  (foreach a '(("COMPANY" "Don vi thi cong" "C\\U+00D4NG TY ..." 37 50.8 3.0)
               ("PROJECT" "Cong trinh" "C\\U+00D4NG TR\\U+00CCNH ..." 37 42.8 3.0)
               ("ITEM" "Hang muc" "H\\U+1EA0NG M\\U+1EE4C ..." 37 34.8 3.0)
               ("TITLE" "Ten ban ve" "T\\U+00CAN B\\U+1EA2N V\\U+1EBC" 37 22.0 4.0)
               ("DRAWN" "Nguoi ve" "" 37 11 2.5)
               ("CHECKED" "Kiem tra" "" 37 3 2.5)
               ("SCALE" "Ty le" "1/100" 117 11 2.5)
               ("DATE" "Ngay" "" 157 11 2.5)
               ("SHEET" "So ban ve" "SD-01" 117 3 2.5)
               ("REV" "Lan sua" "0" 162 3 2.5))
    (entmake (list '(0 . "ATTDEF") '(8 . "SD-CHU")
                   (cons 10 (sd:p+ tb (nth 3 a) (nth 4 a))) (cons 40 (nth 5 a))
                   (cons 1 (nth 2 a)) (cons 3 (nth 1 a)) (cons 2 (nth 0 a))
                   '(70 . 0) (cons 7 (sd:tstyle)) '(72 . 0) '(74 . 0))))
  (entmake '((0 . "ENDBLK"))))

;; Chen block co thuoc tinh; vals = ((TAG . gia tri) ...)
(defun sd:insert-attr (bname pt sc lay vals / e ed tag p)
  (entmake (list '(0 . "INSERT") (cons 8 lay) '(66 . 1) (cons 2 bname) (cons 10 pt)
                 (cons 41 sc) (cons 42 sc) (cons 43 sc) '(50 . 0.0)))
  (setq e (tblobjname "BLOCK" bname))
  (while (setq e (entnext e))
    (setq ed (entget e))
    (if (= (cdr (assoc 0 ed)) "ATTDEF")
      (progn
        (setq tag (cdr (assoc 2 ed))
              p   (cdr (assoc 10 ed)))
        (entmake (list '(0 . "ATTRIB") (cons 8 (cdr (assoc 8 ed)))
                       (cons 10 (sd:p+ pt (* sc (car p)) (* sc (cadr p))))
                       (cons 40 (* sc (cdr (assoc 40 ed))))
                       (cons 1 (cond ((cdr (assoc tag vals))) ((cdr (assoc 1 ed)))))
                       (cons 2 tag) '(70 . 0) (cons 7 (cdr (assoc 7 ed))))))))
  (entmake '((0 . "SEQEND")))
  (entlast))

(defun c:SDKHUNG (/ sz ori sc paper w h bname pt)
  (sd:begin)
  (if (not (sd:dlg "Khung ban ve (SDKHUNG)"
                   (list (list "sz" "Kho giay" 'kw "A1" '("A0" "A1" "A2" "A3" "A4"))
                         (list "ori" "Huong giay" 'kw "Ngang" '("Ngang" "Dung"))
                         (list "sc" "Ty le khung 1/" 'int *SD:SCALE*))))
    (exit))
  (setq sz (sd:v "sz") ori (sd:v "ori") sc (sd:v "sc"))
  (setq paper (cdr (assoc sz '(("A0" 1189 841) ("A1" 841 594) ("A2" 594 420)
                               ("A3" 420 297) ("A4" 297 210)))))
  (if (= ori "Dung")
    (setq w (float (cadr paper)) h (float (car paper)))
    (setq w (float (car paper)) h (float (cadr paper))))
  (setq bname (strcat "SD-KHUNG-" sz (if (= ori "Dung") "D" "")))
  (if (not (tblsearch "BLOCK" bname))
    (sd:def-frame bname w h (if (member sz '("A3" "A4")) 5.0 10.0)))
  (if (setq pt (sd:getpt "\nDiem chen (goc trai duoi khung): " nil))
    (progn
      (sd:insert-attr bname pt (float sc) "SD-KHUNG"
                      (list (cons "SCALE" (strcat "1/" (itoa sc)))
                            (cons "DATE" (sd:today))))
      (princ (strcat "\n[SD] Da chen khung " sz " ty le 1/" (itoa sc)
                     ". Nhap dup vao khung ten de sua thong tin."))))
  (sd:finish))

;;; --------------------------------------------------------------------------
;;;  SDTRUC - Luoi truc (so 1,2,3... theo X; chu A,B,C... theo Y) + kich thuoc
;;; --------------------------------------------------------------------------
(defun sd:axis-letter (i / L)
  (setq L "ABCDEFGHJKLMNPQRSTUVWXYZ")
  (if (< i 24)
    (substr L (1+ i) 1)
    (strcat (substr L (1+ (rem i 24)) 1) (itoa (/ i 24)))))

(defun sd:bubble (c r lab)
  (sd:circle c r "SD-KYHIEU")
  (sd:text c lab (* 0.9 r) "MC" "SD-CHU"))

(defun c:SDTRUC (/ sc o xs ys ext r xmax ymax i lab yb xl)
  (sd:begin)
  (setq sc (sd:sc))
  (if (not (sd:dlg "Luoi truc (SDTRUC)"
                   (list (list "gx" "Khoang cach truc X (mm), vd 3*6000,4500" 'str (cond (*SD:GX*) ("3*6000")))
                         (list "gy" "Khoang cach truc Y (mm), vd 2*7200" 'str (cond (*SD:GY*) ("2*7200"))))))
    (exit))
  (setq *SD:GX* (sd:v "gx") *SD:GY* (sd:v "gy"))
  (setq xs (sd:cumul (sd:parse-spacing *SD:GX*))
        ys (sd:cumul (sd:parse-spacing *SD:GY*)))
  (if (setq o (sd:getpt "\nDiem goc (giao truc 1-A): " nil))
    (progn
      (setq ext (* 12.0 sc) r (* 4.0 sc) xmax (last xs) ymax (last ys) i 0)
      (foreach x xs
        (setq i (1+ i) lab (itoa i))
        (sd:line (sd:p+ o x (- ext)) (sd:p+ o x (+ ymax ext)) "SD-TRUC")
        (sd:bubble (sd:p+ o x (- (+ ext r))) r lab)
        (sd:bubble (sd:p+ o x (+ ymax ext r)) r lab))
      (setq i 0)
      (foreach y ys
        (setq lab (sd:axis-letter i) i (1+ i))
        (sd:line (sd:p+ o (- ext) y) (sd:p+ o (+ xmax ext) y) "SD-TRUC")
        (sd:bubble (sd:p+ o (- (+ ext r)) y) r lab)
        (sd:bubble (sd:p+ o (+ xmax ext r) y) r lab))
      ;; Kich thuoc: chuoi khoang truc + tong
      (sd:use-dimstyle sc)
      (setq yb (- (+ ext r r)) xl (- (+ ext r r)))
      (if (cdr xs)
        (progn
          (sd:dimchain (mapcar '(lambda (x) (sd:p+ o x yb)) xs) "H" (sd:p+ o 0 (- yb (* 8 sc))))
          (if (cddr xs)
            (sd:dim (sd:p+ o 0 yb) (sd:p+ o xmax yb) "H" (sd:p+ o 0 (- yb (* 16 sc)))))))
      (if (cdr ys)
        (progn
          (sd:dimchain (mapcar '(lambda (y) (sd:p+ o xl y)) ys) "V" (sd:p+ o (- xl (* 8 sc)) 0))
          (if (cddr ys)
            (sd:dim (sd:p+ o xl 0) (sd:p+ o xl ymax) "V" (sd:p+ o (- xl (* 16 sc)) 0)))))
      (princ (strcat "\n[SD] Da ve " (itoa (length xs)) " x " (itoa (length ys)) " truc."))))
  (sd:finish))

;;; --------------------------------------------------------------------------
;;;  SDCAODO - Ky hieu cao do (tu dong tinh theo diem goc hoac nhap tay), co hop thoai
;;; --------------------------------------------------------------------------
(defun sd:fmtlevel (v)
  (cond ((< (abs v) 0.0005) "%%p0.000")
        ((> v 0) (strcat "+" (sd:rtos v 3)))
        (t (sd:rtos v 3))))

(defun sd:levelmark (pt v sc)
  (sd:pline (list pt (sd:p+ pt (* -1.5 sc) (* 2.5 sc)) (sd:p+ pt (* 1.5 sc) (* 2.5 sc))) t "SD-KYHIEU")
  (sd:solid3 pt (sd:p+ pt 0 (* 2.5 sc)) (sd:p+ pt (* 1.5 sc) (* 2.5 sc)) "SD-KYHIEU")
  (sd:line (sd:p+ pt (* -1.5 sc) (* 2.5 sc)) (sd:p+ pt (* 14.0 sc) (* 2.5 sc)) "SD-KYHIEU")
  (sd:text (sd:p+ pt (* 1.0 sc) (* 3.3 sc)) (sd:fmtlevel v) (* 2.5 sc) "L" "SD-CHU"))

;; Chon diem goc: *SD:YB* = toa do Y cua diem co cao do da biet
(defun sd:caodo-base (/ b)
  (if (setq b (sd:getpt "\nChon diem co cao do da biet (diem goc): " nil))
    (setq *SD:YB* (cadr b))))

(defun c:SDCAODO (/ sc pt v mode y0)
  (sd:begin)
  (setq sc (sd:sc))
  (if (not (sd:dlg "Ky hieu cao do (SDCAODO)"
                   (list (list "mode" "Cach ghi cao do" 'kw (cond (*SD:CDMODE*) ("Goc"))
                               '(("Goc" . "Tu tinh theo diem goc (toa do Y)") ("Tay" . "Nhap gia tri tung diem")))
                         (list "setb" "Chon lai diem goc tren ban ve" 'tog (null *SD:YB*) nil '("mode" "Goc"))
                         (list "v0" "Cao do tai diem goc (m)" 'real0 (cond (*SD:Y0V*) (0.0)) nil '("mode" "Goc"))
                         (list "vt" "Gia tri cao do dau tien (m)" 'real0 (cond (*SD:CDV*) (0.0)) nil '("mode" "Tay")))))
    (exit))
  (setq mode (sd:v "mode") *SD:CDMODE* mode *SD:Y0V* (sd:v "v0") v (sd:v "vt"))
  (if (and (= mode "Goc") (or (sd:v "setb") (null *SD:YB*)))
    (sd:caodo-base))
  (if (and (= mode "Goc") (null *SD:YB*))
    (princ "\n[SD] Chua co diem goc.")
    (while (progn (if (= mode "Goc") (initget "G"))
                  (setq pt (getpoint (if (= mode "Goc")
                                       "\nDiem dat cao do [G = chon lai diem goc] <Enter ket thuc>: "
                                       "\nDiem dat cao do <Enter ket thuc>: "))))
      (if (= pt "G")
        (sd:caodo-base)
        (progn
          (setq pt (sd:w pt))
          (if (= mode "Goc")
            (setq y0 (- *SD:YB* (* 1000.0 *SD:Y0V*)) v (/ (- (cadr pt) y0) 1000.0))
            (setq v (cond ((getreal (strcat "\nGia tri cao do (m) <" (sd:rtos v 3) ">: "))) (v))
                  *SD:CDV* v))
          (sd:levelmark pt v sc)))))
  (sd:finish))

;;; --------------------------------------------------------------------------
;;;  SDMC - Ky hieu mat cat
;;; --------------------------------------------------------------------------
(defun c:SDMC (/ sc p1 p2 ps lab ang n pp dir bp tp)
  (sd:begin)
  (setq sc (sd:sc))
  (if (not (sd:dlg "Ky hieu mat cat (SDMC)" (list (list "lab" "Ten mat cat" 'str (cond (*SD:MCLAB*) ("1"))))))
    (exit))
  (if (and (setq p1 (sd:getpt "\nDiem dau duong cat: " nil))
           (setq p2 (sd:getpt "\nDiem cuoi duong cat: " p1))
           (setq ps (sd:getpt "\nChon phia nhin: " p2)))
    (progn
      (setq lab (sd:v "lab"))
      (if (wcmatch lab "#*") (setq *SD:MCLAB* (itoa (1+ (atoi lab)))))
      (setq ang (angle p1 p2))
      ;; huong nhin vuong goc, ve phia diem ps
      (setq n (if (> (- (* (- (car p2) (car p1)) (- (cadr ps) (cadr p1)))
                        (* (- (cadr p2) (cadr p1)) (- (car ps) (car p1)))) 0)
                (+ ang (/ pi 2)) (- ang (/ pi 2))))
      (foreach e (list (list p1 ang) (list p2 (+ ang pi)))
        (setq pp (car e) dir (cadr e))
        (sd:plinew (list pp (polar pp dir (* 8 sc))) nil (* 0.6 sc) "SD-KYHIEU")
        (setq tp (polar pp n (* 7 sc)) bp (polar pp n (* 4.5 sc)))
        (sd:line pp bp "SD-KYHIEU")
        (sd:solid3 tp (polar bp dir (* 1.0 sc)) (polar bp (+ dir pi) (* 1.0 sc)) "SD-KYHIEU")
        (sd:text (polar (polar pp n (* 4 sc)) (+ dir pi) (* 3.5 sc)) lab (* 3.5 sc) "MC" "SD-CHU"))))
  (sd:finish))

;;; --------------------------------------------------------------------------
;;;  Mat cat BTCT: dam (SDDAM) va cot (SDCOT)
;;; --------------------------------------------------------------------------
;; Dai: duong tim cach mep (a + ds/2), co moc 135 do o goc trai tren
(defun sd:stirrup (o b h a ds / c k)
  (setq c (+ a (/ ds 2.0)))
  (sd:plinew (list (sd:p+ o c c) (sd:p+ o (- b c) c) (sd:p+ o (- b c) (- h c)) (sd:p+ o c (- h c)))
             t ds "SD-THEP-DAI")
  (setq k (sd:p+ o c (- h c)))
  (sd:plinew (list (sd:p+ k 0 (* -2 ds)) (sd:p+ k (* 5 ds) (* -7 ds))) nil ds "SD-THEP-DAI")
  (sd:plinew (list (sd:p+ k (* 2 ds) 0) (sd:p+ k (* 7 ds) (* -5 ds))) nil ds "SD-THEP-DAI"))

;; Hang thanh thep n thanh, duong kinh d, tai cao do y. Tra ve diem thanh dau tien.
(defun sd:barrow (o b a ds n d y / x0 dx i)
  (setq x0 (+ a ds (/ d 2.0)))
  (if (= n 1)
    (progn (sd:dot (sd:p+ o (/ b 2.0) y) d "SD-THEP-CHU") (sd:p+ o (/ b 2.0) y))
    (progn
      (setq dx (/ (- b x0 x0) (1- n)) i 0)
      (repeat n
        (sd:dot (sd:p+ o (+ x0 (* i dx)) y) d "SD-THEP-CHU")
        (setq i (1+ i)))
      (sd:p+ o x0 y))))

(defun sd:sec-common (o b h a ds s ts title)
  (sd:rect o b h "SD-BETONG")
  (sd:stirrup o b h a ds)
  (sd:use-dimstyle ts)
  (sd:dim o (sd:p+ o b 0) "H" (sd:p+ o 0 (* -8 ts)))
  (sd:dim (sd:p+ o b 0) (sd:p+ o b h) "V" (sd:p+ o (+ b (* 8 ts)) 0))
  (sd:tagL (sd:p+ o (+ a (/ ds 2.0)) (/ h 2.0)) (sd:p+ o (* -6 ts) (/ h 2.0))
           (strcat "%%c" (sd:num ds) "a" (sd:num s)) ts)
  (sd:text (sd:p+ o (/ b 2.0) (* -17 ts)) title (* 3.5 ts) "MC" "SD-CHU")
  (sd:text (sd:p+ o (/ b 2.0) (* -22 ts)) (strcat (sd:num b) "\\U+00D7" (sd:num h)) (* 2.5 ts) "MC" "SD-CHU"))

(defun c:SDDAM (/ ts name b h a top bot ds s o p)
  (sd:begin)
  (setq ts (float *SD:DETSCALE*))
  (if (not (sd:dlg "Mat cat dam BTCT (SDDAM)"
                   (list (list "name" "Ten dam" 'str (cond (*SD:DNAME*) ("D1")))
                         (list "b" "Be rong b (mm)" 'real (cond (*SD:DB*) (220.0)))
                         (list "h" "Chieu cao h (mm)" 'real (cond (*SD:DH*) (500.0)))
                         (list "a" "Lop bao ve (mm)" 'real 25.0)
                         (list "top" "Thep tren (vd 2d18)" 'bar "2d18")
                         (list "bot" "Thep duoi (vd 3d20)" 'bar "3d20")
                         (list "ds" "Duong kinh dai (mm)" 'real 8.0)
                         (list "s" "Buoc dai (mm)" 'real 150.0))))
    (exit))
  (setq name (sd:v "name") b (sd:v "b") h (sd:v "h") a (sd:v "a") top (sd:v "top") bot (sd:v "bot")
        ds (sd:v "ds") s (sd:v "s"))
  (setq *SD:DNAME* name *SD:DB* b *SD:DH* h)
  (if (setq o (sd:getpt "\nDiem chen (goc trai duoi): " nil))
    (progn
      (sd:sec-common o b h a ds s ts (strcat "M\\U+1EB6T C\\U+1EAET " name))
      (setq p (sd:barrow o b a ds (car top) (cadr top) (- h a ds (/ (cadr top) 2.0))))
      (sd:tagL p (sd:p+ o (* -6 ts) (+ h (* 6 ts)))
               (strcat (itoa (car top)) "%%c" (sd:num (cadr top))) ts)
      (setq p (sd:barrow o b a ds (car bot) (cadr bot) (+ a ds (/ (cadr bot) 2.0))))
      (sd:tagL p (sd:p+ o (* -6 ts) (* -4 ts))
               (strcat (itoa (car bot)) "%%c" (sd:num (cadr bot))) ts)
      (sd:use-dimstyle *SD:SCALE*)))
  (sd:finish))

;; Dai phu cot: chon thanh giua can giu (TCVN 5574 / ACI: thanh goc + thanh xen ke duoc giu,
;; thanh khong giu cach thanh duoc giu <= 150 mm thong thuy). Tra ve chi so thanh giua (1..n-2).
(defun sd:tie-pick (n s d mode / i r prev)
  (setq prev t i 1)
  (if (/= mode "Khong")
    (repeat (max 0 (- n 2))
      (if (or (= mode "Tatca") (not prev) (> (- s d) 150.0))
        (setq r (cons i r) prev t)
        (setq prev nil))
      (setq i (1+ i))))
  (reverse r))

;; Gom dai phu giong nhau: grp = (((shp prm) so-luong hint) ...)
(defun sd:tie-add (grp shp prm hint / k e)
  (setq k (list shp (mapcar '(lambda (x) (fix (+ x 0.5))) prm)))
  (if (setq e (assoc k grp))
    (subst (list k (1+ (cadr e)) (caddr e)) e grp)
    (append grp (list (list k 1 hint)))))

;; Ve (draw = T) dai phu trong mat cat cot goc o; tra ve cac nhom ((shp prm so-dai-1-lop hint) ...)
;; mode: Tudong / Tatca / Khong; typ: MocC (dai 1 nhanh, moc 135) / Kin (dai kin trong, ghep cap doi xung)
(defun sd:col-ties (o b h a ds nb nh d mode typ draw / x0 grp dir n side span s idx pos q i j w c1 hk p1 p2)
  (setq x0 (+ a ds (/ d 2.0)) c1 (+ a (* 1.5 ds)) hk (* 4 ds))
  ;; dir "X": thanh giua tren 2 hang canh b, dai di theo Y; dir "Y": thanh giua 2 cot canh h, dai theo X
  (foreach dir (list (list "X" nb b h) (list "Y" nh h b))
    (setq n (cadr dir) side (caddr dir) span (cadddr dir))
    (if (> n 2)
      (progn
        (setq s (/ (- side x0 x0) (1- n))
              idx (sd:tie-pick n s d mode)
              pos (mapcar '(lambda (i) (+ x0 (* i s))) idx))
        (while pos
          (if (and (= typ "Kin") (cdr pos))
            (progn
              (setq i (car pos) j (last pos) w (+ (- j i) d ds ds)
                    pos (cdr (reverse (cdr (reverse pos)))))
              (setq grp (sd:tie-add grp "Dai" (list w (- span a a)) (if (= (car dir) "X") (list (- i (/ d 2.0) ds) (/ span 2.0)) (list (/ span 2.0) (- i (/ d 2.0) ds)))))
              (if draw
                (sd:plinew (mapcar '(lambda (q) (if (= (car dir) "X") (sd:p+ o (car q) (cadr q)) (sd:p+ o (cadr q) (car q))))
                                   (list (list (- i (/ d 2.0) (/ ds 2.0)) c1) (list (+ j (/ d 2.0) (/ ds 2.0)) c1)
                                         (list (+ j (/ d 2.0) (/ ds 2.0)) (- span c1)) (list (- i (/ d 2.0) (/ ds 2.0)) (- span c1))))
                           t ds "SD-THEP-DAI")))
            (progn
              (setq i (car pos) pos (cdr pos))
              (setq grp (sd:tie-add grp "Mot" (list (- span a a)) (if (= (car dir) "X") (list i (/ span 2.0)) (list (/ span 2.0) i))))
              (if draw
                (sd:plinew (mapcar '(lambda (q) (if (= (car dir) "X") (sd:p+ o (car q) (cadr q)) (sd:p+ o (cadr q) (car q))))
                                   (list (list (+ i hk) (+ c1 hk)) (list i c1) (list i (- span c1)) (list (- i hk) (- span c1 hk))))
                           nil ds "SD-THEP-DAI"))))))))
  (mapcar '(lambda (g) (list (car (car g)) (cadr (car g)) (cadr g) (caddr g))) grp))

;; Truong hop thoai dai phu (dung chung SDCOT, SDCOTTHEP)
(defun sd:tie-fields ()
  (list (list "dp" "Dai phu / moc C" 'kw "Tudong"
              '(("Tudong" . "Tu dong: thanh xen ke, cach <= 150") ("Tatca" . "Giu moi thanh giua") ("Khong" . "Khong co dai phu")))
        (list "lp" "Loai dai phu" 'kw "MocC" '(("MocC" . "Moc C - dai 1 nhanh") ("Kin" . "Dai kin trong (ghep cap)"))
              '("dp" "Tudong" "Tatca"))))

(defun c:SDCOT (/ ts name b h a nb nh d ds s o x0 yb yt dy i p tot g)
  (sd:begin)
  (setq ts (float *SD:DETSCALE*))
  (if (not (sd:dlg "Mat cat cot BTCT (SDCOT)"
                   (list (list "name" "Ten cot" 'str (cond (*SD:CNAME*) ("C1")))
                         (list "b" "Canh b - theo X (mm)" 'real (cond (*SD:CB*) (300.0)))
                         (list "h" "Canh h - theo Y (mm)" 'real (cond (*SD:CH*) (400.0)))
                         (list "a" "Lop bao ve (mm)" 'real 25.0)
                         (list "nb" "So thanh canh b (ke ca thanh goc)" 'int 3)
                         (list "nh" "So thanh canh h (ke ca thanh goc)" 'int 3)
                         (list "d" "Duong kinh thep doc (mm)" 'real 18.0)
                         (list "ds" "Duong kinh dai (mm)" 'real 8.0)
                         (list "s" "Buoc dai (mm)" 'real 200.0)
                         (car (sd:tie-fields)) (cadr (sd:tie-fields)))))
    (exit))
  (setq name (sd:v "name") b (sd:v "b") h (sd:v "h") a (sd:v "a") nb (max 2 (sd:v "nb")) nh (max 2 (sd:v "nh"))
        d (sd:v "d") ds (sd:v "ds") s (sd:v "s"))
  (setq *SD:CNAME* name *SD:CB* b *SD:CH* h)
  (if (setq o (sd:getpt "\nDiem chen (goc trai duoi): " nil))
    (progn
      (sd:sec-common o b h a ds s ts (strcat "M\\U+1EB6T C\\U+1EAET " name))
      (setq x0 (+ a ds (/ d 2.0)) yb x0 yt (- h x0))
      (sd:barrow o b a ds nb d yb)
      (setq p (sd:barrow o b a ds nb d yt))
      (if (> nh 2)
        (progn
          (setq dy (/ (- yt yb) (1- nh)) i 1)
          (repeat (- nh 2)
            (sd:dot (sd:p+ o x0 (+ yb (* i dy))) d "SD-THEP-CHU")
            (sd:dot (sd:p+ o (- b x0) (+ yb (* i dy))) d "SD-THEP-CHU")
            (setq i (1+ i)))))
      (setq tot (+ (* 2 nb) (* 2 (- nh 2))) i 0)
      (sd:tagL p (sd:p+ o (* -6 ts) (+ h (* 6 ts)))
               (strcat (itoa tot) "%%c" (sd:num d)) ts)
      ;; dai phu: ghi chu ben phai mat cat (duoi ngang nam ngoai tiet dien)
      (foreach g (sd:col-ties o b h a ds nb nh d (sd:v "dp") (sd:v "lp") t)
        (setq p (strcat (if (> (nth 2 g) 1) (strcat (itoa (nth 2 g)) "x") "") "%%c" (sd:num ds) "a" (sd:num s)
                        (if (= (car g) "Mot") " MOC C" " DAI PHU")))
        (sd:tagL (sd:p+ o (car (nth 3 g)) (cadr (nth 3 g)))
                 (sd:p+ o (+ b (* 14 ts) (* ts (max 12.0 (* 1.8 (strlen p))))) (- (* 0.35 h) (* i 6 ts)))
                 p ts)
        (setq i (1+ i)))
      (sd:use-dimstyle *SD:SCALE*)))
  (sd:finish))

;;; --------------------------------------------------------------------------
;;;  CAI DAT THEP: cay thuong pham, be tong, mac thep, noi chong, moc, mach cat
;;; --------------------------------------------------------------------------
;; TCVN 5574:2018: Rbt (MPa) theo cap do ben be tong, Rs (MPa) theo mac thep
(setq *SD:RBT* '(("B15" . 0.75) ("B20" . 0.90) ("B25" . 1.05) ("B30" . 1.15)
                 ("B35" . 1.30) ("B40" . 1.40))
      *SD:RS*  '(("CB240-T" . 210.0) ("CB300-V" . 260.0) ("CB400-V" . 350.0)
                 ("CB500-V" . 435.0)))

(defun sd:cfg (key def) (cond ((vlax-ldata-get "SD" key)) (def)))
(defun sd:cfg-put (key v) (vlax-ldata-put "SD" key v) v)

;; Lam tron len boi so cua step
(defun sd:ceil (x step) (* step (fix (+ (/ x step) 0.999999))))

;; Chieu dai noi chong thep (mm), TCVN 5574:2018 muc 10.3.6:
;;   l0,an = Rs.As / (Rbond.us) = Rs.d / (4.Rbond),  Rbond = eta1.eta2.Rbt
;;   eta1 = 2.5 thep van (CB300-V tro len), 1.5 thep tron (CB240-T)
;;   eta2 = 1.0 khi d <= 32, 0.9 khi d = 36, 40
;;   l_lap = alpha.l0,an, alpha = 1.2 vung keo, 0.9 vung nen
;;   va khong nho hon: keo 20d va 250 mm, nen 15d va 200 mm
;; Neu LAPK > 0: l_lap = LAPK x d (vd 40d).
(defun sd:lap (d / k thep rbt rs e1 e2 l0 nen)
  (setq k (sd:cfg "LAPK" 0.0))
  (if (> k 0)
    (sd:ceil (* k d) 50.0)
    (progn
      (setq thep (sd:cfg "THEP" "CB400-V")
            rbt  (cond ((cdr (assoc (sd:cfg "BETONG" "B25") *SD:RBT*))) (1.05))
            rs   (cond ((cdr (assoc thep *SD:RS*))) (350.0))
            e1   (if (= thep "CB240-T") 1.5 2.5)
            e2   (if (> d 32.0) 0.9 1.0)
            l0   (/ (* rs d) (* 4.0 e1 e2 rbt))
            nen  (= (sd:cfg "VUNG" "Keo") "Nen"))
      (sd:ceil (if nen
                 (max (* 0.9 l0) (* 15.0 d) 200.0)
                 (max (* 1.2 l0) (* 20.0 d) 250.0))
               50.0))))

(defun sd:lapinfo (/ k)
  (setq k (sd:cfg "LAPK" 0.0))
  (if (> k 0)
    (strcat (sd:num k) "d")
    (strcat "TCVN 5574:2018, " (sd:cfg "BETONG" "B25") ", " (sd:cfg "THEP" "CB400-V")
            ", vung " (if (= (sd:cfg "VUNG" "Keo") "Nen") "nen" "keo"))))

;; Chia thanh thang dai hon cay thuong pham thanh cac doan cat (da cong lap).
;; Tra ve nil neu khong can noi.
(defun sd:splice (L d / ls lap m p r)
  (setq ls (sd:cfg "STOCK" 11700.0) lap (sd:lap d))
  (if (and (> L ls) (> ls (* 2 lap)))
    (progn
      (setq m (fix (+ (/ (- L lap) (- ls lap)) 0.999999)))
      (if (= (sd:cfg "NOIKIEU" "Cay") "Deu")
        (progn
          (setq p (min ls (sd:ceil (/ (+ L (* (1- m) lap)) m) 10.0)))
          (repeat m (setq r (cons p r))))
        (progn
          (repeat (1- m) (setq r (cons ls r)))
          (setq r (append r (list (- L (* (1- m) (- ls lap))))))))
      r)))

;; Gom phan tu trung: (a a b) -> ((a . 2) (b . 1)), giu thu tu
(defun sd:group (lst / r e)
  (foreach x lst
    (if (setq e (assoc x r))
      (setq r (subst (cons x (1+ (cdr e))) e r))
      (setq r (cons (cons x 1) r))))
  (reverse r))

;; (11700 11700 5300) -> "11700x2 + 5300"
(defun sd:pcs-str (lst mul)
  (sd:join (mapcar '(lambda (g) (strcat (sd:num (car g))
                                        (if (> (cdr g) 1) (strcat mul (itoa (cdr g))) "")))
                   (sd:group lst))
           " + "))

(defun sd:nums->str (lst) (if lst (sd:join (mapcar 'sd:num lst) ",") ""))
(defun sd:str->nums (s) (if s (mapcar 'atof (vl-remove "" (sd:split s ",")))))
(defun sd:repeat (x n / r) (repeat n (setq r (cons x r))) r)
(defun sd:replace-nth (i v lst / j)
  (setq j -1)
  (mapcar '(lambda (x) (if (= (setq j (1+ j)) i) v x)) lst))

(defun c:SDTHEPSET (/ v)
  (sd:begin)
  (if (not (sd:dlg "Cai dat thep (SDTHEPSET)"
                   (list (list "STOCK" "Chieu dai cay thep thuong pham (mm)" 'real (sd:cfg "STOCK" 11700.0))
                         (list "BETONG" "Cap do ben be tong" 'kw (sd:cfg "BETONG" "B25") '("B15" "B20" "B25" "B30" "B35" "B40"))
                         (list "THEP" "Mac thep" 'kw (sd:cfg "THEP" "CB400-V") '("CB240-T" "CB300-V" "CB400-V" "CB500-V"))
                         (list "VUNG" "Vung noi chong" 'kw (sd:cfg "VUNG" "Keo") '(("Keo" . "Vung keo") ("Nen" . "Vung nen")))
                         (list "LAPK" "He so noi k (lap = k.d), 0 = theo TCVN" 'real0 (sd:cfg "LAPK" 0.0))
                         (list "NOIKIEU" "Chia doan noi" 'kw (sd:cfg "NOIKIEU" "Cay")
                               '(("Cay" . "Cay nguyen + doan le") ("Deu" . "Chia deu")))
                         (list "HOOK" "Moc dai 135 do = k.d (>= 75 mm), k" 'real (sd:cfg "HOOK" 10.0))
                         (list "KERF" "Be rong mach cat (mm)" 'real0 (sd:cfg "KERF" 0.0))
                         (list "REUSE" "Doan thua tai su dung toi thieu (mm)" 'real (sd:cfg "REUSE" 1000.0)))))
    (exit))
  (foreach k '("STOCK" "BETONG" "THEP" "VUNG" "LAPK" "NOIKIEU" "HOOK" "KERF" "REUSE")
    (sd:cfg-put k (if (numberp (sd:v k)) (float (sd:v k)) (sd:v k))))
  (princ (strcat "\n[SD] Chieu dai noi chong (" (sd:lapinfo) "):"))
  (foreach d '(10.0 12.0 14.0 16.0 18.0 20.0 22.0 25.0 28.0 32.0)
    (princ (strcat "\n   D" (sd:num d) ": " (sd:num (sd:lap d)) " mm (" (sd:rtos (/ (sd:lap d) d) 1) "d)")))
  (sd:finish))

;;; --------------------------------------------------------------------------
;;;  HINH DANG THANH THEP
;;;  (ma  ten  tham-so  diem-ve[0..1]  doan-phu  nhan(tham-so x y can-le)  goi-y  mac-dinh)
;;; --------------------------------------------------------------------------
(setq *SD:SHAPES*
  '(("Thang" "Th\\U+1EB3ng" ("A") ((0 0.35) (1 0.35)) nil
     ((0 0.5 0.75 "MC"))
     "A = chieu dai thanh" (6000.0))
    ("L" "Ch\\U+1EEF L" ("A" "B") ((0 1) (0 0) (1 0)) nil
     ((0 0.55 0.3 "MC") (1 0.05 0.65 "ML"))
     "A = doan ngang, B = doan uon (kich thuoc ngoai)" (3000.0 300.0))
    ("U" "Ch\\U+1EEF U" ("A" "B" "C") ((0 1) (0 0) (1 0) (1 1)) nil
     ((0 0.05 0.65 "ML") (1 0.5 0.3 "MC") (2 0.95 0.65 "MR"))
     "A = canh trai, B = day, C = canh phai" (300.0 3000.0 300.0))
    ("Z" "C\\U+1ED5 d\\U+00EA" ("A" "B" "C") ((0 0) (0.3 0) (0.6 1) (1 1)) nil
     ((0 0.15 0.3 "MC") (1 0.47 0.45 "ML") (2 0.8 0.7 "MC"))
     "A = doan duoi, B = doan xien, C = doan tren" (1000.0 500.0 1000.0))
    ("Dai" "\\U+0110ai k\\U+00EDn" ("A" "B") ((0.3 0) (0.7 0) (0.7 1) (0.3 1) (0.3 0))
     (((0.3 0.85) (0.4 0.55)) ((0.36 1) (0.46 0.7)))
     ((0 0.5 0.3 "MC") (1 0.74 0.5 "ML"))
     "A = be rong, B = chieu cao (kich thuoc ngoai dai), cong them 2 moc 135 do" (170.0 450.0))
    ("Mot" "\\U+0110ai 1 nh\\U+00E1nh" ("A") ((0 0.6) (1 0.6))
     (((0 0.6) (0.08 0.15)) ((1 0.6) (0.92 0.15)))
     ((0 0.5 0.85 "MC"))
     "A = chieu dai thang, cong them 2 moc 135 do" (200.0))))

(defun sd:hook (d) (max 75.0 (* (sd:cfg "HOOK" 10.0) d)))

(defun sd:shape-len (code prm d)
  (cond ((= code "Dai") (+ (* 2.0 (+ (nth 0 prm) (nth 1 prm))) (* 2.0 (sd:hook d))))
        ((= code "Mot") (+ (nth 0 prm) (* 2.0 (sd:hook d))))
        (t (apply '+ prm))))

;; Ve so do hinh dang vao vung chu nhat goc o, rong w, cao h (khong theo ty le)
(defun sd:nmap (p o w h) (sd:p+ o (* w (car p)) (* h (cadr p))))
(defun sd:draw-shape (code prm o w h sc / sh)
  (if (setq sh (assoc code *SD:SHAPES*))
    (progn
      (sd:pline (mapcar '(lambda (p) (sd:nmap p o w h)) (nth 3 sh)) nil "SD-THEP-CHU")
      (foreach s (nth 4 sh)
        (sd:line (sd:nmap (car s) o w h) (sd:nmap (cadr s) o w h) "SD-THEP-CHU"))
      (foreach l (nth 5 sh)
        (if (nth (car l) prm)
          (sd:text (sd:nmap (cdr l) o w h) (sd:num (nth (car l) prm)) (* 1.8 sc) (nth 3 l) "SD-CHU"))))))

(defun sd:measure (/ ss i len)
  (setq len 0.0)
  (princ "\nChon cac doan the hien thanh thep: ")
  (if (setq ss (ssget '((0 . "LINE,LWPOLYLINE,POLYLINE,ARC,SPLINE"))))
    (progn (setq i 0)
           (repeat (sslength ss) (setq len (+ len (sd:len (ssname ss i))) i (1+ i)))))
  (princ (strcat "\nChieu dai do duoc: " (sd:rtos len 0) " mm"))
  len)

;;; --------------------------------------------------------------------------
;;;  SDTHEP - Ghi chu thanh thep: hinh dang, noi chong tu dong, luu XDATA
;;;  XDATA "SD_REBAR": so hieu, SL/CK, d, L, so CK, hinh dang, kich thuoc, doan cat
;;; --------------------------------------------------------------------------
(defun c:SDTHEP (/ sc mk n d shp prm len pcs lap k ls p1 p2 sg r c txt tl)
  (sd:begin)
  (setq sc (sd:sc) r (* 3.0 sc) ls (sd:cfg "STOCK" 11700.0))
  (setq shp (cond (*SD:LSHP*) ("Thang"))
        prm (cond ((cdr (assoc shp *SD:PRMS*))) ((nth 7 (assoc shp *SD:SHAPES*)))))
  (if (not (sd:dlg "Ghi chu thanh thep (SDTHEP)"
                   (list (list "mk" "So hieu thanh thep" 'str (itoa *SD:MARK*))
                         (list "n" "So thanh trong 1 cau kien" 'int (cond (*SD:LN*) (2)))
                         (list "d" "Duong kinh (mm)" 'real (cond (*SD:LD*) (16.0)))
                         (list "shp" "Hinh dang" 'kw shp
                               '(("Thang" . "Thang") ("L" . "Chu L") ("U" . "Chu U / thep mu") ("Z" . "Co de")
                                 ("Dai" . "Dai kin") ("Mot" . "Dai 1 nhanh / moc C")))
                         (list "note" "A = doan dau / ngang / be rong dai; B, C = cac doan tiep" 'note nil)
                         (list "A" "Kich thuoc A (mm)" 'real (cond ((car prm)) (6000.0)))
                         (list "B" "Kich thuoc B (mm)" 'real (cond ((cadr prm)) (300.0)) nil '("shp" "L" "U" "Z" "Dai"))
                         (list "C" "Kich thuoc C (mm)" 'real (cond ((caddr prm)) (300.0)) nil '("shp" "U" "Z"))
                         (list "do" "Do A tu doi tuong tren ban ve" 'tog nil nil '("shp" "Thang"))
                         (list "k" "So cau kien" 'int 1)
                         (list "ck" "Thuoc cau kien (de trong = khong)" 'str (cond (*SD:LCK*) (""))))))
    (exit))
  (setq *SD:LCK* (sd:v "ck"))
  (setq mk (sd:v "mk") n (sd:v "n") d (sd:v "d") shp (sd:v "shp")
        prm (sd:head (length (nth 2 (assoc shp *SD:SHAPES*))) (list (sd:v "A") (sd:v "B") (sd:v "C"))))
  (if (and (= shp "Thang") (sd:v "do")) (setq prm (list (sd:measure))))
  (setq *SD:PRMS* (cons (cons shp prm) (vl-remove (assoc shp *SD:PRMS*) *SD:PRMS*))
        len (sd:shape-len shp prm d))
  (setq *SD:LN* n *SD:LD* d *SD:LSHP* shp)
  (princ (strcat "\nChieu dai trien khai 1 thanh: L = " (sd:rtos len 0) " mm"))
  (cond ((and (= shp "Thang") (setq pcs (sd:splice len d)))
         (setq lap (sd:lap d))
         (princ (strcat "\nL > " (sd:num ls) " mm: noi chong, lap = " (sd:num lap) " mm ("
                        (sd:lapinfo) ")\n  -> doan cat: " (sd:pcs-str pcs "x")
                        "\n  Luu y: bo tri so le, khong qua 50% so thanh noi tai 1 tiet dien.")))
        ((> len ls)
         (princ (strcat "\n[!] L > chieu dai cay thep " (sd:num ls)
                        " mm. Nen tach thanh 2 so hieu (doan uon + doan thang) de noi."))))
  (setq k (sd:v "k"))
  (if (and (> len 0)
           (setq p1 (sd:getpt "\nDiem tren thanh thep: " nil))
           (setq p2 (sd:getpt "\nVi tri ghi chu: " p1)))
    (progn
      ;; co ky hieu theo ty le vung ve (mat cat chi tiet / mat bang)
      (if (setq sg (sd:sc-pt p1 500.0)) (setq sc sg r (* 3.0 sc)))
      (setq sg (if (>= (car p2) (car p1)) 1.0 -1.0)
            c  (sd:p+ p2 (* sg r) 0)
            txt (strcat (itoa n) "%%c" (sd:num d) " L=" (sd:rtos len 0)
                        (if (> k 1) (strcat " (\\U+00D7" (itoa k) " CK)") ""))
            tl (* sc (max 20.0 (* 1.9 (strlen txt)))))
      (sd:dot p1 (* 0.8 sc) "SD-KYHIEU")
      (sd:line p1 p2 "SD-KYHIEU")
      (entmake (list '(0 . "CIRCLE") '(8 . "SD-KYHIEU") (cons 10 c) (cons 40 r)
                     (list -3 (list "SD_REBAR" (cons 1000 mk) (cons 1070 n)
                                    (cons 1040 d) (cons 1040 len) (cons 1070 k)
                                    (cons 1000 shp) (cons 1000 (sd:nums->str prm))
                                    (cons 1000 (sd:nums->str pcs))))))
      (sd:ck-tag (entlast) *SD:LCK*)
      (sd:text c mk (* 2.5 sc) "MC" "SD-CHU")
      (sd:line (sd:p+ c (* sg r) 0) (sd:p+ c (* sg (+ r tl)) 0) "SD-KYHIEU")
      (sd:text (sd:p+ c (* sg (+ r sc)) (* 0.8 sc)) txt (* 2.5 sc) (if (> sg 0) "L" "R") "SD-CHU")
      (if pcs
        (sd:text (sd:p+ c (* sg (+ r sc)) (* -3.3 sc))
                 (strcat "N\\U+1ED1i: " (sd:pcs-str pcs "\\U+00D7") " (lap " (sd:num lap) ")")
                 (* 2.0 sc) (if (> sg 0) "L" "R") "SD-CHU"))
      (if (wcmatch mk "#*") (setq *SD:MARK* (1+ (atoi mk))))))
  (sd:finish))

;;; --------------------------------------------------------------------------
;;;  Doc du lieu thep tu ban ve
;;;  ban ghi: (so-hieu SL/CK d L soCK hinh-dang (kich-thuoc) (doan-cat))
;;; --------------------------------------------------------------------------
(defun sd:mk< (a b)
  (if (and (wcmatch a "#*") (wcmatch b "#*") (/= (atoi a) (atoi b)))
    (< (atoi a) (atoi b))
    (< a b)))

(defun sd:select-rebars (/ flt ss)
  (setq flt '((0 . "CIRCLE") (-3 ("SD_REBAR"))))
  (princ "\nChon cac ky hieu thep (tao bang SDTHEP) <Enter = tat ca trong ban ve>: ")
  (cond ((ssget flt)) ((ssget "_X" flt))))

(defun sd:xd->rec (xd)
  (list (nth 0 xd) (nth 1 xd) (nth 2 xd) (nth 3 xd) (nth 4 xd)
        (cond ((nth 5 xd)) ("Thang"))
        (cond ((sd:str->nums (nth 6 xd))) ((list (nth 3 xd))))
        (sd:str->nums (nth 7 xd))))

(defun sd:same-rec (a b)
  (and (= (nth 0 a) (nth 0 b)) (= (nth 1 a) (nth 1 b)) (= (nth 5 a) (nth 5 b))
       (equal (nth 2 a) (nth 2 b) 1e-6) (equal (nth 3 a) (nth 3 b) 1e-6)
       (equal (nth 6 a) (nth 6 b) 1e-6) (equal (nth 7 a) (nth 7 b) 1e-6)))

;; Ky hieu thep thong minh (SDTHEPTM) co thanh thep da bi xoa -> bo qua khi thong ke
(defun sd:tm-orphan-p (xd / e)
  (and (= (nth 8 xd) "TM") (/= (nth 9 xd) "")
       (not (and (setq e (handent (nth 9 xd))) (entget e)))))

(defun sd:read-rebars (ss / i rec old data xd)
  (setq i 0)
  (repeat (sslength ss)
    (setq xd  (mapcar 'cdr (cdadr (assoc -3 (entget (ssname ss i) '("SD_REBAR")))))
          rec (sd:xd->rec xd)
          i   (1+ i))
    (cond
      ((sd:tm-orphan-p xd))
      ((setq old (vl-some '(lambda (x) (if (sd:same-rec x rec) x)) data))
       (setq data (subst (list (nth 0 old) (nth 1 old) (nth 2 old) (nth 3 old)
                               (+ (nth 4 old) (nth 4 rec)) (nth 5 old) (nth 6 old) (nth 7 old))
                         old data)))
      (t (setq data (cons rec data)))))
  (sd:sort data '(lambda (a b) (sd:mk< (car a) (car b)))))

;; Tach ban ghi thanh cac dong bang: thanh noi chong -> 1a, 1b... (thang)
;; dong: (so-hieu hinh-dang (kich-thuoc) d L SL/CK soCK)
(defun sd:rec-rows (r / i rows)
  (if (nth 7 r)
    (progn
      (setq i 0)
      (foreach g (sd:group (nth 7 r))
        (setq rows (cons (list (strcat (nth 0 r) (chr (+ 97 i))) "Thang" (list (car g))
                               (nth 2 r) (car g) (* (nth 1 r) (cdr g)) (nth 4 r))
                         rows)
              i (1+ i)))
      (reverse rows))
    (list (list (nth 0 r) (nth 5 r) (nth 6 r) (nth 2 r) (nth 3 r) (nth 1 r) (nth 4 r)))))

;;; --------------------------------------------------------------------------
;;;  Bang tong quat
;;;  rows: ("R" (o...) (hinh-dang kich-thuoc)|nil) | ("S" chu gia-tri) | ("W" chu)
;;; --------------------------------------------------------------------------
(defun sd:table2 (pt title cols rows shpcol sc / W xs th y rh c)
  (setq W  (* sc (apply '+ (mapcar 'cadr cols)))
        xs (sd:cumul (mapcar '(lambda (x) (* sc (cadr x))) cols))
        th (* 2.2 sc) y 0.0)
  (sd:text (sd:p+ pt (/ W 2) (* 4 sc)) title (* 4.0 sc) "MC" "SD-CHU")
  (sd:line pt (sd:p+ pt W 0) "SD-BANG")
  (foreach r (cons (list "H" (mapcar 'car cols) nil) rows)
    (setq rh (* sc (if (and (= (car r) "R") (caddr r)) 12.0 8.0)))
    (foreach x (cond ((member (car r) '("H" "R")) xs)
                     ((= (car r) "S") (list (car xs) (cadr (reverse xs)) (last xs)))
                     (t (list (car xs) (last xs))))
      (sd:line (sd:p+ pt x y) (sd:p+ pt x (- y rh)) "SD-BANG"))
    (cond ((member (car r) '("H" "R"))
           (setq c 0)
           (foreach s (cadr r)
             (if (and (= c shpcol) (caddr r))
               (sd:draw-shape (car (caddr r)) (cadr (caddr r))
                              (sd:p+ pt (+ (nth c xs) (* 6 sc)) (+ (- y rh) (* 2.5 sc)))
                              (- (nth (1+ c) xs) (nth c xs) (* 12 sc)) (- rh (* 5 sc)) sc)
               (sd:text (sd:p+ pt (/ (+ (nth c xs) (nth (1+ c) xs)) 2) (- y (/ rh 2)))
                        s th "MC" "SD-CHU"))
             (setq c (1+ c))))
          ((= (car r) "S")
           (sd:text (sd:p+ pt (* 2 sc) (- y (/ rh 2))) (cadr r) th "ML" "SD-CHU")
           (sd:text (sd:p+ pt (/ (+ (cadr (reverse xs)) (last xs)) 2) (- y (/ rh 2)))
                    (caddr r) th "MC" "SD-CHU"))
          (t (sd:text (sd:p+ pt (* 2 sc) (- y (/ rh 2))) (cadr r) th "ML" "SD-CHU")))
    (setq y (- y rh))
    (sd:line (sd:p+ pt 0 y) (sd:p+ pt W y) "SD-BANG")))

;; ---- Doc / ghi file co duong dan Unicode (thu muc / ten ban ve co chu tieng Viet co dau)
;; Ham open cua AutoLISP khong mo duoc duong dan co ky tu ngoai bang ma ANSI -> ghi / doc qua file tam
;; ten ASCII trong %TEMP%, chep qua lai bang Scripting.FileSystemObject (ho tro Unicode).
(defun sd:fso-do (meth args / fso r)
  (setq r (vl-catch-all-apply
            '(lambda ()
               (setq fso (vlax-create-object "Scripting.FileSystemObject"))
               (sd:invoke-list fso meth args))
            nil))
  (if fso (vl-catch-all-apply 'vlax-release-object (list fso)))
  (if (vl-catch-all-error-p r) nil (if (null r) t r)))
(defun sd:invoke-list (obj meth args) (apply 'vlax-invoke-method (append (list obj meth) args)))
(defun sd:fexists (fn) (or (findfile fn) (eq (sd:fso-do 'FileExists (list fn)) :vlax-true)))
(defun sd:fcopy (src dst) (sd:fso-do 'CopyFile (list src dst :vlax-true)))
(defun sd:tmpname (fn / ext)
  (setq ext (cond ((vl-filename-extension fn)) (".txt")))
  (vl-filename-mktemp "sdfile" nil ext))
;; Mo file (mode "r" / "w" / "a"); ghi nho (handle ten-that file-tam) de sd:close chep ve
(defun sd:open (fn mode / f tmp)
  (cond
    ((setq f (open fn mode)) (setq *SD:FOPEN* (cons (list f fn nil mode) *SD:FOPEN*)) f)
    ((and (setq tmp (sd:tmpname fn))
          (or (= mode "w") (not (sd:fexists fn)) (sd:fcopy fn tmp))
          (if (= mode "r") (sd:fexists fn) t)
          (setq f (open tmp mode)))
     (setq *SD:FOPEN* (cons (list f fn tmp mode) *SD:FOPEN*))
     f)))
;; Dong file; tra ve duong dan file ket qua (ten that, hoac file tam neu khong chep ve duoc)
(defun sd:close (f / e r)
  (close f)
  (setq e (assoc f *SD:FOPEN*) *SD:FOPEN* (vl-remove e *SD:FOPEN*))
  (cond ((null e) nil)
        ((null (caddr e)) (cadr e))
        ((= (nth 3 e) "r") (cadr e))
        ((sd:fcopy (caddr e) (cadr e)) (cadr e))
        (t (princ (strcat "\n[SD] Khong chep duoc ve " (cadr e) " (file dang mo?) - ket qua o: " (caddr e)))
           (caddr e))))

;; Chuoi bo dau tieng Viet (ky tu ngoai ASCII khong co trong bang -> "_")
(setq *SD:VNMAP* '((768 . "") (769 . "") (770 . "") (771 . "") (772 . "") (773 . "") (774 . "") (775 . "") (776 . "") (777 . "") (778 . "") (779 . "") (780 . "") (781 . "") (782 . "") (783 . "") (784 . "") (785 . "") (786 . "") (787 . "") (788 . "") (789 . "") (790 . "") (791 . "") (792 . "") (793 . "") (794 . "") (795 . "") (796 . "") (797 . "") (798 . "") (799 . "") (800 . "") (801 . "") (802 . "") (803 . "") (804 . "") (805 . "") (806 . "") (807 . "") (808 . "") (809 . "") (810 . "") (811 . "") (812 . "") (813 . "") (814 . "") (815 . "") (816 . "") (817 . "") (818 . "") (819 . "") (820 . "") (821 . "") (822 . "") (823 . "") (824 . "") (825 . "") (826 . "") (827 . "") (828 . "") (829 . "") (830 . "") (831 . "") (832 . "") (833 . "") (834 . "") (835 . "") (836 . "") (837 . "") (838 . "") (839 . "") (840 . "") (841 . "") (842 . "") (843 . "") (844 . "") (845 . "") (846 . "") (847 . "") (848 . "") (849 . "") (850 . "") (851 . "") (852 . "") (853 . "") (854 . "") (855 . "") (856 . "") (857 . "") (858 . "") (859 . "") (860 . "") (861 . "") (862 . "") (863 . "") (864 . "") (865 . "") (866 . "") (867 . "") (868 . "") (869 . "") (870 . "") (871 . "") (872 . "") (873 . "") (874 . "") (875 . "") (876 . "") (877 . "") (878 . "") (879 . "") (192 . "A") (193 . "A") (194 . "A") (195 . "A") (196 . "A") (197 . "A") (199 . "C") (200 . "E") (201 . "E") (202 . "E") (203 . "E") (204 . "I") (205 . "I") (206 . "I") (207 . "I") (209 . "N") (210 . "O") (211 . "O") (212 . "O") (213 . "O") (214 . "O") (217 . "U") (218 . "U") (219 . "U") (220 . "U") (221 . "Y") (224 . "a") (225 . "a") (226 . "a") (227 . "a") (228 . "a") (229 . "a") (231 . "c") (232 . "e") (233 . "e") (234 . "e") (235 . "e") (236 . "i") (237 . "i") (238 . "i") (239 . "i") (241 . "n") (242 . "o") (243 . "o") (244 . "o") (245 . "o") (246 . "o") (249 . "u") (250 . "u") (251 . "u") (252 . "u") (253 . "y") (255 . "y") (256 . "A") (257 . "a") (258 . "A") (259 . "a") (260 . "A") (261 . "a") (262 . "C") (263 . "c") (264 . "C") (265 . "c") (266 . "C") (267 . "c") (268 . "C") (269 . "c") (270 . "D") (271 . "d") (272 . "D") (273 . "d") (274 . "E") (275 . "e") (276 . "E") (277 . "e") (278 . "E") (279 . "e") (280 . "E") (281 . "e") (282 . "E") (283 . "e") (284 . "G") (285 . "g") (286 . "G") (287 . "g") (288 . "G") (289 . "g") (290 . "G") (291 . "g") (292 . "H") (293 . "h") (296 . "I") (297 . "i") (298 . "I") (299 . "i") (300 . "I") (301 . "i") (302 . "I") (303 . "i") (304 . "I") (308 . "J") (309 . "j") (310 . "K") (311 . "k") (313 . "L") (314 . "l") (315 . "L") (316 . "l") (317 . "L") (318 . "l") (323 . "N") (324 . "n") (325 . "N") (326 . "n") (327 . "N") (328 . "n") (332 . "O") (333 . "o") (334 . "O") (335 . "o") (336 . "O") (337 . "o") (340 . "R") (341 . "r") (342 . "R") (343 . "r") (344 . "R") (345 . "r") (346 . "S") (347 . "s") (348 . "S") (349 . "s") (350 . "S") (351 . "s") (352 . "S") (353 . "s") (354 . "T") (355 . "t") (356 . "T") (357 . "t") (360 . "U") (361 . "u") (362 . "U") (363 . "u") (364 . "U") (365 . "u") (366 . "U") (367 . "u") (368 . "U") (369 . "u") (370 . "U") (371 . "u") (372 . "W") (373 . "w") (374 . "Y") (375 . "y") (376 . "Y") (377 . "Z") (378 . "z") (379 . "Z") (380 . "z") (381 . "Z") (382 . "z") (416 . "O") (417 . "o") (431 . "U") (432 . "u") (461 . "A") (462 . "a") (463 . "I") (464 . "i") (465 . "O") (466 . "o") (467 . "U") (468 . "u") (469 . "U") (470 . "u") (471 . "U") (472 . "u") (473 . "U") (474 . "u") (475 . "U") (476 . "u") (478 . "A") (479 . "a") (480 . "A") (481 . "a") (486 . "G") (487 . "g") (488 . "K") (489 . "k") (490 . "O") (491 . "o") (492 . "O") (493 . "o") (496 . "j") (500 . "G") (501 . "g") (504 . "N") (505 . "n") (506 . "A") (507 . "a") (512 . "A") (513 . "a") (514 . "A") (515 . "a") (516 . "E") (517 . "e") (518 . "E") (519 . "e") (520 . "I") (521 . "i") (522 . "I") (523 . "i") (524 . "O") (525 . "o") (526 . "O") (527 . "o") (528 . "R") (529 . "r") (530 . "R") (531 . "r") (532 . "U") (533 . "u") (534 . "U") (535 . "u") (536 . "S") (537 . "s") (538 . "T") (539 . "t") (542 . "H") (543 . "h") (550 . "A") (551 . "a") (552 . "E") (553 . "e") (554 . "O") (555 . "o") (556 . "O") (557 . "o") (558 . "O") (559 . "o") (560 . "O") (561 . "o") (562 . "Y") (563 . "y") (7840 . "A") (7841 . "a") (7842 . "A") (7843 . "a") (7844 . "A") (7845 . "a") (7846 . "A") (7847 . "a") (7848 . "A") (7849 . "a") (7850 . "A") (7851 . "a") (7852 . "A") (7853 . "a") (7854 . "A") (7855 . "a") (7856 . "A") (7857 . "a") (7858 . "A") (7859 . "a") (7860 . "A") (7861 . "a") (7862 . "A") (7863 . "a") (7864 . "E") (7865 . "e") (7866 . "E") (7867 . "e") (7868 . "E") (7869 . "e") (7870 . "E") (7871 . "e") (7872 . "E") (7873 . "e") (7874 . "E") (7875 . "e") (7876 . "E") (7877 . "e") (7878 . "E") (7879 . "e") (7880 . "I") (7881 . "i") (7882 . "I") (7883 . "i") (7884 . "O") (7885 . "o") (7886 . "O") (7887 . "o") (7888 . "O") (7889 . "o") (7890 . "O") (7891 . "o") (7892 . "O") (7893 . "o") (7894 . "O") (7895 . "o") (7896 . "O") (7897 . "o") (7898 . "O") (7899 . "o") (7900 . "O") (7901 . "o") (7902 . "O") (7903 . "o") (7904 . "O") (7905 . "o") (7906 . "O") (7907 . "o") (7908 . "U") (7909 . "u") (7910 . "U") (7911 . "u") (7912 . "U") (7913 . "u") (7914 . "U") (7915 . "u") (7916 . "U") (7917 . "u") (7918 . "U") (7919 . "u") (7920 . "U") (7921 . "u") (7922 . "Y") (7923 . "y") (7924 . "Y") (7925 . "y") (7926 . "Y") (7927 . "y") (7928 . "Y") (7929 . "y")))
(defun sd:ascii-name (s / i c r e)
  (setq r "" i 1)
  (while (<= i (strlen s))
    (setq c (ascii (substr s i 1))
          r (strcat r (cond ((< c 128) (chr c)) ((setq e (assoc c *SD:VNMAP*)) (cdr e)) ("_")))
          i (1+ i)))
  r)
(defun sd:non-ascii-p (s / i r)
  (setq i 1)
  (while (and (not r) (<= i (strlen s)))
    (if (> (ascii (substr s i 1)) 127) (setq r t))
    (setq i (1+ i)))
  r)
;; Ten file xuat canh ban ve. Duong dan co chu co dau (AutoLISP open khong ghi duoc) ->
;; thu muc khong dau <o dia>:\ShopDrawing_Xuat\ + ten ban ve bo dau
(defun sd:csv-name (suffix / pre nm dir)
  (setq pre (getvar "DWGPREFIX") nm (vl-filename-base (getvar "DWGNAME")))
  (if (not (sd:non-ascii-p (strcat pre nm)))
    (strcat pre nm suffix)
    (progn
      (setq dir (if (wcmatch pre "?:\\*") (strcat (substr pre 1 3) "ShopDrawing_Xuat") (strcat (getenv "TEMP") "\\ShopDrawing_Xuat")))
      (vl-mkdir dir)
      (if (not *SD:XUATNOTE*)
        (progn (setq *SD:XUATNOTE* t)
               (princ (strcat "\n[SD] Thu muc / ten ban ve co chu co dau: AutoCAD khong ghi file vao do duoc, file xuat luu tai " dir "\\"))))
      (strcat dir "\\" (sd:ascii-name nm) suffix))))

;;; --------------------------------------------------------------------------
;;;  Bang thong ke cot thep: du lieu, ve bang, CSV, bang tu cap nhat
;;; --------------------------------------------------------------------------
;; Du lieu bang tu cac ban ghi thep -> (rows dsum tot spliced)
;; row: (SH hinh-dang kich-thuoc DK L SL/CK soCK tongSL tongdai KL (kich-thuoc-so))
(defun sd:tk-data (data / rows tot w tl dsum rec spliced)
  (setq tot 0.0)
  (foreach r data
    (if (nth 7 r) (setq spliced t))
    ;; x = (so-hieu hinh-dang (kich-thuoc) d L SL/CK soCK)
    (foreach x (sd:rec-rows r)
      (setq tl  (/ (* (nth 4 x) (nth 5 x) (nth 6 x)) 1000.0)
            w   (* tl 0.00617 (nth 3 x) (nth 3 x))
            tot (+ tot w))
      (setq rows (cons (list (nth 0 x) (nth 1 x) (sd:join (mapcar 'sd:num (nth 2 x)) "/")
                             (sd:num (nth 3 x)) (sd:rtos (nth 4 x) 0) (itoa (nth 5 x))
                             (itoa (nth 6 x)) (itoa (* (nth 5 x) (nth 6 x)))
                             (sd:rtos tl 2) (sd:rtos w 2) (nth 2 x))
                       rows))
      (if (setq rec (assoc (nth 3 x) dsum))
        (setq dsum (subst (cons (car rec) (+ (cdr rec) w)) rec dsum))
        (setq dsum (cons (cons (nth 3 x) w) dsum)))))
  (list (reverse rows) (sd:sort dsum '(lambda (a b) (< (car a) (car b)))) tot spliced))

;; Ve bang thong ke tai pt (goc trai tren)
(defun sd:tk-table (pt tk sc / trows)
  (setq trows (mapcar '(lambda (r) (list "R" (list (nth 0 r) "" (nth 3 r) (nth 4 r) (nth 5 r)
                                                   (nth 6 r) (nth 7 r) (nth 8 r) (nth 9 r))
                                         (list (nth 1 r) (nth 10 r))))
                      (car tk)))
  (foreach x (cadr tk)
    (setq trows (append trows (list (list "S" (strcat "T\\U+1ED5ng %%c" (sd:num (car x))) (sd:rtos (cdr x) 2))))))
  (setq trows (append trows (list (list "S" "T\\U+1ED4NG C\\U+1ED8NG" (sd:rtos (caddr tk) 2)))))
  (if (cadddr tk)
    (setq trows (append trows (list (list "W" (strcat "Thanh 1a, 1b...: \\U+0111o\\U+1EA1n c\\U+1EAFt c\\U+1EE7a thanh n\\U+1ED1i ch\\U+1ED3ng; lap theo "
                                                      (sd:lapinfo) "; n\\U+1ED1i so le, <= 50% thanh / ti\\U+1EBFt di\\U+1EC7n."))))))
  (sd:table2 pt "B\\U+1EA2NG TH\\U+1ED0NG K\\U+00CA C\\U+1ED0T TH\\U+00C9P"
             '(("SH" 12) ("H\\U+00CCNH D\\U+1EA0NG" 46) ("\\U+0110K" 12) ("D\\U+00C0I (mm)" 18) ("SL/CK" 13)
               ("S\\U+1ED0 CK" 13) ("T\\U+1ED4NG SL" 16) ("T\\U+1ED4NG D\\U+00C0I (m)" 22) ("KL (kg)" 18))
             trows 1 sc))

(defun sd:tk-csv (tk / fn f)
  (setq fn (sd:csv-name "_ThongKeThep.csv"))
  (if (setq f (sd:open fn "w"))
    (progn
      (write-line "SH,Hinh dang,Kich thuoc (mm),DK(mm),Dai 1 thanh(mm),SL/CK,So CK,Tong SL,Tong dai(m),KL(kg)" f)
      (foreach r (car tk) (write-line (sd:join (reverse (cdr (reverse r))) ",") f))
      (foreach x (cadr tk) (write-line (strcat "Tong D" (sd:num (car x)) ",,,,,,,,," (sd:rtos (cdr x) 2)) f))
      (write-line (strcat "TONG CONG,,,,,,,,," (sd:rtos (caddr tk) 2)) f)
      (setq fn (sd:close f))
      (princ (strcat "\n[SD] Da xuat: " fn)))))

;; Ve bang va tra ve danh sach handle cac doi tuong vua tao
(defun sd:tk-draw (pt tk sc / e0 e hs)
  (setq e0 (entlast))
  (sd:tk-table pt tk sc)
  (setq e (if e0 (entnext e0) (entnext)))
  (while e (setq hs (cons (cdr (assoc 5 (entget e))) hs) e (entnext e)))
  hs)

;; Bang tu cap nhat: ldata "SD" "TKAUTO" = (diem ty-le layout (handle...) chu-ky)
;; chu-ky = noi dung cac dong bang; chi ve lai khi noi dung thay doi (hoac force)
(defun sd:tk-all (/ ss) (if (setq ss (ssget "_X" '((0 . "CIRCLE") (-3 ("SD_REBAR"))))) (sd:tk-data (sd:read-rebars ss))))
(defun sd:tk-sig (tk) (vl-prin1-to-string (list (car tk) (cadr tk))))

(defun sd:tk-refresh (force / a e tk sig)
  (if (and (setq a (vlax-ldata-get "SD" "TKAUTO")) (= (caddr a) (getvar "CTAB")))
    (progn
      (setq tk (sd:tk-all) sig (sd:tk-sig tk))
      (if (or force (/= sig (nth 4 a)))
        (progn
          (foreach h (cadddr a) (if (and (setq e (handent h)) (entget e)) (entdel e)))
          (vlax-ldata-put "SD" "TKAUTO"
                          (list (car a) (cadr a) (caddr a) (if (car tk) (sd:tk-draw (car a) tk (cadr a))) sig))
          t)))))

;;; --------------------------------------------------------------------------
;;;  SDTKTHEP - Bang thong ke cot thep (co hinh dang) + xuat CSV
;;;  Pham vi "Toan ban ve" + tu cap nhat: bang ve lai khi thep thong minh (SDTHEPTM) thay doi
;;; --------------------------------------------------------------------------
(defun c:SDTKTHEP (/ ss tk pt flt all)
  (sd:begin)
  (sd:tag-sync-all)
  (sd:tm-dup-report)
  (if (not (sd:dlg "Bang thong ke cot thep (SDTKTHEP)"
                   (list (list "pv" "Pham vi thong ke" 'kw "Tatca"
                               '(("Tatca" . "Toan ban ve") ("Chon" . "Chon ky hieu tren ban ve")))
                         (list "auto" "Tu cap nhat khi thep thong minh thay doi" 'tog t nil '("pv" "Tatca"))
                         (list "csv" "Xuat file CSV canh file ban ve" 'tog t))))
    (exit))
  (setq flt '((0 . "CIRCLE") (-3 ("SD_REBAR"))) all (= (sd:v "pv") "Tatca"))
  (if (not (setq ss (if all
                      (ssget "_X" flt)
                      (progn (princ "\nChon cac ky hieu thep (SDTHEP / SDTHEPTM): ") (ssget flt)))))
    (princ "\n[SD] Khong tim thay ky hieu thep nao (dung lenh SDTHEP hoac SDTHEPTM de tao).")
    (progn
      (setq tk (sd:tk-data (sd:read-rebars ss)))
      (if (setq pt (sd:getpt "\nDiem chen bang (goc trai tren): " nil))
        (progn
          (setq pt (sd:w pt))
          (if (and all (sd:v "auto"))
            (progn
              (setq tk (sd:tk-all))
              (vlax-ldata-put "SD" "TKAUTO" (list pt (sd:sc) (getvar "CTAB") (sd:tk-draw pt tk (sd:sc)) (sd:tk-sig tk)))
              (princ "\n[SD] Bang tu cap nhat: ve lai khi thep thong minh thay doi (bang tu cap nhat cu, neu co, thanh bang tinh)."))
            (sd:tk-table pt tk (sd:sc)))))
      (if (sd:v "csv") (sd:tk-csv tk))
      (princ (strcat "\n[SD] " (itoa (length (car tk))) " dong thep, tong khoi luong = "
                     (sd:rtos (caddr tk) 2) " kg."))))
  (sd:finish))

;;; --------------------------------------------------------------------------
;;;  SDTHEPTM - Thep thong minh (AutoRebar): polyline -> thanh thep tu cap nhat
;;;  Ky hieu (CIRCLE) giu XDATA "SD_REBAR" nhu SDTHEP, them:
;;;    "TM", handle thanh thep, handle chu ghi chu, kieu SL (0 co dinh / 1 rai), a, [handle duong phan bo]
;;;  Reactor: polyline / duong phan bo thay doi (STRETCH, grip, MOVE dinh...) -> cuoi lenh tinh lai
;;;  hinh dang, L, noi chong, so thanh; sua chu ghi chu va ve lai bang thong ke tu cap nhat.
;;; --------------------------------------------------------------------------
;; Dinh cua thanh thep -> (diem... ) va co khep kin
(defun sd:tm-pts (e / ed typ pts cl)
  (setq ed (entget e) typ (cdr (assoc 0 ed)))
  (cond ((= typ "LWPOLYLINE")
         (foreach g ed (if (= (car g) 10) (setq pts (cons (cdr g) pts))))
         (setq pts (reverse pts) cl (= 1 (logand 1 (cdr (assoc 70 ed))))))
        ((= typ "LINE") (setq pts (list (cdr (assoc 10 ed)) (cdr (assoc 11 ed))))))
  (if (and (not cl) (> (length pts) 3) (< (distance (car pts) (last pts)) 1e-3))
    (setq cl t pts (reverse (cdr (reverse pts)))))
  (list pts cl))

;; z cua tich co huong (b - a) x (c - b)
(defun sd:turn (a b c)
  (- (* (- (car b) (car a)) (- (cadr c) (cadr b))) (* (- (cadr b) (cadr a)) (- (car c) (car b)))))

;; Nhan dang hinh dang tu polyline -> (ma (kich-thuoc))
(defun sd:tm-shape (e / pl pts sg xs ys)
  (setq pl (sd:tm-pts e) pts (car pl))
  (setq sg (mapcar 'distance pts (append (cdr pts) (if (cadr pl) (list (car pts))))))
  (if (not (cadr pl)) (setq sg (sd:head (1- (length pts)) sg)))
  (cond
    ((cadr pl)                                         ; khep kin -> dai
     (if (= (length pts) 4)
       (list "Dai" (list (nth 0 sg) (nth 1 sg)))
       (progn (setq xs (mapcar 'car pts) ys (mapcar 'cadr pts))
              (list "Dai" (list (- (apply 'max xs) (apply 'min xs)) (- (apply 'max ys) (apply 'min ys)))))))
    ((= (length pts) 3) (list "L" (list (max (car sg) (cadr sg)) (min (car sg) (cadr sg)))))
    ((= (length pts) 4)
     (list (if (> (* (sd:turn (nth 0 pts) (nth 1 pts) (nth 2 pts)) (sd:turn (nth 1 pts) (nth 2 pts) (nth 3 pts))) 0)
             "U" "Z")
           sg))
    (t (list "Thang" (list (sd:len e))))))          ; thang, cung, nhieu doan: chieu dai trien khai

;; Hinh dang + kich thuoc lam tron mm (thong ke)
(defun sd:tm-shape-r (e / sp)
  (setq sp (sd:tm-shape e))
  (list (car sp) (mapcar '(lambda (x) (float (fix (+ x 0.5)))) (cadr sp))))

;; nm: 0 co dinh, 1 rai deu (a), 2 dai theo vung (spec "LOAI|so lieu|ghi chu")
(defun sd:tm-label (n d a nm len pcs k / sp)
  (strcat (itoa n) "%%c" (sd:num d)
          (cond ((= nm 1) (strcat " a" (sd:num a)))
                ((and (= nm 2) (= (type a) 'STR) (setq sp (sd:split a "|")) (caddr sp)) (strcat " " (caddr sp)))
                (""))
          " L=" (sd:rtos len 0)
          (if pcs " (n\\U+1ED1i)" "") (if (> k 1) (strcat " (\\U+00D7" (itoa k) " CK)") "")))

;; handle -> ename neu doi tuong con (AutoLISP: and chi tra ve T, nen dung if)
(defun sd:ent-ok (h / e) (if (and h (setq e (handent h)) (entget e)) e))

;; Bo n phan tu dau danh sach
(defun sd:drop (n l) (repeat n (setq l (cdr l))) l)

;; Vi tri dai cot (tu cao do san): vung toi han lz chan / dinh buoc a1, giua a2, trong nut dam (cao hd) buoc a1
(defun sd:col-zone-ys (hn hd c a1 a2 lz / ys y so)
  (setq y 50.0)
  (while (<= y lz) (setq ys (cons y ys) y (+ y a1)))
  (setq so (car ys) y (- hn 50.0))
  (while (and (>= y (- hn lz)) (> y (+ so (* 0.5 a1)))) (setq ys (cons y ys) y (- y a1)))
  (setq y (+ so a2))
  (while (< y (- hn lz (* 0.5 a2))) (setq ys (cons y ys) y (+ y a2)))
  (setq y (+ hn 50.0))
  (while (< y (- (+ hn hd) c)) (setq ys (cons y ys) y (+ y a1)))
  ys)
(defun sd:col-lz (b h hn) (sd:ceil (max b h (/ hn 6.0) 450.0) 50.0))

;; Vi tri dai 1 nhip dam (tinh tu mep goi trai, nhip thong thuy ln): Ln/4 hai dau buoc a1, giua a2
;; -> (trai giua phai)
(defun sd:beam-zone-ys (ln a1 a2 / lz x left right mid)
  (setq lz (* 0.25 ln) x 50.0)
  (while (<= x lz) (setq left (cons x left) x (+ x a1)))
  (setq x (- ln 50.0))
  (while (and (>= x (- ln lz)) (> x (+ (car left) (* 0.5 a1)))) (setq right (cons x right) x (- x a1)))
  (setq x (+ (car left) a2))
  (while (< x (- (car right) (* 0.5 a2))) (setq mid (cons x mid) x (+ x a2)))
  (list left mid right))

;; So dai theo vung tu chieu dai cac duong phan bo. spec "COT|m,hd,c,a1,a2,b,h|ghi chu" (lens = (hn))
;; hoac "DAM|m,a1,a2|ghi chu" (lens = nhip thong thuy tung nhip); m = so dai moi lop
(defun sd:zone-n (spec lens / sp v n)
  (setq sp (sd:split spec "|") v (sd:str->nums (cadr sp)))
  (cond
    ((= (car sp) "COT")
     (* (fix (nth 0 v))
        (length (sd:col-zone-ys (car lens) (nth 1 v) (nth 2 v) (nth 3 v) (nth 4 v) (sd:col-lz (nth 5 v) (nth 6 v) (car lens))))))
    ((= (car sp) "DAM")
     (setq n 0)
     (foreach ln lens (setq n (+ n (length (apply 'append (sd:beam-zone-ys ln (nth 1 v) (nth 2 v)))))))
     (* (fix (nth 0 v)) n))))

;; Tinh lai 1 ky hieu thong minh; tra ve T neu co thay doi
;; XDATA thong minh: 8 "TM", 9 handle thanh ("" = khong gan hinh, giu hinh dang da luu), 10 chu, 11 nm, 12 a,
;; 13 handle duong phan bo, 14 spec (nm = 2), 15.. handle duong phan bo them (nhieu nhip)
(defun sd:tm-update (tag / ed xd raw bar dist d n k nm a sp len pcs new txt te dl lens)
  (setq ed (entget tag '("SD_REBAR")) raw (cdadr (assoc -3 ed)) xd (mapcar 'cdr raw))
  (if (and (= (nth 8 xd) "TM") (or (= (nth 9 xd) "") (setq bar (sd:ent-ok (nth 9 xd)))))
    (progn
      (setq d (nth 2 xd) k (nth 4 xd) nm (nth 11 xd) a (nth 12 xd) dist (sd:ent-ok (nth 13 xd))
            dl (if (nth 13 xd) (mapcar 'sd:ent-ok (cons (nth 13 xd) (sd:drop 15 xd))))
            n (cond ((and (= nm 1) dist (> a 0)) (1+ (fix (+ (/ (sd:len dist) a) 1e-6))))
                    ((and (= nm 2) dl (not (member nil dl)) (nth 14 xd))
                     (sd:zone-n (nth 14 xd) (mapcar 'sd:len dl)))
                    ((nth 1 xd)))
            sp (if bar (sd:tm-shape-r bar) (list (nth 5 xd) (sd:str->nums (nth 6 xd))))
            len (sd:shape-len (car sp) (cadr sp) d)
            pcs (if (= (car sp) "Thang") (sd:splice len d)))
      (setq new (append (list (cons 1000 (nth 0 xd)) (cons 1070 n) (cons 1040 d) (cons 1040 len) (cons 1070 k)
                              (cons 1000 (car sp)) (cons 1000 (sd:nums->str (cadr sp))) (cons 1000 (sd:nums->str pcs))
                              (cons 1000 "TM") (nth 9 raw) (cons 1005 (nth 10 xd))
                              (cons 1070 nm) (cons 1040 a))
                        (if (nth 13 xd) (sd:drop 13 raw))))
      (if (not (equal (mapcar 'cdr new) xd 1e-6))
        (progn
          (entmod (append (vl-remove (assoc -3 ed) ed) (list (list -3 (cons "SD_REBAR" new)))))
          (setq txt (sd:tm-label n d (if (= nm 2) (nth 14 xd) a) nm len pcs k))
          (if (setq te (sd:ent-ok (nth 10 xd)))
            (entmod (subst (cons 1 txt) (assoc 1 (entget te)) (entget te))))
          t)))))

;; ---- Dong bo chu sua tay -> du lieu thep -------------------------------------------
;; Nguoi dung sua truc tiep chu so hieu trong vong tron (13 -> 13a) hoac chu ghi chu ("2%%c18 L=3700" -> "2%%c20 ...")
;; -> cap nhat XDATA SD_REBAR de bang thong ke / SDKL / toi uu cat dung theo chu tren ban ve.
;; Phan tich chu ghi chu: (n d L) (nil neu khong doc duoc), chap nhan %%c, O gach (Unicode), \U+00D8, \U+2205
(defun sd:num-at (s i / r c)
  (setq r "")
  (while (and (<= i (strlen s)) (or (wcmatch (setq c (substr s i 1)) "#") (and (= c ".") (/= r ""))))
    (setq r (strcat r c) i (1+ i)))
  (if (/= r "") (atof r)))
(defun sd:tag-parse (s / u p n d l)
  (setq u (strcase s))
  (foreach k (list "\\U+00D8" "\\U+2205" (chr 216) (chr 248)) (while (vl-string-search k u) (setq u (vl-string-subst "%%C" k u))))
  (setq n (sd:num-at (vl-string-left-trim " " u) 1))
  (if (setq p (vl-string-search "%%C" u)) (setq d (sd:num-at u (+ p 4))))
  (if (setq p (vl-string-search "L=" u)) (setq l (sd:num-at (vl-string-left-trim " " (substr u (+ p 3))) 1)))
  (if (and n d) (list (fix n) d l)))

;; Dong bo 1 ky hieu tu chu; tx = chi muc chu can giua (sd:bt-texts). Tra ve nil / T (da sua) / chuoi canh bao
(defun sd:tag-sync (tag tx / ed raw xd te mk lb new w ch)
  (setq ed (entget tag '("SD_REBAR")) raw (cdadr (assoc -3 ed)) xd (mapcar 'cdr raw) new raw)
  ;; so hieu trong vong tron
  (if (and (setq te (cdr (assoc (sd:bt-pkey (cond ((cdr (assoc 410 ed))) ("Model")) (cdr (assoc 10 ed))) tx)))
           (setq mk (vl-string-trim " " (cdr (assoc 1 (entget te)))))
           (/= mk "") (/= mk (nth 0 xd)))
    (setq new (cons (cons 1000 mk) (cdr new)) ch t))
  ;; chu ghi chu (thep thong minh: handle chu o vi tri 10)
  (if (and (= (nth 8 xd) "TM") (setq te (sd:ent-ok (nth 10 xd))) (setq lb (sd:tag-parse (cdr (assoc 1 (entget te))))))
    (progn
      (if (not (equal (cadr lb) (nth 2 xd) 1e-6))
        (setq new (sd:replace-nth 2 (cons 1040 (float (cadr lb))) new) ch t))
      (if (and (/= (car lb) (nth 1 xd)) (= (nth 11 xd) 0))
        (setq new (sd:replace-nth 1 (cons 1070 (car lb)) new) ch t))
      (if (and (caddr lb) (> (abs (- (caddr lb) (nth 3 xd))) 1.0) (equal (cadr lb) (nth 2 xd) 1e-6))
        (setq w (strcat "so hieu " (cdr (car new)) ": L=" (sd:num (caddr lb)) " sua tay khac chieu dai thanh ve ("
                        (sd:rtos (nth 3 xd) 0) ") - keo gian thanh thep tren ban ve thay vi sua chu")))))
  (if ch
    (progn
      (entmod (append (vl-remove (assoc -3 ed) ed) (list (list -3 (cons "SD_REBAR" new)))))
      (if (= (nth 8 xd) "TM") (sd:tm-update tag))))
  (cond (w) (ch)))

;; Dong bo moi ky hieu -> so ky hieu da sua; in canh bao
(defun sd:tag-sync-all (/ ss i tx n r)
  (setq n 0 i 0)
  (if (setq ss (ssget "_X" '((0 . "CIRCLE") (-3 ("SD_REBAR")))))
    (progn
      (setq tx (sd:bt-texts))
      (repeat (sslength ss)
        (setq r (sd:tag-sync (ssname ss i) tx) i (1+ i))
        (cond ((= r t) (setq n (1+ n)))
              ((= (type r) 'STR) (princ (strcat "\n[SD] Luu y " r ".")))))))
  (if (> n 0) (princ (strcat "\n[SD] Dong bo " (itoa n) " ky hieu thep theo chu sua tay tren ban ve.")))
  n)

;; Cac ky hieu thep thong minh dang gan vao thanh co handle h
(defun sd:tm-tags-of (h / r xd)
  (foreach tag (sd:tm-scan)
    (setq xd (mapcar 'cdr (cdadr (assoc -3 (entget tag '("SD_REBAR"))))))
    (if (= (nth 9 xd) h) (setq r (cons tag r))))
  r)
;; Canh bao thanh co nhieu ky hieu (moi ky hieu tinh 1 lan): ve trung bang SDTHEPTM tren thanh da co ky hieu
(defun sd:tm-dup-report (/ g xd o n)
  (foreach tag (sd:tm-scan)
    (setq xd (mapcar 'cdr (cdadr (assoc -3 (entget tag '("SD_REBAR"))))))
    (if (/= (nth 9 xd) "")
      (if (setq o (assoc (nth 9 xd) g))
        (setq g (subst (append o (list xd)) o g))
        (setq g (cons (list (nth 9 xd) xd) g)))))
  (setq n 0)
  (foreach x g
    (if (cddr x)
      (progn
        (setq n (1+ n))
        (princ (strcat "\n[!] 1 thanh thep co " (itoa (length (cdr x))) " ky hieu: "
                       (sd:join (mapcar '(lambda (y) (strcat (nth 0 y) " (" (itoa (nth 1 y)) "%%c" (sd:num (nth 2 y)) ")")) (cdr x)) ", ")
                       " -> dang tinh " (itoa (length (cdr x))) " lan. Neu khong phai cau kien dung chung thanh, xoa vong tron ky hieu thua.")))))
  n)

;; Gan reactor cho thanh thep / duong phan bo
(defun sd:tm-attach (e / o)
  (if (and e (not (member (cdr (assoc 5 (entget e))) *SD:TM-OWNED*)))
    (progn
      (setq o (vlax-ename->vla-object e) *SD:TM-OWNED* (cons (cdr (assoc 5 (entget e))) *SD:TM-OWNED*))
      (if *SD:TM-OR*
        (vlr-owner-add *SD:TM-OR* o)
        (setq *SD:TM-OR* (vlr-object-reactor (list o) "SD-TM"
                                             '((:vlr-modified . sd:tm-mod) (:vlr-erased . sd:tm-mod)
                                               (:vlr-unerased . sd:tm-mod))))))))

;; Quet ban ve: ban do handle (thanh / duong phan bo) -> ky hieu; tra ve danh sach ky hieu
(defun sd:tm-scan (/ ss i tag xd tags)
  (setq *SD:TM-MAP* nil i 0)
  (if (setq ss (ssget "_X" '((0 . "CIRCLE") (-3 ("SD_REBAR")))))
    (repeat (sslength ss)
      (setq tag (ssname ss i) i (1+ i) xd (mapcar 'cdr (cdadr (assoc -3 (entget tag '("SD_REBAR"))))))
      (if (= (nth 8 xd) "TM")
        (progn
          (setq tags (cons tag tags))
          (foreach h (append (list (nth 9 xd) (nth 13 xd)) (sd:drop 15 xd))
            (if (and h (/= h ""))
              (progn (setq *SD:TM-MAP* (cons (cons h tag) *SD:TM-MAP*))
                     (sd:tm-attach (sd:ent-ok h)))))))))
  tags)

;; Callback reactor (chi ghi nhan, khong sua doi tuong trong luc nay)
(defun sd:tm-mod (owner r p / h)
  (if (= (type (setq h (vl-catch-all-apply 'vla-get-Handle (list owner)))) 'STR)
    (setq *SD:TM-DIRTY* (cons h *SD:TM-DIRTY*))))

;; Cuoi lenh: cap nhat ky hieu bi anh huong + bang thong ke tu cap nhat
(defun sd:tm-flush (all / tags)
  (if all
    (setq tags (sd:tm-scan))
    (foreach h *SD:TM-DIRTY*
      (foreach m *SD:TM-MAP*
        (if (and (= (car m) h) (not (member (cdr m) tags))) (setq tags (cons (cdr m) tags))))))
  (setq *SD:TM-DIRTY* nil)
  (foreach tag tags (if (entget tag) (sd:tm-update tag)))
  ;; bang tu cap nhat: ve lai neu noi dung thong ke doi (ke ca sao chep / xoa ky hieu thuong)
  (sd:tk-refresh nil))

(defun sd:tm-cmd (r p / c)
  (setq c (strcase (car p)))
  (if (wcmatch c "*TEXTEDIT,DDEDIT,MTEDIT,*ATTEDIT,PROPERTIES*,MATCHPROP,FIND")
    (vl-catch-all-apply '(lambda () (if (> (sd:tag-sync-all) 0) (setq *SD:TM-DIRTY* (cons "SYNC" *SD:TM-DIRTY*)))) nil))
  (vl-catch-all-apply 'sd:tm-flush
                      (list (wcmatch c "*COPY*,*MIRROR*,*ARRAY*,PASTE*,U,UNDO,REDO,MREDO,OOPS,*INSERT*,EXPLODE,CHANGE"))))

(defun sd:tm-lisp (r p) (if *SD:TM-DIRTY* (vl-catch-all-apply 'sd:tm-flush (list nil))))

(defun sd:tm-init ()
  (if (not *SD:TM-CR*)
    (setq *SD:TM-CR* (vlr-command-reactor "SD-TM" '((:vlr-commandEnded . sd:tm-cmd) (:vlr-commandCancelled . sd:tm-cmd)
                                                   (:vlr-commandFailed . sd:tm-cmd)))))
  (if (not *SD:TM-LR*)
    (setq *SD:TM-LR* (vlr-lisp-reactor "SD-TM" '((:vlr-lispEnded . sd:tm-lisp)))))
  (sd:tm-scan))

;; Ve ky hieu thong minh: cham tren thanh, duong dan, vong tron so hieu, chu ghi chu
(defun sd:tm-tag (p1 p2 mk txt xd sc / r sg c tl te)
  (setq r (* 3.0 sc) sg (if (>= (car p2) (car p1)) 1.0 -1.0) c (sd:p+ p2 (* sg r) 0)
        tl (* sc (max 20.0 (* 1.9 (strlen txt)))))
  (sd:dot p1 (* 0.8 sc) "SD-KYHIEU")
  (sd:line p1 p2 "SD-KYHIEU")
  (sd:line (sd:p+ c (* sg r) 0) (sd:p+ c (* sg (+ r tl)) 0) "SD-KYHIEU")
  (sd:text (sd:p+ c (* sg (+ r sc)) (* 0.8 sc)) txt (* 2.5 sc) (if (> sg 0) "L" "R") "SD-CHU")
  (setq te (cdr (assoc 5 (entget (entlast)))))
  (entmake (list '(0 . "CIRCLE") '(8 . "SD-KYHIEU") (cons 10 c) (cons 40 r)
                 (list -3 (cons "SD_REBAR" (subst (cons 1005 te) '(1005 . "TXT") xd)))))
  (setq c (list (entlast) c))
  (sd:ck-tag (car c) *SD:CKNAME*)
  (sd:text (cadr c) mk (* 2.5 sc) "MC" "SD-CHU")
  (car c))

;; Ty le vung ve quanh diem c (mat cat 1/25 hay mat dung 1/100...): lay tu ky hieu thep SD gan nhat (r = 3.ty le)
;; hoac kich thuoc gan nhat (dimstyle SD-1-n / DIMSCALE cua dimstyle) trong o vuong +-dx. nil neu khong thay.
(defun sd:sc-pt (c dx / a b best d s ss i ed st)
  (setq a (list (- (car c) dx) (- (cadr c) dx) 0.0) b (list (+ (car c) dx) (+ (cadr c) dx) 0.0))
  (foreach flt (list '((0 . "CIRCLE") (-3 ("SD_REBAR"))) '((0 . "DIMENSION")))
    (if (setq ss (ssget "_C" (trans a 0 1) (trans b 0 1) flt))
      (progn
        (setq i 0)
        (repeat (sslength ss)
          (setq ed (entget (ssname ss i)) i (1+ i)
                s (if (= (cdr (assoc 0 ed)) "CIRCLE")
                    (/ (cdr (assoc 40 ed)) 3.0)
                    (progn (setq st (cdr (assoc 3 ed)))
                           (cond ((and st (wcmatch (strcase st) "SD-1-#*")) (atof (substr st 6)))
                                 ((and st (setq st (tblsearch "DIMSTYLE" st)) (cdr (assoc 40 st)))))))
                d (distance (list (car c) (cadr c)) (list (cadr (assoc 10 ed)) (caddr (assoc 10 ed)))))
          (if (and s (> s 0) (or (null best) (< d (car best)))) (setq best (list d s)))))))
  (if best (float (fix (+ (cadr best) 0.5)))))
;; Ty le vung ve quanh doi tuong e
(defun sd:sc-near (e / bb)
  (if (setq bb (sd:obj-bbox (vlax-ename->vla-object e)))
    (sd:sc-pt (mapcar '(lambda (p q) (/ (+ p q) 2.0)) (car bb) (cadr bb)) (max 500.0 (distance (car bb) (cadr bb))))))

(defun c:SDTHEPTM (/ op sc es bar de dist p1 p2 mk d nm n a k xd tag cnt ss i old kw ed)
  (sd:begin)
  (sd:tm-init)
  (if (not (sd:dlg "Thep thong minh (SDTHEPTM)"
                   (list (list "op" "Thao tac" 'kw "Tao"
                               '(("Tao" . "Tao thep thong minh tu polyline") ("Capnhat" . "Cap nhat tat ca + bang thong ke")
                                 ("Bo" . "Bo lien ket (thanh ky hieu thuong)")))
                         (list "mk" "So hieu thanh thep (tu tang)" 'str (itoa *SD:MARK*) nil '("op" "Tao"))
                         (list "d" "Duong kinh (mm)" 'real (cond (*SD:LD*) (16.0)) nil '("op" "Tao"))
                         (list "nm" "So thanh" 'kw (cond (*SD:TMNM*) ("Codinh"))
                               '(("Codinh" . "Co dinh") ("Rai" . "Rai theo khoang cach tren duong phan bo")) '("op" "Tao"))
                         (list "n" "So thanh trong 1 cau kien" 'int (cond (*SD:LN*) (2)) nil '("nm" "Codinh"))
                         (list "a" "Khoang cach rai a (mm)" 'real (cond (*SD:TMA*) (200.0)) nil '("nm" "Rai"))
                         (list "k" "So cau kien" 'int 1 nil '("op" "Tao"))
                         (list "ck" "Thuoc cau kien (de trong = khong)" 'str (cond (*SD:LCK*) ("")) nil '("op" "Tao"))
                         (list "tl" "Co ky hieu (ty le)" 'kw (cond (*SD:TMTL*) ("Tudong"))
                               (list '("Tudong" . "Tu dong theo vung ve (ky hieu / kich thuoc gan thanh thep)")
                                     (cons "Chinh" (strcat "Ty le chinh 1/" (itoa (fix (sd:sc)))))
                                     (cons "Chitiet" (strcat "Ty le chi tiet 1/" (itoa (fix *SD:DETSCALE*)))))
                               nil '("op" "Tao")))))
    (exit))
  (setq op (sd:v "op") sc (sd:sc) *SD:LCK* (sd:v "ck") *SD:CKNAME* (sd:v "ck") *SD:TMTL* (sd:v "tl"))
  (cond
    ((= op "Capnhat")
     (setq cnt 0)
     (foreach tag (sd:tm-scan) (if (sd:tm-update tag) (setq cnt (1+ cnt))))
     (sd:tk-refresh t)
     (princ (strcat "\n[SD] Da cap nhat " (itoa cnt) " ky hieu thep thong minh"
                    (if (vlax-ldata-get "SD" "TKAUTO") " va bang thong ke tu cap nhat." "."))))
    ((= op "Bo")
     (princ "\nChon ky hieu thep thong minh can bo lien ket: ")
     (if (setq ss (ssget '((0 . "CIRCLE") (-3 ("SD_REBAR")))))
       (progn
         (setq i 0 cnt 0)
         (repeat (sslength ss)
           (setq tag (entget (ssname ss i) '("SD_REBAR")) i (1+ i) xd (cdadr (assoc -3 tag)))
           (if (= (cdr (nth 8 xd)) "TM")
             (progn (entmod (append (vl-remove (assoc -3 tag) tag) (list (list -3 (cons "SD_REBAR" (sd:head 8 xd))))))
                    (setq cnt (1+ cnt)))))
         (sd:tm-scan)
         (princ (strcat "\n[SD] " (itoa cnt) " ky hieu da thanh ky hieu thuong (khong tu cap nhat).")))))
    (t
     (setq mk (sd:v "mk") d (sd:v "d") nm (if (= (sd:v "nm") "Rai") 1 0) n (sd:v "n") a (sd:v "a") k (sd:v "k")
           *SD:LD* d *SD:LN* n *SD:TMA* a *SD:TMNM* (sd:v "nm"))
     (while (setq es (entsel (strcat "\nChon polyline / line the hien thanh thep [" mk "] <Enter ket thuc>: ")))
       (setq bar (car es) dist nil)
       (cond
         ((not (member (cdr (assoc 0 (entget bar))) '("LWPOLYLINE" "LINE" "ARC")))
          (princ "\n[SD] Chi nhan LWPOLYLINE, LINE, ARC."))
         ((and (= nm 1)
               (not (and (setq de (entsel "\nChon duong phan bo (doan rai thep, vd truc dam): "))
                         (setq dist (car de)))))
          (princ "\n[SD] Can duong phan bo de rai thep."))
         ;; thanh da co ky hieu (SDDAMDUNG / lan truoc): cap nhat ky hieu cu thay vi tao them (tranh tinh trung)
         ((and (setq old (sd:tm-tags-of (cdr (assoc 5 (entget bar)))))
               (/= (setq kw (progn (initget "Capnhat Them Bo")
                                   (cond ((getkword (strcat "\nThanh nay da co ky hieu "
                                                            (sd:join (mapcar '(lambda (g) (cdr (cadr (cadr (assoc -3 (entget g '("SD_REBAR"))))))) old) ", ")
                                                            ". [Capnhat (doi D, so thanh)/Them ky hieu (cau kien dung chung)/Bo] <Capnhat>: ")))
                                         ("Capnhat"))))
                   "Them"))
          (if (= kw "Capnhat")
            (foreach g old
              (setq ed (entget g '("SD_REBAR")) xd (cdadr (assoc -3 ed)))
              (setq xd (sd:replace-nth 2 (cons 1040 d) xd))
              (if (and (= nm 0) (= (cdr (nth 11 xd)) 0)) (setq xd (sd:replace-nth 1 (cons 1070 n) xd)))
              (entmod (append (vl-remove (assoc -3 ed) ed) (list (list -3 (cons "SD_REBAR" xd)))))
              (sd:tm-update g)
              (princ (strcat "\n[SD] Da cap nhat ky hieu " (cdr (car xd)) ": "
                             (cdr (assoc 1 (entget (handent (cdr (nth 10 (cdadr (assoc -3 (entget g '("SD_REBAR")))))))))))))))
         ((setq p1 (vlax-curve-getClosestPointTo bar (sd:w (cadr es)))
                p2 (sd:getpt "\nVi tri ghi chu: " (trans p1 0 1)))
          (setq xd (list (cons 1000 mk) (cons 1070 n) (cons 1040 d) (cons 1040 0.0) (cons 1070 k)
                         '(1000 . "Thang") '(1000 . "") '(1000 . "") '(1000 . "TM")
                         (cons 1005 (cdr (assoc 5 (entget bar)))) '(1005 . "TXT") (cons 1070 nm) (cons 1040 a)))
          (if dist (setq xd (append xd (list (cons 1005 (cdr (assoc 5 (entget dist))))))))
          ;; co ky hieu theo ty le vung ve: mat cat 1/25 khong dung co cua mat bang 1/100
          (setq sc (cond ((= *SD:TMTL* "Chinh") (sd:sc))
                         ((= *SD:TMTL* "Chitiet") (float *SD:DETSCALE*))
                         ((sd:sc-near bar))
                         ((float *SD:DETSCALE*))))
          (setq tag (sd:tm-tag p1 (sd:w p2) mk "..." xd sc))
          (sd:tm-update tag)
          (sd:tm-attach bar)
          (if dist (sd:tm-attach dist))
          (princ (strcat "\n[SD] " mk ": " (cdr (assoc 1 (entget (handent (cdr (nth 10 (cdadr (assoc -3 (entget tag '("SD_REBAR"))))))))))
                         "  (co ky hieu 1/" (itoa (fix sc)) ")"))
          (setq mk (if (wcmatch mk "#*") (itoa (1+ (atoi mk))) mk))
          (if (wcmatch mk "#*") (setq *SD:MARK* (atoi mk))))))
     (sd:tm-scan)
     (sd:tk-refresh nil)))
  (sd:finish))

;;; --------------------------------------------------------------------------
;;;  SDDAMDUNG - Mat dung thep dam lien tuc (trien khai thep theo chieu dai dam)
;;;  Cot + truc + kich thuoc, thep tren / duoi chay suot (neo moc 15d hoac thang vao cot bien),
;;;  thep mu goi (Ln/3 hoac Ln/4 tu mep goi), thep duoi tang cuong giua nhip (cach mep goi 0.15Ln),
;;;  dai: vung goi Ln/4 buoc a1, giua nhip buoc a2, dai dau cach mep goi 50 mm.
;;;  Thep doc = thep thong minh (SDTHEPTM): co keo dam -> L, ghi chu, bang thong ke tu cap nhat.
;;; --------------------------------------------------------------------------
;; So hieu theo hinh dang + kich thuoc + d + n: thanh giong nhau dung chung so hieu
(defun sd:dd-mark (key / e)
  (if (setq e (assoc key *SD:DD-KEYS*))
    (cdr e)
    (progn (setq e (itoa *SD:DD-NEXT*) *SD:DD-NEXT* (1+ *SD:DD-NEXT*)
                 *SD:DD-KEYS* (cons (cons key e) *SD:DD-KEYS*))
           e)))

;; Ve 1 thanh thep doc (polyline) + ky hieu; hx = toa do x goi y de dat ghi chu, ly = cao do ghi chu
(defun sd:dd-bar (o pts n d hx ly k tm sc / bar sp mk xd tag p1)
  (sd:pline (mapcar '(lambda (p) (sd:p+ o (car p) (cadr p))) pts) nil "SD-THEP-CHU")
  (setq bar (entlast) sp (sd:tm-shape bar)
        mk (sd:dd-mark (vl-prin1-to-string (list (car sp) (mapcar '(lambda (x) (fix (+ x 0.5))) (cadr sp)) d n)))
        p1 (vlax-curve-getClosestPointTo bar (sd:p+ o hx (cadr (cadr pts))))
        xd (list (cons 1000 mk) (cons 1070 n) (cons 1040 d) (cons 1040 0.0) (cons 1070 k)
                 '(1000 . "Thang") '(1000 . "") '(1000 . "") '(1000 . "TM")
                 (cons 1005 (cdr (assoc 5 (entget bar)))) '(1005 . "TXT") (cons 1070 0) (cons 1040 0.0)))
  (setq tag (sd:tm-tag p1 (sd:p+ o (+ hx (* 4 sc)) ly) mk "..." xd sc))
  (sd:tm-update tag)
  (if tm
    (sd:tm-attach bar)
    (progn (setq xd (entget tag '("SD_REBAR")))
           (entmod (append (vl-remove (assoc -3 xd) xd)
                           (list (list -3 (cons "SD_REBAR" (sd:head 8 (cdadr (assoc -3 xd))))))))))
  tag)

;; Dien tich van khuon thanh dam bi tru tai cho dam phu gac vao (mm2):
;; "220x400*4;300x500*2" -> moi cho giao tru b2 x (h2 - ts)
(defun sd:dp-tru (s ts / tot sz p n)
  (setq tot 0.0)
  (foreach it (sd:split (vl-string-translate "," ";" s) ";")
    (if (setq sz (sd:parse-size it))
      (setq p (vl-string-position (ascii "*") it nil t)
            n (if p (max 1 (atoi (substr it (+ p 2)))) 1)
            tot (+ tot (* n (car sz) (max 0.0 (- (cadr sz) ts)))))))
  tot)

;; Doan moc 90 do neo vao cot bien: 15d, lam tron 10 mm
(defun sd:hk15 (d) (sd:ceil (* 15.0 d) 10.0))

;; Duong cat ngang cot (zigzag) tu x1 den x2 tai y
(defun sd:zig (o x1 x2 y sc / m)
  (setq m (/ (+ x1 x2) 2.0))
  (sd:pline (list (sd:p+ o (- x1 (* 2 sc)) y) (sd:p+ o (- m (* 1.5 sc)) y) (sd:p+ o (- m (* 0.5 sc)) (+ y (* 2 sc)))
                  (sd:p+ o (+ m (* 0.5 sc)) (- y (* 2 sc))) (sd:p+ o (+ m (* 1.5 sc)) y) (sd:p+ o (+ x2 (* 2 sc)) y))
            nil "SD-BETONG"))

;; Ten truc thu i tinh tu ten truc dau
(defun sd:ax-name (a0 i / p)
  (cond ((wcmatch a0 "#,##,###") (itoa (+ (atoi a0) i)))
        ((setq p (vl-string-position (ascii (strcase a0)) "ABCDEFGHJKLMNPQRSTUVWXYZ")) (sd:axis-letter (+ p i)))
        (t (strcat a0 (itoa i)))))

;; Ky hieu mat cat tren mat dung: 2 vach dam tren / duoi dam + so
(defun sd:dd-cut (o x h lab sc)
  (sd:plinew (list (sd:p+ o x (+ h sc)) (sd:p+ o x (+ h (* 4 sc)))) nil (* 0.5 sc) "SD-KYHIEU")
  (sd:plinew (list (sd:p+ o x (- sc)) (sd:p+ o x (* -4 sc))) nil (* 0.5 sc) "SD-KYHIEU")
  (sd:text (sd:p+ o (+ x (* 1.5 sc)) (+ h (* 3 sc))) lab (* 2.5 sc) "ML" "SD-CHU")
  (sd:text (sd:p+ o (+ x (* 1.5 sc)) (* -3 sc)) lab (* 2.5 sc) "ML" "SD-CHU"))

(defun c:SDDAMDUNG (/ ts sides tru name sp cws b h c top bot tsup bmid kt moc ds a1 a2 k sc tm mc o ns xs fl fr ln dls
                     i j x y yt yb yt2 yb2 xeL xeR ext lt pts left right mid st nst stx zone lz s1 s2 s1o s2o
                     dt db r ax tagtxt slen pd)
  (sd:begin)
  (if (not (sd:dlg "Mat dung thep dam (SDDAMDUNG)"
                   (list (list "name" "Ten dam" 'str (cond (*SD:DNAME*) ("D1")))
                         (list "sp" "Cac nhip truc - truc (mm), vd 6000,2*4500" 'str (cond (*SD:DDL*) ("6000,4500")))
                         (list "cw" "Be rong cot tai cac goi (mm), vd 400 hoac 400,300,400" 'str (cond (*SD:DDC*) ("400")))
                         (list "ax" "Ten truc dau tien" 'str (cond (*SD:DDAX*) ("1")))
                         (list "b" "Be rong dam b (mm)" 'real (cond (*SD:DB*) (220.0)))
                         (list "h" "Chieu cao dam h (mm)" 'real (cond (*SD:DH*) (500.0)))
                         (list "c" "Lop bao ve (mm)" 'real 25.0)
                         (list "vt" "Vi tri dam (tinh van khuon)" 'kw (cond (*SD:DDVT*) ("Giua"))
                               '(("Giua" . "Dam giua - san 2 ben") ("Bien" . "Dam bien - san 1 ben") ("Doclap" . "Khong co san")))
                         (list "ts" "Chieu day san lien khoi (mm)" 'real0 (cond (*SD:SLT*) (120.0)) nil '("vt" "Giua" "Bien"))
                         (list "dp" "Dam phu gac vao bxh*so cho (vd 220x400*4)" 'str "")
                         (list "top" "Thep tren chay suot (vd 2d18)" 'bar "2d18")
                         (list "bot" "Thep duoi chay suot (vd 2d20)" 'bar "2d20")
                         (list "tsup" "Thep mu goi (vd 2d18; trong = khong)" 'str "2d18")
                         (list "bmid" "Thep duoi tang cuong giua nhip (trong = khong)" 'str "")
                         (list "lt" "Thep mu vuon tu mep goi" 'kw "1/3" '(("1/3" . "Ln/3") ("1/4" . "Ln/4")))
                         (list "neo" "Neo thep vao cot bien" 'kw "Moc"
                               '(("Moc" . "Uon 90 do, doan moc 15d") ("Thang" . "Thang den mep cot (tu chia noi)")))
                         (list "ds" "Duong kinh dai (mm)" 'real 8.0)
                         (list "a1" "Buoc dai vung goi Ln/4 (mm)" 'real 100.0)
                         (list "a2" "Buoc dai giua nhip (mm)" 'real 200.0)
                         (sd:tang-field)
                         (list "mk" "So hieu thep bat dau" 'int *SD:MARK*)
                         (list "k" "So cau kien (dam giong nhau)" 'int 1)
                         (list "sc" "Ty le ve 1/" 'int (fix *SD:DETSCALE*))
                         (list "mc" "Ve mat cat goi (1-1) va giua nhip (2-2)" 'tog t)
                         (list "tm" "Thep thong minh (tu cap nhat khi co keo)" 'tog t))))
    (exit))
  (setq name (sd:v "name") b (sd:v "b") h (sd:v "h") c (sd:v "c") top (sd:v "top") bot (sd:v "bot")
        ds (sd:v "ds") a1 (sd:v "a1") a2 (sd:v "a2") k (sd:v "k") sc (float (sd:v "sc")) tm (sd:v "tm") mc (sd:v "mc")
        moc (= (sd:v "neo") "Moc") kt (if (= (sd:v "lt") "1/3") (/ 1.0 3.0) 0.25)
        sp (sd:parse-spacing (sd:v "sp")) cws (sd:parse-spacing (sd:v "cw"))
        tsup (if (/= (vl-string-trim " " (sd:v "tsup")) "") (sd:parse-bar (sd:v "tsup")) "")
        bmid (if (/= (vl-string-trim " " (sd:v "bmid")) "") (sd:parse-bar (sd:v "bmid")) ""))
  (setq *SD:DNAME* name *SD:DB* b *SD:DH* h *SD:DDL* (sd:v "sp") *SD:DDC* (sd:v "cw") *SD:DDAX* (sd:v "ax")
        *SD:DDVT* (sd:v "vt"))
  ;; van khuon thanh dam: tru phan san lien khoi (h - ts) va cho dam phu gac vao
  (setq ts (if (= (sd:v "vt") "Doclap") 0.0 (min (sd:v "ts") h))
        sides (cond ((= (sd:v "vt") "Giua") (* 2 (- h ts))) ((= (sd:v "vt") "Bien") (- (* 2 h) ts)) (t (* 2 h)))
        tru (sd:dp-tru (sd:v "dp") ts))
  (cond
    ((or (null sp) (null cws)) (princ "\n[SD] Nhip / be rong cot khong hop le."))
    ((or (null tsup) (null bmid)) (princ "\n[SD] Thep mu / thep tang cuong sai dinh dang (vd 2d18)."))
    (t
     (if (= tsup "") (setq tsup nil))
     (if (= bmid "") (setq bmid nil))
     (setq ns (length sp) xs (sd:cumul sp) i 0)
     (foreach x xs
       (setq r (cond ((nth i cws)) ((last cws)))
             fl (append fl (list (- x (/ r 2.0)))) fr (append fr (list (+ x (/ r 2.0)))) i (1+ i)))
     (setq j 0)
     (repeat ns (setq ln (append ln (list (- (nth (1+ j) fl) (nth j fr)))) j (1+ j)))
     (if (vl-some '(lambda (x) (<= x (* 4 a1))) ln)
       (princ "\n[SD] Nhip thong thuy qua ngan so voi cot / buoc dai.")
       (if (setq o (sd:getpt "\nDiem chen (giao truc dau voi day dam): " nil))
         (progn
           (setq o (sd:w o) dt (cadr top) db (cadr bot)
                 ext (max 300.0 (* 12 sc)) yt (- h c ds (/ dt 2.0)) yb (+ c ds (/ db 2.0))
                 yt2 (- yt 25.0 (/ dt 2.0) (if tsup (/ (cadr tsup) 2.0) 0.0))
                 yb2 (+ yb 25.0 (/ db 2.0) (if bmid (/ (cadr bmid) 2.0) 0.0))
                 xeL (+ (car fl) c) xeR (- (last fr) c))
           (sd:kt-begin (sd:v "mk") name)
           ;; ---- be tong: cot (2 dau cat zigzag), dam giua cac mep cot
           (setq i 0)
           (foreach x xs
             (if (= i 0)
               (sd:line (sd:p+ o (nth i fl) (- ext)) (sd:p+ o (nth i fl) (+ h ext)) "SD-BETONG")
               (progn (sd:line (sd:p+ o (nth i fl) (- ext)) (sd:p+ o (nth i fl) 0) "SD-BETONG")
                      (sd:line (sd:p+ o (nth i fl) h) (sd:p+ o (nth i fl) (+ h ext)) "SD-BETONG")))
             (if (= i ns)
               (sd:line (sd:p+ o (nth i fr) (- ext)) (sd:p+ o (nth i fr) (+ h ext)) "SD-BETONG")
               (progn (sd:line (sd:p+ o (nth i fr) (- ext)) (sd:p+ o (nth i fr) 0) "SD-BETONG")
                      (sd:line (sd:p+ o (nth i fr) h) (sd:p+ o (nth i fr) (+ h ext)) "SD-BETONG")))
             (sd:zig o (nth i fl) (nth i fr) (- ext) sc)
             (sd:zig o (nth i fl) (nth i fr) (+ h ext) sc)
             ;; truc
             (sd:line (sd:p+ o x (- (+ ext (* 4 sc)))) (sd:p+ o x (+ h ext (* 4 sc))) "SD-TRUC")
             (sd:bubble (sd:p+ o x (+ h ext (* 8 sc))) (* 4 sc) (sd:ax-name (sd:v "ax") i))
             (setq i (1+ i)))
           (setq j 0)
           (repeat ns
             (sd:line (sd:p+ o (nth j fr) 0) (sd:p+ o (nth (1+ j) fl) 0) "SD-BETONG")
             (sd:line (sd:p+ o (nth j fr) h) (sd:p+ o (nth (1+ j) fl) h) "SD-BETONG")
             (setq j (1+ j)))
           ;; ---- dai: vung goi Ln/4 buoc a1, giua nhip buoc a2
           (setq j 0 nst 0)
           (repeat ns
             (setq lz (* 0.25 (nth j ln)) zone (sd:beam-zone-ys (nth j ln) a1 a2) x (nth j fr)
                   left (mapcar '(lambda (y) (+ x y)) (car zone)) mid (mapcar '(lambda (y) (+ x y)) (cadr zone))
                   right (mapcar '(lambda (y) (+ x y)) (caddr zone))
                   ;; duong phan bo dai = nhip thong thuy (co keo goi -> so dai theo vung tu tinh lai)
                   dls (append dls (list (sd:kt-dline (sd:p+ o (nth j fr) (+ c ds 30)) (sd:p+ o (nth (1+ j) fl) (+ c ds 30)) sc))))
             (foreach x (append left mid right)
               (sd:line (sd:p+ o x c) (sd:p+ o x (- h c)) "SD-THEP-DAI"))
             (setq nst (+ nst (length left) (length mid) (length right)))
             (if (and (= j 0) mid) (setq stx (nth (/ (length mid) 2) mid)))
             (foreach zone (list (list (+ (nth j fr) (/ lz 2.0)) a1) (list (/ (+ (nth j fr) (nth (1+ j) fl)) 2.0) a2)
                                 (list (- (nth (1+ j) fl) (/ lz 2.0)) a1))
               (sd:text (sd:p+ o (car zone) (/ h 2.0)) (strcat "%%c" (sd:num ds) "a" (sd:num (cadr zone)))
                        (* 2.0 sc) "MC" "SD-CHU"))
             (setq pd (append pd (list (nth j fr) (+ (nth j fr) lz) (- (nth (1+ j) fl) lz) (nth (1+ j) fl))) j (1+ j)))
           ;; ---- thep doc (thong minh)
           (setq pts (if moc
                       (list (list xeL (- yt (sd:hk15 dt))) (list xeL yt) (list xeR yt) (list xeR (- yt (sd:hk15 dt))))
                       (list (list xeL yt) (list xeR yt))))
           (sd:dd-bar o pts (car top) dt (+ (car fr) (* 0.3 (car ln))) (+ h (* 16 sc)) k tm sc)
           (setq pts (if moc
                       (list (list xeL (+ yb (sd:hk15 db))) (list xeL yb) (list xeR yb) (list xeR (+ yb (sd:hk15 db))))
                       (list (list xeL yb) (list xeR yb))))
           (sd:dd-bar o pts (car bot) db (+ (car fr) (* 0.3 (car ln))) (* -16 sc) k tm sc)
           (if tsup
             (progn
               (setq i 0)
               (foreach x xs
                 (setq left  (if (> i 0) (sd:ceil (* kt (nth (1- i) ln)) 50.0))
                       right (if (< i ns) (sd:ceil (* kt (nth i ln)) 50.0)))
                 (cond
                   ((= i 0)
                    (setq pts (append (if moc (list (list xeL (- yt2 (sd:hk15 (cadr tsup))))))
                                      (list (list xeL yt2) (list (+ (nth i fr) right) yt2)))
                          lt (+ (nth i fr) (/ right 2.0))))
                   ((= i ns)
                    (setq pts (append (list (list (- (nth i fl) left) yt2) (list xeR yt2))
                                      (if moc (list (list xeR (- yt2 (sd:hk15 (cadr tsup)))))))
                          lt (- (nth i fl) (/ left 2.0))))
                   (t (setq pts (list (list (- (nth i fl) left) yt2) (list (+ (nth i fr) right) yt2))
                            lt (+ (nth i fr) (/ right 2.0)))))
                 (sd:dd-bar o pts (car tsup) (cadr tsup) lt (+ h (* 8 sc)) k tm sc)
                 (setq i (1+ i)))))
           (if bmid
             (progn
               (setq j 0)
               (repeat ns
                 (setq x (sd:ceil (* 0.15 (nth j ln)) 50.0))
                 (sd:dd-bar o (list (list (+ (nth j fr) x) yb2) (list (- (nth (1+ j) fl) x) yb2))
                            (car bmid) (cadr bmid) (/ (+ (nth j fr) (nth (1+ j) fl)) 2.0) (* -8 sc) k tm sc)
                 (setq j (1+ j)))))
           ;; ---- dai: 1 ky hieu cho ca dam, so dai theo vung tinh tu cac duong phan bo tung nhip
           (if (null stx) (setq stx (+ (car fr) (/ (car ln) 2.0))))
           (sd:kt-dist o (list stx (- h c)) (list (+ stx (* 4 sc)) (+ h (* 24 sc))) ds "Dai" (list (- b c c) (- h c c)) k sc tm
                       2 0.0 (strcat "DAM|1," (sd:num a1) "," (sd:num a2) "|a" (sd:num a1) "/" (sd:num a2)) dls)
           ;; ---- kich thuoc: vung dai, nhip truc, tong
           (sd:use-dimstyle sc)
           (sd:dimchain (mapcar '(lambda (x) (sd:p+ o x (- ext))) pd) "H" (sd:p+ o 0 (- (+ ext (* 10 sc)))))
           (sd:dimchain (mapcar '(lambda (x) (sd:p+ o x (- ext))) xs) "H" (sd:p+ o 0 (- (+ ext (* 18 sc)))))
           (if (> ns 1) (sd:dim (sd:p+ o 0 (- ext)) (sd:p+ o (last xs) (- ext)) "H" (sd:p+ o 0 (- (+ ext (* 26 sc))))))
           (sd:dim (sd:p+ o (car fl) 0) (sd:p+ o (car fl) h) "V" (sd:p+ o (- (car fl) (* 8 sc)) 0))
           (sd:ck-title (sd:p+ o (/ (last xs) 2.0) (- (+ ext (* 36 sc))))
                        (strcat "M\\U+1EB6T \\U+0110\\U+1EE8NG TH\\U+00C9P D\\U+1EA6M " name " (" (sd:num b) "\\U+00D7" (sd:num h) ")  TL 1/" (itoa (fix sc)))
                        sc name "Dam" k (/ (* b h (apply '+ ln)) 1e9) (/ (- (* (+ b sides) (apply '+ ln)) tru) 1e6)
                        (strcat (sd:num b) "x" (sd:num h) ", Ln=" (sd:num (apply '+ ln))
                                (cond ((= (sd:v "vt") "Giua") ", VK tru san 2 ben") ((= (sd:v "vt") "Bien") ", VK tru san 1 ben") (""))
                                (if (> tru 0) (strcat ", tru dam phu " (sd:rtos (/ tru 1e6) 2) "m2") "")))
           ;; du lieu cho SDNOITHEP (doc hang loat): nhip, goi, dau thanh tinh tu truc, thep tren / duoi
           (sd:noi-reg (entlast)
                       (list "DAM" name (sd:v "sp") (sd:v "cw")
                             (- (/ (car cws) 2.0) c) (- (/ (cond ((nth ns cws)) ((last cws))) 2.0) c) (if moc 1 0)
                             (car top) (cadr top) (car bot) (cadr bot) k (cond (*SD:TANG*) (""))))
           ;; ---- mat cat 1-1 (goi) va 2-2 (giua nhip 1)
           (if mc
             (progn
               (setq s1 (if (> ns 1) (+ (nth 1 fr) 150.0) (+ (car fr) 150.0))
                     s2 (/ (+ (car fr) (nth 1 fl)) 2.0)
                     s1o (sd:p+ o (+ (last fr) (* 40 sc)) 0) s2o (sd:p+ s1o (+ b (* 40 sc)) 0))
               (sd:dd-cut o s1 h "1" sc)
               (sd:dd-cut o s2 h "2" sc)
               (foreach s (list (list s1o "1-1" a1 tsup nil) (list s2o "2-2" a2 nil bmid))
                 (sd:sec-common (car s) b h c ds (caddr s) sc (strcat "M\\U+1EB6T C\\U+1EAET " (cadr s)))
                 (sd:tagL (sd:barrow (car s) b c ds (car top) dt yt) (sd:p+ (car s) (* -6 sc) (+ h (* 6 sc)))
                          (strcat (itoa (car top)) "%%c" (sd:num dt)
                                  (if (nth 3 s) (strcat " + " (itoa (car tsup)) "%%c" (sd:num (cadr tsup))) ""))
                          sc)
                 (if (nth 3 s) (sd:barrow (car s) b c ds (car tsup) (cadr tsup) yt2))
                 (sd:tagL (sd:barrow (car s) b c ds (car bot) db yb) (sd:p+ (car s) (* -6 sc) (* -4 sc))
                          (strcat (itoa (car bot)) "%%c" (sd:num db)
                                  (if (nth 4 s) (strcat " + " (itoa (car bmid)) "%%c" (sd:num (cadr bmid))) ""))
                          sc)
                 (if (nth 4 s) (sd:barrow (car s) b c ds (car bmid) (cadr bmid) yb2)))))
           (sd:use-dimstyle *SD:SCALE*)
           (sd:kt-end)
           (if (and moc (> (+ (last xs) (* 2 (sd:hk15 dt))) (sd:cfg "STOCK" 11700.0)))
             (princ "\n[SD] Luu y: thanh chay suot co moc dai hon cay thep, khong tu chia noi. Nen chon neo Thang hoac tach thanh."))
           (princ (strcat "\n[SD] Da ve mat dung dam " name ": " (itoa ns) " nhip, " (itoa nst) " dai, so hieu "
                          (itoa (sd:v "mk")) "-" (itoa (1- *SD:DD-NEXT*))
                          (if tm ". Thep doc la thep thong minh (co keo tu cap nhat)." "."))))))))
  (sd:finish))

;;; --------------------------------------------------------------------------
;;;  KHAI TRIEN BTCT + KHOI LUONG
;;;  - Moi cau kien do lenh khai trien ve co 1 "nhan cau kien" (chu tieu de) mang XDATA "SD_KL":
;;;      ten, loai, so CK, be tong 1 CK (m3), van khuon 1 CK (m2), ghi chu kich thuoc
;;;  - Ky hieu thep cua cau kien mang XDATA "SD_CK" = ten cau kien (thong ke thep theo cau kien)
;;;  - SDKL doc toan ban ve -> file Excel (be tong, van khuon, thep theo duong kinh, chi tiet thep)
;;; --------------------------------------------------------------------------
;; Gan ten cau kien cho ky hieu thep
(defun sd:ck-tag (e name)
  (if (and e name (/= name ""))
    (entmod (append (entget e) (list (list -3 (list "SD_CK" (cons 1000 name))))))))

;; Dang ky khoi luong cau kien len doi tuong e (v: m3 / 1 CK, s: m2 / 1 CK)
(defun sd:ck-reg (e name typ k v s info)
  (entmod (append (entget e)
                  (list (list -3 (list "SD_KL" (cons 1000 name) (cons 1000 typ) (cons 1070 k)
                                       (cons 1040 v) (cons 1040 s) (cons 1000 info) (cons 1000 (cond (*SD:TANG*) ("")))))))))

;; Du lieu hinh hoc thep cho SDNOITHEP (XDATA "SD_NOI"): chuoi -> 1000, so nguyen -> 1070, so thuc -> 1040
(defun sd:noi-reg (e lst)
  (entmod (append (entget e)
                  (list (list -3 (cons "SD_NOI" (mapcar '(lambda (v) (cond ((= (type v) 'STR) (cons 1000 v)) ((= (type v) 'INT) (cons 1070 v))
                                                                            (t (cons 1040 (float v)))))
                                                        lst)))))))

;; Chu tieu de cau kien + dang ky khoi luong (kich thuoc mm -> m3, m2 da tinh truoc)
(defun sd:ck-title (pt str sc name typ k v s info)
  (sd:text pt str (* 3.5 sc) "MC" "SD-CHU")
  (sd:ck-reg (entlast) name typ k v s info)
  (princ (strcat "\n[SD] " name " (" typ "): be tong " (sd:rtos v 3) " m3, van khuon " (sd:rtos s 2)
                 " m2 / 1 CK" (if (> k 1) (strcat " x " (itoa k) " CK") "") ".")))

;; Duong phan bo thep (doan thang co 2 vach dau); tra ve ename doan thang
(defun sd:kt-dline (p q sc / a e)
  (sd:line p q "SD-KYHIEU")
  (setq e (entlast) a (+ (angle p q) (/ pi 2)))
  (foreach x (list p q)
    (sd:line (polar x a (* 1.5 sc)) (polar x (+ a pi) (* 1.5 sc)) "SD-KYHIEU"))
  e)

;; Thanh thep thong minh tong quat
;;  o: goc toa do cuc bo; pts: dinh polyline (cuc bo); hint: diem gan thanh (cuc bo) cho dau ghi chu;
;;  p2: vi tri ky hieu (cuc bo); dist: (p q) duong phan bo (cuc bo) + a buoc rai -> so thanh tu tinh
(defun sd:kt-bar (o pts n d hint p2 k tm sc dist a / bar sp mk xd tag p1 de)
  (sd:pline (mapcar '(lambda (p) (sd:p+ o (car p) (cadr p))) pts) nil "SD-THEP-CHU")
  (setq bar (entlast) sp (sd:tm-shape bar))
  (if dist (setq de (sd:kt-dline (sd:p+ o (car (car dist)) (cadr (car dist)))
                                 (sd:p+ o (car (cadr dist)) (cadr (cadr dist))) sc)))
  (setq mk (sd:dd-mark (vl-prin1-to-string
                         (list (car sp) (mapcar '(lambda (x) (fix (+ x 0.5))) (cadr sp)) d
                               (if dist (list a (fix (+ 0.5 (distance (car dist) (cadr dist))))) n))))
        p1 (vlax-curve-getClosestPointTo bar (sd:p+ o (car hint) (cadr hint)))
        xd (append (list (cons 1000 mk) (cons 1070 n) (cons 1040 d) (cons 1040 0.0) (cons 1070 k)
                         '(1000 . "Thang") '(1000 . "") '(1000 . "") '(1000 . "TM")
                         (cons 1005 (cdr (assoc 5 (entget bar)))) '(1005 . "TXT")
                         (cons 1070 (if dist 1 0)) (cons 1040 (if dist a 0.0)))
                   (if de (list (cons 1005 (cdr (assoc 5 (entget de))))))))
  (setq tag (sd:tm-tag p1 (sd:p+ o (car p2) (cadr p2)) mk "..." xd sc))
  (sd:tm-update tag)
  (if tm
    (progn (sd:tm-attach bar) (if de (sd:tm-attach de)))
    (progn (setq xd (entget tag '("SD_REBAR")))
           (entmod (append (vl-remove (assoc -3 xd) xd)
                           (list (list -3 (cons "SD_REBAR" (sd:head 8 (cdadr (assoc -3 xd))))))))))
  tag)

;; Ky hieu thep so luong co dinh (khong gan hinh ve): dai, thep phan bo, thep cho doi xung...
(defun sd:kt-fixed (o hint p2 n d shp prm k sc note / len mk)
  (setq len (sd:shape-len shp prm d)
        mk  (sd:dd-mark (vl-prin1-to-string (list shp (mapcar '(lambda (x) (fix (+ x 0.5))) prm) d n))))
  (sd:tm-tag (sd:p+ o (car hint) (cadr hint)) (sd:p+ o (car p2) (cadr p2)) mk
             (strcat (itoa n) "%%c" (sd:num d) note " L=" (sd:rtos len 0) (if (> k 1) (strcat " (\\U+00D7" (itoa k) " CK)") ""))
             (list (cons 1000 mk) (cons 1070 n) (cons 1040 d) (cons 1040 len) (cons 1070 k)
                   (cons 1000 shp) (cons 1000 (sd:nums->str prm)) '(1000 . ""))
             sc))

;; Ky hieu thong minh khong gan hinh thanh: so luong theo duong phan bo da ve (dl = cac ename)
;;  nm 1: rai deu buoc a tren (car dl); nm 2: theo vung spec (xem sd:zone-n), dl = 1 hoac nhieu nhip
;;  tm nil -> chuyen thanh ky hieu co dinh (so luong luc ve)
(defun sd:kt-dist (o hint p2 d shp prm k sc tm nm a spec dl / mk xd tag)
  (setq mk (sd:dd-mark (vl-prin1-to-string (list shp (mapcar '(lambda (x) (fix (+ x 0.5))) prm) d nm a spec
                                                 (mapcar '(lambda (e) (fix (+ 0.5 (sd:len e)))) dl))))
        xd (append (list (cons 1000 mk) (cons 1070 0) (cons 1040 d) (cons 1040 0.0) (cons 1070 k)
                         (cons 1000 shp) (cons 1000 (sd:nums->str prm)) '(1000 . "") '(1000 . "TM")
                         '(1000 . "") '(1005 . "TXT") (cons 1070 nm) (cons 1040 a)
                         (cons 1005 (cdr (assoc 5 (entget (car dl))))))
                   (if (= nm 2)
                     (cons (cons 1000 spec) (mapcar '(lambda (e) (cons 1005 (cdr (assoc 5 (entget e))))) (cdr dl))))))
  (setq tag (sd:tm-tag (sd:p+ o (car hint) (cadr hint)) (sd:p+ o (car p2) (cadr p2)) mk "..." xd sc))
  (sd:tm-update tag)
  (if tm
    (foreach e dl (sd:tm-attach e))
    (progn (setq xd (entget tag '("SD_REBAR")))
           (entmod (append (vl-remove (assoc -3 xd) xd)
                           (list (list -3 (cons "SD_REBAR" (sd:head 8 (cdadr (assoc -3 xd))))))))))
  tag)

;; Bat dau / ket thuc danh so thep cho 1 lenh khai trien
(defun sd:kt-begin (mk name)
  (sd:tm-init)
  (if (assoc "tang" *SD:FV*) (setq *SD:TANG* (vl-string-trim " " (sd:v "tang"))))
  (setq *SD:DD-KEYS* nil *SD:DD-NEXT* mk *SD:CKNAME* name))
(defun sd:kt-end () (setq *SD:MARK* *SD:DD-NEXT* *SD:CKNAME* nil))

;; Ky hieu mat cat A-A: 2 vach day + chu, tai p (huong vach theo goc ang)
(defun sd:kt-cutmark (p ang lab sc)
  (sd:plinew (list p (polar p ang (* 4 sc))) nil (* 0.6 sc) "SD-KYHIEU")
  (sd:text (polar p ang (* 6 sc)) lab (* 3.0 sc) "MC" "SD-CHU"))

;; Truong dung chung cua cac lenh khai trien
(defun sd:tang-field () (list "tang" "Tang / khu vuc (nhom khi xuat Excel, vd T1)" 'str (cond (*SD:TANG*) (""))))
(defun sd:kt-fields ()
  (list (sd:tang-field)
        (list "mk" "So hieu thep bat dau" 'int *SD:MARK*)
        (list "k" "So cau kien giong nhau" 'int 1)
        (list "sc" "Ty le ve 1/" 'int (fix *SD:DETSCALE*))
        (list "tm" "Thep thong minh (tu cap nhat khi co keo)" 'tog t)))

;; "8d18" -> (8 18.0); trong -> "" ; sai -> nil
(defun sd:opt-bar (s) (if (= (vl-string-trim " " s) "") "" (sd:parse-bar s)))

;;; --------------------------------------------------------------------------
;;;  SDMONGTHEP - Khai trien mong don: mat bang + mat cat A-A, B-B
;;;  Luoi thep day 2 phuong (uon moc len 10d), thep cho cot co chan, dai cot trong mong
;;; --------------------------------------------------------------------------
;; Co cot tren mong / dai: canh cot, thep cho (chan nam tren luoi yb, vuon len lap), dai cot trong mong.
;; e: goc mat cat; x: be rong mat cat; w: canh cot trong mat cat; main: mat cat chinh (ghi ky hieu);
;; ylow: cao do dai duoi cung.
(defun sd:kt-colstub (e x w H yb ylow lap cot dsc bc hc main k tm sc / cc foot xs ys y)
  (setq cc 40.0)
  (sd:line (sd:p+ e (/ (- x w) 2.0) H) (sd:p+ e (/ (- x w) 2.0) (+ H lap 300)) "SD-BETONG")
  (sd:line (sd:p+ e (/ (+ x w) 2.0) H) (sd:p+ e (/ (+ x w) 2.0) (+ H lap 300)) "SD-BETONG")
  (sd:zig e (/ (- x w) 2.0) (/ (+ x w) 2.0) (+ H lap 300) sc)
  (if (listp cot)
    (progn
      (setq foot (sd:ceil (max (* 15 (cadr cot)) 200.0) 10.0)
            xs (+ (/ (- x w) 2.0) cc (/ (cadr cot) 2.0))
            ys (- (/ (+ x w) 2.0) cc (/ (cadr cot) 2.0)))
      (sd:pline (list (sd:p+ e (+ ys foot) (+ yb (/ (cadr cot) 2.0))) (sd:p+ e ys (+ yb (/ (cadr cot) 2.0)))
                      (sd:p+ e ys (+ H lap))) nil "SD-THEP-CHU")
      (if main
        (sd:kt-bar e (list (list (- xs foot) (+ yb (/ (cadr cot) 2.0))) (list xs (+ yb (/ (cadr cot) 2.0))) (list xs (+ H lap)))
                   (car cot) (cadr cot) (list xs (+ H (/ lap 2.0))) (list (- xs (* 30 sc)) (+ H lap (* 4 sc))) k tm sc nil 0.0)
        (sd:pline (list (sd:p+ e (- xs foot) (+ yb (/ (cadr cot) 2.0))) (sd:p+ e xs (+ yb (/ (cadr cot) 2.0)))
                        (sd:p+ e xs (+ H lap))) nil "SD-THEP-CHU"))))
  (if (listp dsc)
    (progn
      (setq y (- H 100.0))
      (repeat (car dsc)
        (sd:line (sd:p+ e (+ (/ (- x w) 2.0) 25) y) (sd:p+ e (- (/ (+ x w) 2.0) 25) y) "SD-THEP-DAI")
        (setq y (- y (/ (- H 100.0 ylow) (max 1 (1- (car dsc)))))))
      (if main
        (sd:kt-fixed e (list (- (/ (+ x w) 2.0) 25) (- H 100.0)) (list (+ x (* 4 sc)) (+ H (* 2 sc)))
                     (car dsc) (cadr dsc) "Dai" (list (- bc 50) (- hc 50)) k sc "")))))

(defun c:SDMONGTHEP (/ name A B H hv h1 a2 b2 bc hc lot c dx ax dy ay moc cot dsc k sc tm o oa ob x y hkx hky
                       xs lap yb yt v s e)
  (sd:begin)
  (if (not (sd:dlg "Khai trien mong don (SDMONGTHEP)"
                   (append
                     (list (list "name" "Ten mong" 'str (cond (*SD:FMN*) ("M1")))
                           (list "A" "Canh A - theo X (mm)" 'real (cond (*SD:FMX*) (2000.0)))
                           (list "B" "Canh B - theo Y (mm)" 'real (cond (*SD:FMY*) (1600.0)))
                           (list "H" "Chieu cao mong (mm)" 'real (cond (*SD:FMH*) (500.0)))
                           (list "hv" "Chieu cao phan vat (mm, 0 = mong hop)" 'real0 (cond (*SD:FMHV*) (0.0)))
                           (list "vkv" "Tinh van khuon mat vat" 'tog nil)
                           (list "bc" "Cot - canh theo X (mm)" 'real 400.0)
                           (list "hc" "Cot - canh theo Y (mm)" 'real 400.0)
                           (list "lot" "Be tong lot day (mm, 0 = khong)" 'real0 100.0)
                           (list "c" "Lop bao ve day mong (mm)" 'real 50.0)
                           (list "dx" "Thep day phuong X - duong kinh (mm)" 'real 14.0)
                           (list "ax" "Thep day phuong X - buoc (mm)" 'real 150.0)
                           (list "dy" "Thep day phuong Y - duong kinh (mm)" 'real 14.0)
                           (list "ay" "Thep day phuong Y - buoc (mm)" 'real 150.0)
                           (list "moc" "Thep day uon moc len 2 dau (10d)" 'tog t)
                           (list "cot" "Thep cho cot (vd 8d18; trong = khong)" 'str "8d18")
                           (list "dsc" "Dai cot trong mong (vd 3d8; trong = khong)" 'str "3d8"))
                     (sd:kt-fields))))
    (exit))
  (setq name (sd:v "name") A (sd:v "A") B (sd:v "B") H (sd:v "H") bc (sd:v "bc") hc (sd:v "hc") lot (sd:v "lot")
        c (sd:v "c") dx (sd:v "dx") ax (sd:v "ax") dy (sd:v "dy") ay (sd:v "ay") moc (sd:v "moc")
        cot (sd:opt-bar (sd:v "cot")) dsc (sd:opt-bar (sd:v "dsc"))
        k (sd:v "k") sc (float (sd:v "sc")) tm (sd:v "tm")
        *SD:FMN* name *SD:FMX* A *SD:FMY* B *SD:FMH* H
        hv (min (sd:v "hv") (- H c c)) *SD:FMHV* hv h1 (- H hv) a2 (+ bc 100.0) b2 (+ hc 100.0))
  (cond
    ((or (null cot) (null dsc)) (princ "\n[SD] Thep cho / dai cot sai dinh dang (vd 8d18)."))
    ((or (>= bc A) (>= hc B) (<= H (* 2 c))) (princ "\n[SD] Kich thuoc mong / cot khong hop le."))
    ((setq o (sd:getpt "\nDiem chen mat bang (goc trai duoi mong): " nil))
     (sd:kt-begin (sd:v "mk") name)
     (setq o (sd:w o)
           oa (sd:p+ o (+ A (* 40 sc)) 0) ob (sd:p+ oa (+ A (* 40 sc)) 0)
           hkx (if moc (min (- h1 c c) (sd:ceil (max (* 10 dx) 100.0) 10.0)) 0.0)
           hky (if moc (min (- h1 c c) (sd:ceil (max (* 10 dy) 100.0) 10.0)) 0.0)
           yb (+ c dx dy))
     ;; ---- mat bang
     (sd:rect o A B "SD-BETONG")
     (sd:rect (sd:p+ o (/ (- A bc) 2.0) (/ (- B hc) 2.0)) bc hc "SD-BETONG")
     ;; mong vat: mat tren a2 x b2 (go 50 quanh cot) + 4 duong mep vat
     (if (> hv 0)
       (progn
         (sd:rect (sd:p+ o (/ (- A a2) 2.0) (/ (- B b2) 2.0)) a2 b2 "SD-BETONG")
         (foreach q (list (list 0.0 0.0 -1 -1) (list A 0.0 1 -1) (list A B 1 1) (list 0.0 B -1 1))
           (sd:line (sd:p+ o (car q) (cadr q)) (sd:p+ o (+ (/ A 2.0) (* (caddr q) (/ a2 2.0))) (+ (/ B 2.0) (* (cadddr q) (/ b2 2.0))))
                    "SD-BETONG"))))
     (if (> lot 0) (sd:rect (sd:p+ o -100 -100) (+ A 200) (+ B 200) "SD-KHUAT"))
     (setq y (+ c (/ dx 2.0)))
     (while (<= y (- B c -1)) (sd:line (sd:p+ o c y) (sd:p+ o (- A c) y) "SD-THEP-DAI") (setq y (+ y ax)))
     (setq x (+ c (/ dy 2.0)))
     (while (<= x (- A c -1)) (sd:line (sd:p+ o x c) (sd:p+ o x (- B c)) "SD-THEP-DAI") (setq x (+ x ay)))
     (sd:use-dimstyle sc)
     (sd:dim o (sd:p+ o A 0) "H" (sd:p+ o 0 (* -10 sc)))
     (sd:dim o (sd:p+ o 0 B) "V" (sd:p+ o (* -10 sc) 0))
     (sd:kt-cutmark (sd:p+ o -150 (/ B 2.0)) pi "A" sc)
     (sd:kt-cutmark (sd:p+ o (+ A 150) (/ B 2.0)) 0.0 "A" sc)
     (sd:kt-cutmark (sd:p+ o (/ A 2.0) -150) (* 1.5 pi) "B" sc)
     (sd:kt-cutmark (sd:p+ o (/ A 2.0) (+ B 150)) (/ pi 2) "B" sc)
     ;; be tong: phan hop A.B.h1 + phan vat (lang tru cut, cong thuc prismoid); van khuon thanh dung (+ mat vat)
     (setq v (/ (+ (* A B h1) (* (/ hv 6.0) (+ (* A B) (* a2 b2) (* 4.0 (/ (+ A a2) 2.0) (/ (+ B b2) 2.0))))) 1e9)
           s (/ (+ (* 2.0 (+ A B) h1)
                   (if (and (> hv 0) (sd:v "vkv"))
                     (+ (* (+ A a2) (sqrt (+ (* hv hv) (expt (/ (- B b2) 2.0) 2))))
                        (* (+ B b2) (sqrt (+ (* hv hv) (expt (/ (- A a2) 2.0) 2)))))
                     0.0))
                1e6))
     (sd:ck-title (sd:p+ o (/ A 2.0) (* -22 sc)) (strcat "M\\U+1EB6T B\\U+1EB0NG M\\U+00D3NG " name " (" (sd:num A) "\\U+00D7" (sd:num B) "\\U+00D7" (sd:num H)
                                                          (if (> hv 0) (strcat ", v\\U+00E1t " (sd:num hv)) "") ")")
                  sc name "Mong" k v s (strcat (sd:num A) "x" (sd:num B) "x" (sd:num H) (if (> hv 0) (strcat " vat " (sd:num hv)) "")))
     (if (> lot 0)
       (sd:ck-title (sd:p+ o (/ A 2.0) (* -28 sc)) (strcat "B\\U+00EA t\\U+00F4ng l\\U+00F3t d\\U+00E0y " (sd:num lot))
                    sc (strcat name "-LOT") "Be tong lot" k (/ (* (+ A 200) (+ B 200) lot) 1e9) 0.0
                    (strcat (sd:num (+ A 200)) "x" (sd:num (+ B 200)) "x" (sd:num lot))))
     ;; ---- mat cat A-A (doc theo X) va B-B (doc theo Y)
     (setq lap (if (listp cot) (sd:lap (cadr cot)) 0.0))
     (foreach sec (list (list oa A bc "A-A" dx ax hkx dy ay (list (* 0.35 A) (+ c (/ dx 2.0)) (* 0.35 A) (- B c (/ dx 2.0))))
                        (list ob B hc "B-B" dy ay hky dx ax (list (+ c (/ dy 2.0)) (* 0.35 B) (- A c (/ dy 2.0)) (* 0.35 B))))
       (setq e (car sec) x (cadr sec))
       ;; be tong: mong, lot, co cot
       (if (> hv 0)
         (sd:pline (mapcar '(lambda (p) (sd:p+ e (car p) (cadr p)))
                           (list (list 0.0 0.0) (list x 0.0) (list x h1) (list (/ (+ x (caddr sec) 100.0) 2.0) H)
                                 (list (/ (- x (caddr sec) 100.0) 2.0) H) (list 0.0 h1)))
                   t "SD-BETONG")
         (sd:rect e x H "SD-BETONG"))
       (if (> lot 0) (sd:rect (sd:p+ e -100 (- lot)) (+ x 200) lot "SD-BETONG"))
       ;; thanh chinh cua mat cat (thong minh, rai theo duong phan bo tren mat bang)
       (setq yt (if (= (cadddr sec) "A-A") (+ c (/ dx 2.0)) (+ c dx (/ dy 2.0))))
       (sd:kt-bar e (if moc
                      (list (list c (+ yt (nth 6 sec))) (list c yt) (list (- x c) yt) (list (- x c) (+ yt (nth 6 sec))))
                      (list (list c yt) (list (- x c) yt)))
                  0 (nth 4 sec) (list (* 0.25 x) yt) (list (+ (* 0.25 x) (* 4 sc)) (+ H (* 8 sc))) k tm sc
                  (list (mapcar '- (list (car (nth 9 sec)) (cadr (nth 9 sec))) (list (car (mapcar '- e o)) (cadr (mapcar '- e o))))
                        (mapcar '- (list (caddr (nth 9 sec)) (cadddr (nth 9 sec))) (list (car (mapcar '- e o)) (cadr (mapcar '- e o)))))
                  (nth 5 sec))
       ;; thanh phuong kia: cham
       (setq y (if (= (cadddr sec) "A-A") (+ c dx (/ dy 2.0)) (+ c (/ dx 2.0))) xs (+ c (/ (nth 7 sec) 2.0)))
       (while (<= xs (- x c -1)) (sd:dot (sd:p+ e xs y) (nth 7 sec) "SD-THEP-CHU") (setq xs (+ xs (nth 8 sec))))
       ;; co cot: thep cho + dai cot trong mong
       (sd:kt-colstub e x (caddr sec) H yb (+ c 50.0) lap cot dsc bc hc (= (cadddr sec) "A-A") k tm sc)
       ;; kich thuoc + ten mat cat
       (sd:dim e (sd:p+ e x 0) "H" (sd:p+ e 0 (- (+ lot (* 8 sc)))))
       (sd:dim (sd:p+ e x 0) (sd:p+ e x H) "V" (sd:p+ e (+ x (* 8 sc)) 0))
       (if (> hv 0) (sd:dim e (sd:p+ e 0 h1) "V" (sd:p+ e (* -8 sc) 0)))
       (sd:text (sd:p+ e (/ x 2.0) (- (+ lot (* 20 sc)))) (strcat "M\\U+1EB6T C\\U+1EAET " (cadddr sec)) (* 3.5 sc) "MC" "SD-CHU"))
     (sd:use-dimstyle *SD:SCALE*)
     (sd:kt-end)))
  (sd:finish))

;;; --------------------------------------------------------------------------
;;;  SDMONGBANG - Khai trien mong bang (tiet dien chu T nguoc): ban mong co vat + suon (dam mong)
;;;  Mat bang doan mong + mat cat ngang. Thep ngang ban (chiu luc, moc 10d) rai doc mong theo duong phan bo;
;;;  thep doc ban (phan bo), thep suon tren / duoi, dai suon.
;;; --------------------------------------------------------------------------
(defun c:SDMONGBANG (/ name L B hb hv bs hs lot c dn an dd ad st sb ds as k sc tm o e x y hk yb ytop sec ar v s
                       xl xr nd ns n)
  (sd:begin)
  (if (not (sd:dlg "Khai trien mong bang (SDMONGBANG)"
                   (append
                     (list (list "name" "Ten mong bang" 'str (cond (*SD:MBN*) ("MB1")))
                           (list "L" "Chieu dai doan mong (mm)" 'real (cond (*SD:MBL*) (6000.0)))
                           (list "B" "Be rong ban mong (mm)" 'real (cond (*SD:MBB*) (1400.0)))
                           (list "hb" "Chieu day ban tai mep (mm)" 'real 300.0)
                           (list "hv" "Chieu cao phan vat ban (mm, 0 = khong)" 'real0 150.0)
                           (list "bs" "Be rong suon / dam mong (mm)" 'real 400.0)
                           (list "hs" "Chieu cao suon tu day mong (mm, 0 = khong suon)" 'real0 900.0)
                           (list "lot" "Be tong lot day (mm, 0 = khong)" 'real0 100.0)
                           (list "c" "Lop bao ve (mm)" 'real 50.0)
                           (list "dn" "Thep ngang ban (chiu luc) - d (mm)" 'real 14.0)
                           (list "an" "Thep ngang ban - buoc (mm)" 'real 150.0)
                           (list "dd" "Thep doc ban (phan bo) - d (mm)" 'real 10.0)
                           (list "ad" "Thep doc ban - buoc (mm)" 'real 200.0)
                           (list "st" "Thep suon tren (vd 4d20; trong = khong)" 'str "4d20")
                           (list "sb" "Thep suon duoi (vd 4d20; trong = khong)" 'str "4d20")
                           (list "ds" "Dai suon - d (mm)" 'real 8.0)
                           (list "as" "Dai suon - buoc (mm)" 'real 200.0)
                           (list "vkv" "Tinh van khuon mat vat" 'tog nil))
                     (sd:kt-fields))))
    (exit))
  (setq name (sd:v "name") L (sd:v "L") B (sd:v "B") hb (sd:v "hb") hv (sd:v "hv") bs (sd:v "bs") hs (sd:v "hs")
        lot (sd:v "lot") c (sd:v "c") dn (sd:v "dn") an (sd:v "an") dd (sd:v "dd") ad (sd:v "ad")
        st (sd:opt-bar (sd:v "st")) sb (sd:opt-bar (sd:v "sb")) ds (sd:v "ds") as (sd:v "as")
        k (sd:v "k") sc (float (sd:v "sc")) tm (sd:v "tm")
        *SD:MBN* name *SD:MBL* L *SD:MBB* B)
  (cond
    ((or (null st) (null sb)) (princ "\n[SD] Thep suon sai dinh dang (vd 4d20)."))
    ((or (>= bs B) (<= hb (* 2 c)) (and (> hs 0) (< hs (+ hb hv 100)))) (princ "\n[SD] Kich thuoc mong bang khong hop le."))
    ((setq o (sd:getpt "\nDiem chen mat bang (goc trai duoi doan mong): " nil))
     (sd:kt-begin (sd:v "mk") name)
     (setq o (sd:w o) e (sd:p+ o (+ L (* 40 sc)) 0)
           ytop (if (> hs 0) hs (+ hb hv)) xl (/ (- B bs) 2.0) xr (/ (+ B bs) 2.0)
           hk (min (- hb c c) (sd:ceil (max (* 10 dn) 100.0) 10.0))
           sec (list (list 0.0 0.0) (list B 0.0) (list B hb) (list xr (+ hb hv)) (list xr ytop) (list xl ytop) (list xl (+ hb hv)) (list 0.0 hb))
           ar (sd:poly-area sec)
           yb (+ c dn dd))
     ;; ---- mat bang: ban, suon (net khuat), luoi thep
     (sd:rect o L B "SD-BETONG")
     (sd:line (sd:p+ o 0 xl) (sd:p+ o L xl) "SD-KHUAT")
     (sd:line (sd:p+ o 0 xr) (sd:p+ o L xr) "SD-KHUAT")
     (if (> lot 0) (sd:rect (sd:p+ o 0 -100) L (+ B 200) "SD-KHUAT"))
     (setq x (+ c (/ dn 2.0)))
     (while (<= x (- L c -1)) (sd:line (sd:p+ o x c) (sd:p+ o x (- B c)) "SD-THEP-DAI") (setq x (+ x an)))
     ;; thep doc ban: 1 thanh dai dien (so thanh = so cham tren mat cat)
     (setq nd (1+ (fix (/ (- B c c dd) ad))))
     (sd:kt-bar o (list (list c (+ c dn (/ dd 2.0))) (list (- L c) (+ c dn (/ dd 2.0)))) nd dd
                (list (* 0.6 L) (+ c dn (/ dd 2.0))) (list (+ (* 0.6 L) (* 4 sc)) (* -8 sc)) k tm sc nil 0.0)
     ;; thep suon tren / duoi (doc mong)
     (if (and (> hs 0) (listp st))
       (sd:kt-bar o (list (list c (+ xl c ds (/ (cadr st) 2.0))) (list (- L c) (+ xl c ds (/ (cadr st) 2.0)))) (car st) (cadr st)
                  (list (* 0.75 L) (+ xl c ds)) (list (+ (* 0.75 L) (* 4 sc)) (+ B (* 6 sc))) k tm sc nil 0.0))
     (if (and (> hs 0) (listp sb))
       (sd:kt-bar o (list (list c (- xr c ds (/ (cadr sb) 2.0))) (list (- L c) (- xr c ds (/ (cadr sb) 2.0)))) (car sb) (cadr sb)
                  (list (* 0.45 L) (- xr c ds)) (list (+ (* 0.45 L) (* 4 sc)) (+ B (* 12 sc))) k tm sc nil 0.0))
     (sd:use-dimstyle sc)
     (sd:dim o (sd:p+ o L 0) "H" (sd:p+ o 0 (- (+ 100 (* 16 sc)))))
     (sd:dim o (sd:p+ o 0 B) "V" (sd:p+ o (* -10 sc) 0))
     (sd:kt-cutmark (sd:p+ o (* 0.2 L) -150) (* 1.5 pi) "A" sc)
     (sd:kt-cutmark (sd:p+ o (* 0.2 L) (+ B 150)) (/ pi 2) "A" sc)
     ;; ---- khoi luong: mat cat x L; van khuon 2 thanh ban + 2 thanh suon + 2 dau doan (+ mat vat)
     (setq v (/ (* ar L) 1e9)
           s (/ (+ (* 2.0 L (+ hb (if (> hs 0) (- hs hb hv) 0.0))) (* 2.0 ar)
                   (if (and (> hv 0) (sd:v "vkv")) (* 2.0 L (sqrt (+ (* hv hv) (* xl xl)))) 0.0))
                1e6))
     (sd:ck-title (sd:p+ o (/ L 2.0) (- (+ 100 (* 28 sc))))
                  (strcat "M\\U+1EB6T B\\U+1EB0NG M\\U+00D3NG B\\U+0102NG " name " (L=" (sd:num L) ", B=" (sd:num B) ")")
                  sc name "Mong" k v s (strcat "bang L=" (sd:num L) ", B=" (sd:num B) ", h=" (sd:num ytop)))
     (if (> lot 0)
       (sd:ck-title (sd:p+ o (/ L 2.0) (- (+ 100 (* 34 sc)))) (strcat "B\\U+00EA t\\U+00F4ng l\\U+00F3t d\\U+00E0y " (sd:num lot))
                    sc (strcat name "-LOT") "Be tong lot" k (/ (* L (+ B 200) lot) 1e9) 0.0
                    (strcat (sd:num L) "x" (sd:num (+ B 200)) "x" (sd:num lot))))
     ;; ---- mat cat A-A
     (sd:pline (mapcar '(lambda (p) (sd:p+ e (car p) (cadr p))) sec) t "SD-BETONG")
     (if (> lot 0) (sd:rect (sd:p+ e -100 (- lot)) (+ B 200) lot "SD-BETONG"))
     ;; thep ngang ban (thong minh, rai doc mong theo duong phan bo tren mat bang)
     (setq y (+ c (/ dn 2.0)))
     (sd:kt-bar e (list (list c (+ y hk)) (list c y) (list (- B c) y) (list (- B c) (+ y hk))) 0 dn
                (list (* 0.2 B) y) (list (+ (* 0.2 B) (* 4 sc)) (+ ytop (* 8 sc))) k tm sc
                (list (list (- (+ c (/ dn 2.0)) (+ L (* 40 sc))) (* 0.85 B)) (list (- (- L c (/ dn 2.0)) (+ L (* 40 sc))) (* 0.85 B)))
                an)
     ;; thep doc ban: cham
     (setq x (+ c (/ dd 2.0)))
     (while (<= x (- B c -1)) (sd:dot (sd:p+ e x (+ c dn (/ dd 2.0))) dd "SD-THEP-CHU") (setq x (+ x ad)))
     ;; suon: dai + thep tren / duoi
     (if (> hs 0)
       (progn
         (sd:plinew (list (sd:p+ e (+ xl c) (+ c dn)) (sd:p+ e (- xr c) (+ c dn)) (sd:p+ e (- xr c) (- hs c)) (sd:p+ e (+ xl c) (- hs c)))
                    t ds "SD-THEP-DAI")
         (if (listp st) (sd:barrow (sd:p+ e xl 0) bs c ds (car st) (cadr st) (- hs c ds (/ (cadr st) 2.0))))
         (if (listp sb) (sd:barrow (sd:p+ e xl 0) bs c ds (car sb) (cadr sb) (+ yb (/ (cadr sb) 2.0))))
         ;; duong phan bo dai suon tren mat bang (50 .. L-50): keo dai doan mong -> so dai tu tinh lai
         (sd:kt-dist e (list (- xr c) (/ (+ hs hb) 2.0)) (list (+ B (* 4 sc)) (/ (+ hs hb) 2.0)) ds "Dai"
                     (list (- bs c c) (- hs c c dn)) k sc tm 1 as nil
                     (list (sd:kt-dline (sd:p+ o 50.0 (/ B 2.0)) (sd:p+ o (- L 50.0) (/ B 2.0)) sc)))))
     (sd:dim e (sd:p+ e B 0) "H" (sd:p+ e 0 (- (+ lot (* 8 sc)))))
     (sd:dim (sd:p+ e B 0) (sd:p+ e B hb) "V" (sd:p+ e (+ B (* 8 sc)) 0))
     (sd:dim e (sd:p+ e 0 ytop) "V" (sd:p+ e (* -8 sc) 0))
     (if (> hs 0) (sd:dim (sd:p+ e xl ytop) (sd:p+ e xr ytop) "H" (sd:p+ e 0 (+ ytop (* 4 sc)))))
     (sd:text (sd:p+ e (/ B 2.0) (- (+ lot (* 20 sc)))) "M\\U+1EB6T C\\U+1EAET A-A" (* 3.5 sc) "MC" "SD-CHU")
     (sd:use-dimstyle *SD:SCALE*)
     (sd:kt-end)))
  (sd:finish))

;;; --------------------------------------------------------------------------
;;;  SDDAICOC - Khai trien dai coc: mat bang (luoi coc, luoi thep) + mat cat A-A, B-B
;;;  Luoi day dat tren dau coc (doan coc ngam + lop bao ve), moc len 10d hoac het chieu cao;
;;;  luoi tren tuy chon; thep cho + dai cot dung chung voi mong don.
;;; --------------------------------------------------------------------------
(defun c:SDDAICOC (/ name A B H bc hc nx ny sx sy dc tron hn lot c dx ax dy ay moc trn dt at cot dsc k sc tm o oa ob
                     xs ys x y e sec hkx hky y0 yb lap v s np)
  (sd:begin)
  (if (not (sd:dlg "Khai trien dai coc (SDDAICOC)"
                   (append
                     (list (list "name" "Ten dai coc" 'str (cond (*SD:DCN*) ("DC1")))
                           (list "A" "Canh A - theo X (mm)" 'real (cond (*SD:DCA*) (2000.0)))
                           (list "B" "Canh B - theo Y (mm)" 'real (cond (*SD:DCB*) (2000.0)))
                           (list "H" "Chieu cao dai (mm)" 'real (cond (*SD:DCH*) (1000.0)))
                           (list "bc" "Cot - canh theo X (mm)" 'real 400.0)
                           (list "hc" "Cot - canh theo Y (mm)" 'real 400.0)
                           (list "nx" "So coc theo X" 'int 2)
                           (list "ny" "So coc theo Y" 'int 2)
                           (list "sx" "Khoang cach coc theo X (mm)" 'real 1200.0)
                           (list "sy" "Khoang cach coc theo Y (mm)" 'real 1200.0)
                           (list "dc" "Canh / duong kinh coc (mm)" 'real 300.0)
                           (list "hinh" "Tiet dien coc" 'kw "Vuong" '(("Vuong" . "Vuong") ("Tron" . "Tron")))
                           (list "hn" "Doan coc ngam vao dai (mm)" 'real0 100.0)
                           (list "tru" "Tru the tich dau coc ngam khoi be tong dai" 'tog t)
                           (list "lot" "Be tong lot day (mm, 0 = khong)" 'real0 100.0)
                           (list "c" "Lop bao ve (tren dau coc / mat tren) (mm)" 'real 50.0)
                           (list "dx" "Luoi day phuong X - d (mm)" 'real 16.0)
                           (list "ax" "Luoi day phuong X - buoc (mm)" 'real 150.0)
                           (list "dy" "Luoi day phuong Y - d (mm)" 'real 16.0)
                           (list "ay" "Luoi day phuong Y - buoc (mm)" 'real 150.0)
                           (list "moc" "Luoi day uon len" 'kw "10d" '(("10d" . "Moc 10d") ("Het" . "Het chieu cao dai")))
                           (list "trn" "Co luoi thep tren" 'tog nil)
                           (list "dt" "Luoi tren - d (mm)" 'real 12.0)
                           (list "at" "Luoi tren - buoc (mm)" 'real 200.0)
                           (list "cot" "Thep cho cot (vd 8d18; trong = khong)" 'str "8d18")
                           (list "dsc" "Dai cot trong dai (vd 3d8; trong = khong)" 'str "3d8"))
                     (sd:kt-fields))))
    (exit))
  (setq name (sd:v "name") A (sd:v "A") B (sd:v "B") H (sd:v "H") bc (sd:v "bc") hc (sd:v "hc")
        nx (max 1 (sd:v "nx")) ny (max 1 (sd:v "ny")) sx (sd:v "sx") sy (sd:v "sy") dc (sd:v "dc")
        tron (= (sd:v "hinh") "Tron") hn (sd:v "hn") lot (sd:v "lot") c (sd:v "c")
        dx (sd:v "dx") ax (sd:v "ax") dy (sd:v "dy") ay (sd:v "ay") moc (sd:v "moc") trn (sd:v "trn")
        dt (sd:v "dt") at (sd:v "at") cot (sd:opt-bar (sd:v "cot")) dsc (sd:opt-bar (sd:v "dsc"))
        k (sd:v "k") sc (float (sd:v "sc")) tm (sd:v "tm")
        *SD:DCN* name *SD:DCA* A *SD:DCB* B *SD:DCH* H)
  ;; vi tri tim coc (doi xung quanh tam dai)
  (setq xs (mapcar '(lambda (i) (+ (/ A 2.0) (* (- i (/ (1- nx) 2.0)) sx))) (sd:range 0 (1- nx)))
        ys (mapcar '(lambda (i) (+ (/ B 2.0) (* (- i (/ (1- ny) 2.0)) sy))) (sd:range 0 (1- ny))))
  (cond
    ((or (null cot) (null dsc)) (princ "\n[SD] Thep cho / dai cot sai dinh dang (vd 8d18)."))
    ((or (< (- (car xs) (/ dc 2.0)) 0) (< (- (car ys) (/ dc 2.0)) 0) (>= (+ hn c c dx dy) H))
     (princ "\n[SD] Luoi coc vuot ra ngoai dai hoac dai qua thap."))
    ((setq o (sd:getpt "\nDiem chen mat bang (goc trai duoi dai): " nil))
     (sd:kt-begin (sd:v "mk") name)
     (setq o (sd:w o) oa (sd:p+ o (+ A (* 40 sc)) 0) ob (sd:p+ oa (+ A (* 40 sc)) 0)
           y0 (+ hn c) yb (+ y0 dx dy) np (* nx ny)
           hkx (if (= moc "Het") (- H y0 c (/ dx 2.0)) (min (- H y0 c) (sd:ceil (max (* 10 dx) 100.0) 10.0)))
           hky (if (= moc "Het") (- H y0 dx c (/ dy 2.0)) (min (- H y0 c) (sd:ceil (max (* 10 dy) 100.0) 10.0)))
           lap (if (listp cot) (sd:lap (cadr cot)) 0.0))
     ;; ---- mat bang
     (sd:rect o A B "SD-BETONG")
     (sd:rect (sd:p+ o (/ (- A bc) 2.0) (/ (- B hc) 2.0)) bc hc "SD-BETONG")
     (if (> lot 0) (sd:rect (sd:p+ o -100 -100) (+ A 200) (+ B 200) "SD-KHUAT"))
     (foreach px xs
       (foreach py ys
         (if tron
           (sd:circle (sd:p+ o px py) (/ dc 2.0) "SD-KHUAT")
           (sd:rect (sd:p+ o (- px (/ dc 2.0)) (- py (/ dc 2.0))) dc dc "SD-KHUAT"))
         (sd:line (sd:p+ o (- px 100) py) (sd:p+ o (+ px 100) py) "SD-TRUC")
         (sd:line (sd:p+ o px (- py 100)) (sd:p+ o px (+ py 100)) "SD-TRUC")))
     (setq y (+ c (/ dx 2.0)))
     (while (<= y (- B c -1)) (sd:line (sd:p+ o c y) (sd:p+ o (- A c) y) "SD-THEP-DAI") (setq y (+ y ax)))
     (setq x (+ c (/ dy 2.0)))
     (while (<= x (- A c -1)) (sd:line (sd:p+ o x c) (sd:p+ o x (- B c)) "SD-THEP-DAI") (setq x (+ x ay)))
     (sd:use-dimstyle sc)
     (sd:dim o (sd:p+ o A 0) "H" (sd:p+ o 0 (* -10 sc)))
     (sd:dim o (sd:p+ o 0 B) "V" (sd:p+ o (* -10 sc) 0))
     (if (> nx 1) (sd:dimchain (mapcar '(lambda (px) (sd:p+ o px 0)) (append (list 0.0) xs (list A))) "H" (sd:p+ o 0 (* -5 sc))))
     (if (> ny 1) (sd:dimchain (mapcar '(lambda (py) (sd:p+ o 0 py)) (append (list 0.0) ys (list B))) "V" (sd:p+ o (* -5 sc) 0)))
     (sd:kt-cutmark (sd:p+ o -150 (car ys)) pi "A" sc)
     (sd:kt-cutmark (sd:p+ o (+ A 150) (car ys)) 0.0 "A" sc)
     (sd:kt-cutmark (sd:p+ o (car xs) -150) (* 1.5 pi) "B" sc)
     (sd:kt-cutmark (sd:p+ o (car xs) (+ B 150)) (/ pi 2) "B" sc)
     ;; ---- khoi luong
     (setq v (/ (- (* A B H) (if (sd:v "tru") (* np hn (if tron (* pi 0.25 dc dc) (* dc dc))) 0.0)) 1e9)
           s (/ (* 2.0 (+ A B) H) 1e6))
     (sd:ck-title (sd:p+ o (/ A 2.0) (* -22 sc))
                  (strcat "M\\U+1EB6T B\\U+1EB0NG \\U+0110\\U+00C0I C\\U+1ECCC " name " (" (sd:num A) "\\U+00D7" (sd:num B) "\\U+00D7" (sd:num H) ", " (itoa np) " c\\U+1ECDc)")
                  sc name "Mong" k v s (strcat "dai " (sd:num A) "x" (sd:num B) "x" (sd:num H) ", " (itoa np) " coc"
                                               (if (sd:v "tru") " (tru dau coc)" "")))
     (if (> lot 0)
       (sd:ck-title (sd:p+ o (/ A 2.0) (* -28 sc)) (strcat "B\\U+00EA t\\U+00F4ng l\\U+00F3t d\\U+00E0y " (sd:num lot))
                    sc (strcat name "-LOT") "Be tong lot" k (/ (* (+ A 200) (+ B 200) lot) 1e9) 0.0
                    (strcat (sd:num (+ A 200)) "x" (sd:num (+ B 200)) "x" (sd:num lot))))
     ;; ---- mat cat A-A (doc X, qua hang coc dau) va B-B (doc Y)
     (foreach sec (list (list oa A bc "A-A" dx ax hkx dy ay xs (list (* 0.5 A) (+ c (/ dx 2.0)) (* 0.5 A) (- B c (/ dx 2.0))) y0)
                        (list ob B hc "B-B" dy ay hky dx ax ys (list (+ c (/ dy 2.0)) (* 0.5 B) (- A c (/ dy 2.0)) (* 0.5 B)) (+ y0 dx)))
       (setq e (car sec) x (cadr sec))
       (sd:rect e x H "SD-BETONG")
       (if (> lot 0) (sd:rect (sd:p+ e -100 (- lot)) (+ x 200) lot "SD-BETONG"))
       ;; coc: ngam hn vao dai, cat net duoi day
       (foreach p (nth 9 sec)
         (sd:line (sd:p+ e (- p (/ dc 2.0)) hn) (sd:p+ e (- p (/ dc 2.0)) (- (+ lot 600))) "SD-BETONG")
         (sd:line (sd:p+ e (+ p (/ dc 2.0)) hn) (sd:p+ e (+ p (/ dc 2.0)) (- (+ lot 600))) "SD-BETONG")
         (sd:line (sd:p+ e (- p (/ dc 2.0)) hn) (sd:p+ e (+ p (/ dc 2.0)) hn) "SD-BETONG")
         (sd:zig e (- p (/ dc 2.0)) (+ p (/ dc 2.0)) (- (+ lot 600)) sc))
       ;; luoi day (thong minh, rai theo duong phan bo tren mat bang)
       (setq y (+ (nth 11 sec) (/ (nth 4 sec) 2.0)))
       (sd:kt-bar e (list (list c (+ y (nth 6 sec))) (list c y) (list (- x c) y) (list (- x c) (+ y (nth 6 sec)))) 0 (nth 4 sec)
                  (list (* 0.3 x) y) (list (+ (* 0.3 x) (* 4 sc)) (+ H (* 8 sc))) k tm sc
                  (list (mapcar '- (list (car (nth 10 sec)) (cadr (nth 10 sec))) (list (car (mapcar '- e o)) (cadr (mapcar '- e o))))
                        (mapcar '- (list (caddr (nth 10 sec)) (cadddr (nth 10 sec))) (list (car (mapcar '- e o)) (cadr (mapcar '- e o)))))
                  (nth 5 sec))
       ;; luoi day phuong kia: cham
       (setq y (if (= (cadddr sec) "A-A") (+ y0 dx (/ dy 2.0)) (+ y0 (/ dx 2.0))) x (+ c (/ (nth 7 sec) 2.0)))
       (while (<= x (- (cadr sec) c -1)) (sd:dot (sd:p+ e x y) (nth 7 sec) "SD-THEP-CHU") (setq x (+ x (nth 8 sec))))
       (setq x (cadr sec))
       ;; luoi tren: thanh thang (thong minh, so thanh co dinh theo be rong)
       (if trn
         (sd:kt-bar e (list (list c (- H c (/ dt 2.0))) (list (- x c) (- H c (/ dt 2.0))))
                    (1+ (fix (/ (- (if (= (cadddr sec) "A-A") B A) c c) at))) dt
                    (list (* 0.75 x) (- H c (/ dt 2.0))) (list (+ (* 0.75 x) (* 4 sc)) (+ H (* 14 sc))) k tm sc nil 0.0))
       ;; co cot: thep cho dat tren luoi day + dai
       (sd:kt-colstub e x (caddr sec) H yb (+ yb 50.0) lap cot dsc bc hc (= (cadddr sec) "A-A") k tm sc)
       (sd:dim e (sd:p+ e x 0) "H" (sd:p+ e 0 (- (+ lot 600 (* 8 sc)))))
       (sd:dim (sd:p+ e x 0) (sd:p+ e x H) "V" (sd:p+ e (+ x (* 8 sc)) 0))
       (sd:text (sd:p+ e (/ x 2.0) (- (+ lot 600 (* 20 sc)))) (strcat "M\\U+1EB6T C\\U+1EAET " (cadddr sec)) (* 3.5 sc) "MC" "SD-CHU"))
     (sd:use-dimstyle *SD:SCALE*)
     (sd:kt-end)))
  (sd:finish))

;;; --------------------------------------------------------------------------
;;;  SDCOTTHEP - Khai trien thep cot 1 tang: mat dung + mat cat
;;;  Thep doc vuon len noi chong voi cot tang tren; dai day vung toi han max(b, h, Hn/6, 450)
;;;  o chan / dinh cot va trong nut dam, giua cot buoc thua.
;;; --------------------------------------------------------------------------
(defun c:SDCOTTHEP (/ name b h Hf hd c nb nh d noi ds a1 a2 k sc tm mc o hn lz x1 x2 yt lap y ys nst n so i g dl zs)
  (sd:begin)
  (if (not (sd:dlg "Khai trien thep cot (SDCOTTHEP)"
                   (append
                     (list (list "name" "Ten cot" 'str (cond (*SD:CNAME*) ("C1")))
                           (list "b" "Canh b - mat dung (mm)" 'real (cond (*SD:CB*) (300.0)))
                           (list "h" "Canh h - vuong goc (mm)" 'real (cond (*SD:CH*) (400.0)))
                           (list "Hf" "Chieu cao tang (san - san) (mm)" 'real (cond (*SD:CHF*) (3600.0)))
                           (list "hd" "Chieu cao dam tai dinh cot (mm)" 'real 500.0)
                           (list "c" "Lop bao ve (mm)" 'real 25.0)
                           (list "nb" "So thanh canh b (ke ca goc)" 'int 3)
                           (list "nh" "So thanh canh h (ke ca goc)" 'int 3)
                           (list "d" "Duong kinh thep doc (mm)" 'real 18.0)
                           (list "noi" "Thep vuon len noi chong voi cot tang tren" 'tog t)
                           (list "ds" "Duong kinh dai (mm)" 'real 8.0)
                           (list "a1" "Buoc dai vung toi han / nut (mm)" 'real 100.0)
                           (list "a2" "Buoc dai giua cot (mm)" 'real 200.0)
                           (list "vtc" "Vi tri cot (van khuon nut dam)" 'kw "Giua"
                                 '(("Giua" . "Cot giua - dam 4 phia") ("Bien" . "Cot bien - dam 3 phia") ("Goc" . "Cot goc - dam 2 phia")))
                           (list "mc" "Ve mat cat cot" 'tog t))
                     (sd:tie-fields)
                     (sd:kt-fields))))
    (exit))
  (setq name (sd:v "name") b (sd:v "b") h (sd:v "h") Hf (sd:v "Hf") hd (sd:v "hd") c (sd:v "c")
        nb (max 2 (sd:v "nb")) nh (max 2 (sd:v "nh")) d (sd:v "d") noi (sd:v "noi") ds (sd:v "ds")
        a1 (sd:v "a1") a2 (sd:v "a2") k (sd:v "k") sc (float (sd:v "sc")) tm (sd:v "tm") mc (sd:v "mc")
        *SD:CNAME* name *SD:CB* b *SD:CH* h *SD:CHF* Hf)
  (cond
    ((<= (- Hf hd) (* 4 a1)) (princ "\n[SD] Chieu cao cot thong thuy qua nho."))
    ((setq o (sd:getpt "\nDiem chen mat dung (chan cot, mep trai, cao do san): " nil))
     (sd:kt-begin (sd:v "mk") name)
     (setq o (sd:w o) hn (- Hf hd) lz (sd:col-lz b h hn)
           lap (if noi (sd:lap d) 0.0) x1 (+ c ds (/ d 2.0)) x2 (- b x1)
           yt (if noi (+ Hf lap) (- Hf c)) n (+ (* 2 nb) (* 2 (- nh 2))))
     ;; ---- be tong: cot duoi, san, cot, dam dinh, cot tren
     (sd:line (sd:p+ o 0 -500) (sd:p+ o 0 hn) "SD-BETONG")
     (sd:line (sd:p+ o b -500) (sd:p+ o b hn) "SD-BETONG")
     (sd:zig o 0 b -500 sc)
     (foreach y (list 0.0 -120.0)
       (sd:line (sd:p+ o -400 y) (sd:p+ o 0 y) "SD-BETONG")
       (sd:line (sd:p+ o b y) (sd:p+ o (+ b 400) y) "SD-BETONG"))
     (foreach y (list hn Hf)
       (sd:line (sd:p+ o -400 y) (sd:p+ o 0 y) "SD-BETONG")
       (sd:line (sd:p+ o b y) (sd:p+ o (+ b 400) y) "SD-BETONG"))
     (sd:line (sd:p+ o 0 Hf) (sd:p+ o 0 (+ yt 300)) "SD-BETONG")
     (sd:line (sd:p+ o b Hf) (sd:p+ o b (+ yt 300)) "SD-BETONG")
     (sd:zig o 0 b (+ yt 300) sc)
     ;; ---- thep doc tang duoi (vuon len noi) - chi the hien
     (sd:pline (list (sd:p+ o (+ x1 d) -500) (sd:p+ o (+ x1 d) lap)) nil "SD-THEP-CHU")
     (sd:pline (list (sd:p+ o (- x2 d) -500) (sd:p+ o (- x2 d) lap)) nil "SD-THEP-CHU")
     ;; ---- thep doc tang nay (thong minh) + thanh doi xung
     (sd:kt-bar o (list (list x1 0.0) (list x1 yt)) n d (list x1 (* 0.55 hn)) (list (* -30 sc) (* 0.6 hn)) k tm sc nil 0.0)
     (sd:pline (list (sd:p+ o x2 0) (sd:p+ o x2 yt)) nil "SD-THEP-CHU")
     ;; ---- dai: vung toi han chan / dinh, giua, nut dam
     (setq ys (sd:col-zone-ys hn hd c a1 a2 lz))
     (foreach y ys (sd:line (sd:p+ o c y) (sd:p+ o (- b c) y) "SD-THEP-DAI"))
     (setq nst (length ys)
           ;; duong phan bo dai = chieu cao thong thuy cot (STRETCH dinh / chan cot -> so dai theo vung tu tinh lai)
           dl (sd:kt-dline (sd:p+ o (/ b 2.0) 0) (sd:p+ o (/ b 2.0) hn) sc)
           zs (strcat (sd:nums->str (list hd c a1 a2 b h)) "|a" (sd:num a1) "/" (sd:num a2)))
     (sd:kt-dist o (list (- b c) (/ hn 2.0)) (list (+ b (* 6 sc)) (* 0.42 hn)) ds "Dai" (list (- b c c) (- h c c)) k sc tm
                 2 0.0 (strcat "COT|1," zs) (list dl))
     (foreach z (list (list (/ lz 2.0) a1) (list (/ hn 2.0) a2) (list (- hn (/ lz 2.0)) a1) (list (/ (+ hn Hf) 2.0) a1))
       (sd:text (sd:p+ o (+ b (* 3 sc)) (car z)) (strcat "%%c" (sd:num ds) "a" (sd:num (cadr z))) (* 2.0 sc) "ML" "SD-CHU"))
     ;; ---- kich thuoc
     (sd:use-dimstyle sc)
     (sd:dimchain (mapcar '(lambda (y) (sd:p+ o b y)) (list 0.0 lz (- hn lz) hn Hf)) "V" (sd:p+ o (+ b (* 24 sc)) 0))
     (sd:dim (sd:p+ o b 0) (sd:p+ o b Hf) "V" (sd:p+ o (+ b (* 32 sc)) 0))
     (if noi (sd:dim (sd:p+ o 0 Hf) (sd:p+ o 0 yt) "V" (sd:p+ o (* -10 sc) 0)))
     (sd:dim o (sd:p+ o b 0) "H" (sd:p+ o 0 (* -24 sc)))
     (sd:ck-title (sd:p+ o (/ b 2.0) (* -36 sc))
                  (strcat "M\\U+1EB6T \\U+0110\\U+1EE8NG TH\\U+00C9P C\\U+1ED8T " name " (" (sd:num b) "\\U+00D7" (sd:num h) ", H=" (sd:num Hf) ")")
                  ;; be tong: ca nut giao dam (b.h.H); van khuon: than cot den day dam + mat nut khong co dam
                  sc name "Cot" k (/ (* b h Hf) 1e9)
                  (/ (+ (* 2.0 (+ b h) hn) (cond ((= (sd:v "vtc") "Bien") (* b hd)) ((= (sd:v "vtc") "Goc") (* (+ b h) hd)) (0.0))) 1e6)
                  (strcat (sd:num b) "x" (sd:num h) "x" (sd:num Hf) " (gom nut dam)"
                          (cond ((= (sd:v "vtc") "Bien") ", VK nut 1 mat") ((= (sd:v "vtc") "Goc") ", VK nut 2 mat") (""))))
     ;; du lieu cho SDNOITHEP: chieu cao tang, dam dinh, thep doc (cot cung ten cac tang ghep thanh chong cot)
     (sd:noi-reg (entlast) (list "COT" name (float Hf) (float hd) n d c (if noi 1 0) k (cond (*SD:TANG*) (""))))
     ;; ---- mat cat
     (if mc
       (progn
         (setq so (sd:p+ o (+ b (* 50 sc)) (/ hn 2.0)))
         (sd:sec-common so b h c ds a2 sc (strcat "M\\U+1EB6T C\\U+1EAET " name))
         (setq x1 (+ c ds (/ d 2.0)))
         (sd:barrow so b c ds nb d x1)
         (sd:barrow so b c ds nb d (- h x1))
         (if (> nh 2)
           (progn (setq y 1)
                  (repeat (- nh 2)
                    (sd:dot (sd:p+ so x1 (+ x1 (* y (/ (- h x1 x1) (1- nh))))) d "SD-THEP-CHU")
                    (sd:dot (sd:p+ so (- b x1) (+ x1 (* y (/ (- h x1 x1) (1- nh))))) d "SD-THEP-CHU")
                    (setq y (1+ y)))))
         (sd:tagL (sd:p+ so x1 (- h x1)) (sd:p+ so (* -6 sc) (+ h (* 6 sc))) (strcat (itoa n) "%%c" (sd:num d)) sc)))
     ;; ---- dai phu / moc C: cung so lop voi dai chinh; ky hieu canh mat cat (hoac mat dung neu khong ve mat cat)
     (setq i 0)
     (foreach g (sd:col-ties (if mc so o) b h c ds nb nh d (sd:v "dp") (sd:v "lp") mc)
       (sd:kt-dist (if mc so o)
                   (if mc (nth 3 g) (list (/ b 2.0) (* 0.3 hn)))
                   (if mc (list (+ b (* 16 sc)) (- (* 0.3 h) (* i 7 sc))) (list (+ b (* 6 sc)) (- (* 0.3 hn) (* i 7 sc))))
                   ds (car g) (cadr g) k sc tm 2 0.0
                   (strcat "COT|" (itoa (nth 2 g)) "," zs (if (= (car g) "Mot") " moc C" " dai phu")) (list dl))
       (setq i (1+ i)))
     (sd:use-dimstyle *SD:SCALE*)
     (sd:kt-end)))
  (sd:finish))

;;; --------------------------------------------------------------------------
;;;  SDSANTHEP - Khai trien thep o san (mat bang): thep lop duoi 2 phuong, thep mu 4 canh
;;;  Thanh dai dien ve tren mat bang (thep mu ve ca chan gap vao mat bang) + duong phan bo:
;;;  so thanh = chieu dai duong phan bo / a + 1, tu cap nhat khi co keo.
;;; --------------------------------------------------------------------------
(defun sd:san-mu (o edge typ L bw lt leg pos d a k tm sc / s f in out pts dist hint)
  ;; edge: "T" trai (x=0), "P" phai (x=L), "D" duoi (y=0), "N" tren (y=L); pos = vi tri doc canh
  (setq s (if (member edge '("T" "D")) 1.0 -1.0)            ; huong vao o san
        f (if (member edge '("T" "D")) 0.0 L)                ; toa do truc dam
        in (+ f (* s (+ (/ bw 2.0) lt)))
        out (if (= typ "Bien") (- f (* s (- (/ bw 2.0) 25.0))) (- f (* s (+ (/ bw 2.0) lt)))))
  (if (member edge '("T" "P"))
    (setq pts (list (list out (- pos leg)) (list out pos) (list in pos) (list in (- pos leg)))
          hint (list (/ (+ f in) 2.0) pos))
    (setq pts (list (list (- pos leg) out) (list pos out) (list pos in) (list (- pos leg) in))
          hint (list pos (/ (+ f in) 2.0))))
  (list pts hint (+ f (* s (+ (/ bw 2.0) (* 0.6 lt))))))

;; ---- Phat hien thep mu trung giua cac o san ke nhau
;; Moi o san luu XDATA "SD_SAN" tren tieu de: ten + moi canh "canh|huong|truc|a|b|trang thai|lt" (toa do WCS):
;;  huong V (canh T/P, truc x = const, khoang theo y) / H (canh D/N, truc y = const, khoang theo x);
;;  a..b = khoang thep mu da rai doc canh; trang thai Lientuc (vat qua dam sang o ben) / Bien / Khong.
(defun sd:san-recs (/ ss i xd nm r)
  (setq i 0)
  (if (setq ss (ssget "_X" '((0 . "TEXT") (-3 ("SD_SAN")))))
    (repeat (sslength ss)
      (setq xd (mapcar 'cdr (cdadr (assoc -3 (entget (ssname ss i) '("SD_SAN"))))) i (1+ i) nm (car xd))
      (foreach e (cdr xd)
        (setq e (sd:split e "|")
              r (cons (list (nth 0 e) (nth 1 e) (atof (nth 2 e)) (atof (nth 3 e)) (atof (nth 4 e)) (nth 5 e) (atof (nth 6 e)) nm) r)))))
  r)

;; Cac doan [lo hi] cua canh (huong dir, truc ax, khoang a..b) da co thep mu vat sang tu canh doi dien cua o ke ben
;; -> ((lo hi lt ten) ...)
(defun sd:san-cover (edge dir ax a b recs / opp r lo hi)
  (setq opp (cdr (assoc edge '(("T" . "P") ("P" . "T") ("D" . "N") ("N" . "D")))))
  (foreach q recs
    (if (and (= (car q) opp) (= (cadr q) dir) (equal (caddr q) ax 1.0) (= (nth 5 q) "Lientuc")
             (< (setq lo (max a (nth 3 q))) (setq hi (min b (nth 4 q)))))
      (setq r (cons (list lo hi (nth 6 q) (nth 7 q)) r))))
  r)

;; Doan con trong [a b] khong bi phu boi cov -> doan dai nhat (lo hi) hoac nil
(defun sd:iv-free (a b cov / x best)
  (setq x a cov (sd:sort cov '(lambda (p q) (< (car p) (car q)))))
  (foreach c cov
    (if (> (- (car c) x) (if best (- (cadr best) (car best)) 0.0)) (setq best (list x (car c))))
    (setq x (max x (cadr c))))
  (if (> (- b x) (if best (- (cadr best) (car best)) 0.0)) (setq best (list x b)))
  best)

(defun c:SDSANTHEP (/ name Lx Ly bw t1 c dbx abx dby aby dt at kt k sc tm o x0 x1 y0 y1 lnx lny leg yb xb r e lt q
                      recs ed dir ax a b cov fr st mode pos sts)
  (sd:begin)
  (if (not (sd:dlg "Khai trien thep san (SDSANTHEP)"
                   (append
                     (list (list "name" "Ten o san" 'str (cond (*SD:SNAME*) ("S1")))
                           (list "Lx" "Nhip truc - truc theo X (mm)" 'real (cond (*SD:SLX*) (6000.0)))
                           (list "Ly" "Nhip truc - truc theo Y (mm)" 'real (cond (*SD:SLY*) (4500.0)))
                           (list "bw" "Be rong dam bao quanh (mm)" 'real 220.0)
                           (list "t" "Chieu day san (mm)" 'real 120.0)
                           (list "c" "Lop bao ve (mm)" 'real 20.0)
                           (list "dbx" "Thep duoi phuong X - d (mm)" 'real 8.0)
                           (list "abx" "Thep duoi phuong X - buoc (mm)" 'real 200.0)
                           (list "dby" "Thep duoi phuong Y - d (mm)" 'real 8.0)
                           (list "aby" "Thep duoi phuong Y - buoc (mm)" 'real 200.0)
                           (list "dt" "Thep mu - d (mm)" 'real 8.0)
                           (list "at" "Thep mu - buoc (mm)" 'real 200.0)
                           (list "lt" "Thep mu vuon tu mep dam" 'kw "1/4" '(("1/4" . "Ln/4") ("1/3" . "Ln/3")))
                           (list "eT" "Canh trai (truc dau X)" 'kw "Tudong"
                                 '(("Tudong" . "Tu dong - bo qua phan o ke ben da co thep mu") ("Lientuc" . "Lien tuc - vat qua dam")
                                   ("Bien" . "Bien - neo vao dam") ("Khong" . "Khong ve")))
                           (list "eP" "Canh phai" 'kw "Tudong"
                                 '(("Tudong" . "Tu dong - bo qua phan o ke ben da co thep mu") ("Lientuc" . "Lien tuc - vat qua dam")
                                   ("Bien" . "Bien - neo vao dam") ("Khong" . "Khong ve")))
                           (list "eD" "Canh duoi (truc dau Y)" 'kw "Tudong"
                                 '(("Tudong" . "Tu dong - bo qua phan o ke ben da co thep mu") ("Lientuc" . "Lien tuc - vat qua dam")
                                   ("Bien" . "Bien - neo vao dam") ("Khong" . "Khong ve")))
                           (list "eN" "Canh tren" 'kw "Tudong"
                                 '(("Tudong" . "Tu dong - bo qua phan o ke ben da co thep mu") ("Lientuc" . "Lien tuc - vat qua dam")
                                   ("Bien" . "Bien - neo vao dam") ("Khong" . "Khong ve"))))
                     (sd:kt-fields))))
    (exit))
  (setq name (sd:v "name") Lx (sd:v "Lx") Ly (sd:v "Ly") bw (sd:v "bw") t1 (sd:v "t") c (sd:v "c")
        dbx (sd:v "dbx") abx (sd:v "abx") dby (sd:v "dby") aby (sd:v "aby") dt (sd:v "dt") at (sd:v "at")
        kt (if (= (sd:v "lt") "1/3") (/ 1.0 3.0) 0.25) k (sd:v "k") sc (float (sd:v "sc")) tm (sd:v "tm")
        *SD:SNAME* name *SD:SLX* Lx *SD:SLY* Ly)
  (setq x0 (/ bw 2.0) x1 (- Lx (/ bw 2.0)) y0 (/ bw 2.0) y1 (- Ly (/ bw 2.0)) lnx (- x1 x0) lny (- y1 y0)
        leg (max 50.0 (- t1 c c)))
  (cond
    ((or (<= lnx 500) (<= lny 500)) (princ "\n[SD] O san qua nho so voi be rong dam."))
    ((setq o (sd:getpt "\nDiem chen (giao truc trai - duoi): " nil))
     (sd:kt-begin (sd:v "mk") name)
     (setq o (sd:w o) r (* 4 sc))
     ;; ---- truc + dam (net khuat)
     (foreach x (list 0.0 Lx)
       (sd:line (sd:p+ o x (- (+ x0 (* 4 sc)))) (sd:p+ o x (+ Ly x0 (* 12 sc))) "SD-TRUC")
       (sd:bubble (sd:p+ o x (+ Ly x0 (* 12 sc) r)) r (if (= x 0.0) "1" "2"))
       (sd:line (sd:p+ o (- x x0) (- y0)) (sd:p+ o (- x x0) (+ Ly y0)) "SD-KHUAT")
       (sd:line (sd:p+ o (+ x x0) (- y0)) (sd:p+ o (+ x x0) (+ Ly y0)) "SD-KHUAT"))
     (foreach y (list 0.0 Ly)
       (sd:line (sd:p+ o (- (+ x0 (* 4 sc))) y) (sd:p+ o (+ Lx x0 (* 12 sc)) y) "SD-TRUC")
       (sd:bubble (sd:p+ o (+ Lx x0 (* 12 sc) r) y) r (if (= y 0.0) "A" "B"))
       (sd:line (sd:p+ o (- x0) (- y y0)) (sd:p+ o (+ Lx x0) (- y y0)) "SD-KHUAT")
       (sd:line (sd:p+ o (- x0) (+ y y0)) (sd:p+ o (+ Lx x0) (+ y y0)) "SD-KHUAT"))
     ;; ---- thep lop duoi
     (setq yb (* 0.42 Ly) xb (* 0.58 Lx))
     (sd:kt-bar o (list (list 0.0 yb) (list Lx yb)) 0 dbx (list (* 0.5 Lx) yb) (list (+ (* 0.5 Lx) (* 4 sc)) (+ yb (* 6 sc)))
                k tm sc (list (list (* 0.3 Lx) (+ y0 50)) (list (* 0.3 Lx) (- y1 50))) abx)
     (sd:kt-bar o (list (list xb 0.0) (list xb Ly)) 0 dby (list xb (* 0.75 Ly)) (list (+ xb (* 4 sc)) (+ (* 0.75 Ly) (* 4 sc)))
                k tm sc (list (list (+ x0 50) (* 0.25 Ly)) (list (- x1 50) (* 0.25 Ly))) aby)
     ;; ---- thep mu 4 canh: doi chieu voi cac o san da ve (canh chung truc) de khong rai trung
     (setq recs (sd:san-recs))
     (foreach e (list (list "T" (sd:v "eT") Lx lnx (* 0.62 Ly)) (list "P" (sd:v "eP") Lx lnx (* 0.62 Ly))
                      (list "D" (sd:v "eD") Ly lny (* 0.3 Lx)) (list "N" (sd:v "eN") Ly lny (* 0.3 Lx)))
       (setq ed (car e) mode (cadr e) dir (if (member ed '("T" "P")) "V" "H")
             ax (if (= dir "V") (+ (car o) (if (= ed "T") 0.0 Lx)) (+ (cadr o) (if (= ed "D") 0.0 Ly)))
             a (if (= dir "V") (+ (cadr o) y0) (+ (car o) x0)) b (if (= dir "V") (+ (cadr o) y1) (+ (car o) x1))
             cov (sd:san-cover ed dir ax a b recs) fr (list a b) st mode
             lt (sd:ceil (* kt (nth 3 e)) 50.0))
       (cond
         ((and (= mode "Tudong") cov)
          (setq fr (sd:iv-free a b cov))
          (if (or (null fr) (< (- (cadr fr) (car fr)) 300.0))
            (setq st "Khong")
            (setq st "Lientuc"))
          (princ (strcat "\n[SD] Canh " ed ": o " (nth 3 (car cov)) " da co thep mu vat qua dam"
                         (if (= st "Khong") " -> khong ve lai." " -> chi rai phan con lai.")))
          (foreach c cov
            (if (> lt (+ (caddr c) 50.0))
              (princ (strcat "\n[SD]   Luu y: thep mu o " (nth 3 c) " vuon " (sd:num (caddr c)) " < Ln/" (if (= kt 0.25) "4" "3")
                             " cua o nay (" (sd:num lt) "), kiem tra lai.")))))
         ((= mode "Tudong") (setq st "Lientuc"))
         ((and cov (/= mode "Khong"))
          (princ (strcat "\n[SD] Canh " ed ": TRUNG thep mu voi o " (nth 3 (car cov)) " (da ve Lien tuc). Chon Tudong / Khong de bo."))))
       (if (null fr) (setq fr (list a a)))
       (setq sts (append sts (list (list ed st dir ax (car fr) (cadr fr) lt))))
       (if (/= st "Khong")
         (progn
           ;; doan rai (cuc bo doc canh) + vi tri thanh dai dien nam trong doan
           (setq a (- (car fr) (if (= dir "V") (cadr o) (car o))) b (- (cadr fr) (if (= dir "V") (cadr o) (car o)))
                 pos (if (and (> (nth 4 e) (+ a 100)) (< (nth 4 e) (- b 100))) (nth 4 e) (/ (+ a b) 2.0))
                 q (sd:san-mu o ed st (caddr e) bw lt leg pos dt at k tm sc))
           (sd:kt-bar o (car q) 0 dt (cadr q) (list (+ (car (cadr q)) (* 4 sc)) (+ (cadr (cadr q)) (* 5 sc))) k tm sc
                      (if (= dir "V")
                        (list (list (caddr q) (+ a 50)) (list (caddr q) (- b 50)))
                        (list (list (+ a 50) (caddr q)) (list (- b 50) (caddr q))))
                      at))))
     ;; ---- kich thuoc + tieu de
     ;; kich thuoc / tieu de nam ngoai phan thep mu vuon sang o ben
     (setq xb (if (= (cadr (assoc "T" sts)) "Lientuc") (+ x0 (sd:ceil (* kt lnx) 50.0)) x0)
           yb (if (= (cadr (assoc "D" sts)) "Lientuc") (+ y0 (sd:ceil (* kt lny) 50.0)) y0))
     (sd:use-dimstyle sc)
     (sd:dim o (sd:p+ o Lx 0) "H" (sd:p+ o 0 (- (+ yb (* 10 sc)))))
     (sd:dim o (sd:p+ o 0 Ly) "V" (sd:p+ o (- (+ xb (* 10 sc))) 0))
     (sd:ck-title (sd:p+ o (/ Lx 2.0) (- (+ yb (* 24 sc))))
                  (strcat "M\\U+1EB6T B\\U+1EB0NG TH\\U+00C9P S\\U+00C0N " name " (" (sd:num Lx) "\\U+00D7" (sd:num Ly) ", t=" (sd:num t1) ")")
                  sc name "San" k (/ (* lnx lny t1) 1e9) (/ (* lnx lny) 1e6)
                  (strcat (sd:num lnx) "x" (sd:num lny) "x" (sd:num t1)))
     ;; dang ky canh / thep mu cua o nay cho cac o ve sau
     (setq e (entlast))
     (entmod (append (entget e) (list (list -3 (cons "SD_SAN" (cons (cons 1000 name)
                       (mapcar '(lambda (x) (cons 1000 (sd:join (list (nth 0 x) (nth 2 x) (sd:rtos (nth 3 x) 1) (sd:rtos (nth 4 x) 1)
                                                                      (sd:rtos (nth 5 x) 1) (nth 1 x) (sd:rtos (nth 6 x) 0)) "|")))
                               sts)))))))
     (sd:use-dimstyle *SD:SCALE*)
     (sd:kt-end)))
  (sd:finish))

;;; --------------------------------------------------------------------------
;;;  SDTHANGTHEP - Khai trien thep ban thang (mat cat doc ve thang)
;;;  Chieu nghi duoi - ban thang nghieng - chieu nghi tren; thep chiu luc duoi chay suot (co de),
;;;  thep mu tai 2 cho gay khuc (Ltong/4 moi phia), thep phan bo vuong goc.
;;; --------------------------------------------------------------------------
;; Dien tich da giac (cong thuc Gauss)
(defun sd:poly-area (pts / s)
  (setq s 0.0)
  (mapcar '(lambda (p q) (setq s (+ s (- (* (car p) (cadr q)) (* (car q) (cadr p))))))
          pts (append (cdr pts) (list (car pts))))
  (abs (/ s 2.0)))

;; Chieu dai duong gap khuc
(defun sd:path-len (pts) (apply '+ (mapcar 'distance pts (cdr pts))))

;; Cac diem cach deu step tren duong gap khuc (bat dau tu step/2)
(defun sd:path-pts (pts step / r s p q d u)
  (setq s (/ step 2.0))
  (while (cdr pts)
    (setq p (car pts) q (cadr pts) d (distance p q))
    (while (<= s d)
      (setq u (/ s d) r (cons (list (+ (car p) (* u (- (car q) (car p)))) (+ (cadr p) (* u (- (cadr q) (cadr p))))) r)
            s (+ s step)))
    (setq s (- s d) pts (cdr pts)))
  (reverse r))

;; Bien dang be tong cau thang nhieu ve noi tiep (cuc bo): fl = ((X Y n La Lb) ...) goc moi ve tai mui bac dau
;; -> (top bot): top = mat bac + chieu nghi, bot = mat duoi ban (chieu nghi - ban nghieng - chieu nghi ...)
(defun sd:thang-prof (fl r g t1 / tn cs xs1 f X Y n run rise top bot i)
  (setq tn (/ r g) cs (cos (atan r g)) xs1 (/ (- (/ t1 cs) t1) tn)
        f (car fl) top (list (list (- (car f) (nth 3 f)) (cadr f))) bot (list (list (- (car f) (nth 3 f)) (- (cadr f) t1))))
  (foreach f fl
    (setq X (car f) Y (cadr f) n (nth 2 f) run (* (1- n) g) rise (* n r) top (append top (list (list X Y))) i 0)
    (repeat n
      (setq top (append top (list (list (+ X (* i g)) (+ Y (* (1+ i) r))))))
      (if (< i (1- n)) (setq top (append top (list (list (+ X (* (1+ i) g)) (+ Y (* (1+ i) r)))))))
      (setq i (1+ i)))
    (setq bot (append bot (list (list (+ X xs1) (- Y t1))
                                (list (+ X (/ (+ (- rise t1) (/ t1 cs)) tn)) (- (+ Y rise) t1))))))
  (setq f (last fl) run (* (1- (nth 2 f)) g) rise (* (nth 2 f) r))
  (list (append top (list (list (+ (car f) run (nth 4 f)) (+ (cadr f) rise))))
        (append bot (list (list (+ (car f) run (nth 4 f)) (- (+ (cadr f) rise) t1))))))

;; Thep 1 ve (goc of = mui bac dau, mat chieu nghi duoi): chiu luc co de, mu 2 cho gay, phan bo
;; La / Lb chieu nghi duoi / tren; shA / shB: chieu nghi dung chung voi ve ke ben -> thep phan bo chi rai nua chieu nghi
(defun sd:thang-ve (of n r g t1 B La Lb shA shB c d1 a1 d2 a2 d3 a3 k sc tm
                    / tn cs sn run rise cb xm1 xm2 main n1 n2 e lf lt xk1 xk2 xs1 xs2 dp)
  (setq tn (/ r g) cs (cos (atan r g)) sn (sin (atan r g)) run (* (1- n) g) rise (* n r)
        xs1 (/ (- (/ t1 cs) t1) tn) xs2 (/ (+ (- rise t1) (/ t1 cs)) tn)
        cb (+ c (/ d1 2.0))
        xm1 (/ (- (/ (- t1 cb) cs) (- t1 cb)) tn) xm2 (/ (+ (- rise (- t1 cb)) (/ (- t1 cb) cs)) tn)
        main (list (list (+ (- La) c) (+ (- t1) cb)) (list xm1 (+ (- t1) cb)) (list xm2 (+ (- rise t1) cb))
                   (list (- (+ run Lb) c) (+ (- rise t1) cb)))
        n1 (1+ (fix (/ (- B c c) a1))) n2 (1+ (fix (/ (- B c c) a2))))
  (sd:kt-bar of main n1 d1 (list (/ (+ xm1 xm2) 2.0) (/ (- rise t1) 2.0))
             (list (+ (/ (+ xm1 xm2) 2.0) (* 6 sc)) (- (/ (- rise t1) 2.0) (* 14 sc))) k tm sc nil 0.0)
  ;; thep mu tai 2 gay khuc (duoi mat bac, cach c + d2/2)
  (setq e (+ c (/ d2 2.0)) lf (/ (- xs2 xs1) cs) lt (sd:ceil (* 0.25 lf) 50.0)
        xk1 (/ (- (/ e cs) e) tn) xk2 (/ (+ (- rise e) (/ e cs)) tn))
  (sd:kt-bar of (list (list (max (+ (- La) c) (- xk1 lt)) (- e)) (list xk1 (- e)) (list (+ xk1 (* lt cs)) (+ (- e) (* lt sn))))
             n2 d2 (list (- xk1 (/ lt 2.0)) (- e)) (list (- xk1 (/ lt 2.0) (* 10 sc)) (* 8 sc)) k tm sc nil 0.0)
  (sd:kt-bar of (list (list (- xk2 (* lt cs)) (- rise e (* lt sn))) (list xk2 (- rise e)) (list (min (- (+ run Lb) c) (+ xk2 lt)) (- rise e)))
             n2 d2 (list (+ xk2 (/ lt 2.0)) (- rise e)) (list (+ xk2 (/ lt 2.0) (* 4 sc)) (+ rise (* 8 sc))) k tm sc nil 0.0)
  ;; thep phan bo: cham tren thanh chiu luc; duong phan bo (thong minh) cat o giua chieu nghi dung chung
  (setq dp main)
  (if shA (setq dp (cons (list (/ La -2.0) (cadr (car dp))) (cdr dp))))
  (if shB (setq dp (append (sd:head 3 dp) (list (list (+ run (/ Lb 2.0)) (cadr (last dp)))))))
  (foreach p (sd:path-pts dp a3)
    (sd:dot (sd:p+ of (car p) (+ (cadr p) (/ (+ d1 d3) 2.0))) d3 "SD-THEP-CHU"))
  (sd:pline (mapcar '(lambda (p) (sd:p+ of (car p) (- (cadr p) (/ (+ d1 d3) 2.0) (* 3 sc)))) dp) nil "SD-KYHIEU")
  (sd:kt-dist of (list (* 0.3 run) (+ (- (* 0.3 run tn) (/ (- t1 cb) cs)) (/ (+ d1 d3) 2.0)))
              (list (+ (* 0.3 run) (* 4 sc)) (- (* 0.3 run tn) (* 18 sc))) d3 "Thang" (list (- B c c)) k sc tm
              1 a3 nil (list (entlast))))

;; Kich thuoc + ghi chu bac 1 ve (goc of)
(defun sd:thang-dim (of n r g t1 La Lb sc vd / run rise)
  (setq run (* (1- n) g) rise (* n r))
  (sd:dimchain (mapcar '(lambda (x) (sd:p+ of x (- t1))) (list (- La) 0.0 run (+ run Lb))) "H" (sd:p+ of 0 (- (+ t1 (* 26 sc)))))
  (if vd (sd:dim (sd:p+ of (+ run Lb) 0) (sd:p+ of (+ run Lb) rise) "V" (sd:p+ of (+ run Lb (* 10 sc)) 0)))
  (sd:text (sd:p+ of (/ run 2.0) (- (+ t1 (* 32 sc))))
           (strcat (itoa (1- n)) "\\U+00D7" (sd:num g) " = " (sd:num run) ";  " (itoa n) "\\U+00D7" (sd:num r) " = " (sd:num rise))
           (* 2.5 sc) "MC" "SD-CHU"))

(defun c:SDTHANGTHEP (/ name ns r g t1 B L1 L2 Lm gap Bcn c d1 a1 d2 a2 d3 a3 k sc tm o nf fl px py f i al tn cs xs1 bad
                        pr poly area sof rtot sa ss of La Lb nm v s info sx)
  (sd:begin)
  (if (not (sd:dlg "Khai trien thep cau thang (SDTHANGTHEP)"
                   (append
                     (list (list "name" "Ten cau thang / ve" 'str (cond (*SD:TNAME*) ("TB1")))
                           (list "nv" "So bac tung ve (vd 10 hoac 11,10 hoac 3*8)" 'str (cond (*SD:TNV*) ("10")))
                           (list "kieu" "Bo tri cac ve" 'kw (cond (*SD:TKIEU*) ("Thang"))
                                 '(("Thang" . "Thang - cac ve noi tiep, 1 mat cat") ("Gap" . "Gap chu U - moi ve 1 mat cat")))
                           (list "r" "Chieu cao bac (mm)" 'real 150.0)
                           (list "g" "Be rong mat bac (mm)" 'real 300.0)
                           (list "t" "Chieu day ban thang / chieu nghi (mm)" 'real 120.0)
                           (list "B" "Be rong ve thang (mm)" 'real 1200.0)
                           (list "L1" "Chieu nghi / san duoi - dai (mm, >= 300)" 'real 1200.0)
                           (list "L2" "Chieu nghi / san tren - dai (mm, >= 300)" 'real 1200.0)
                           (list "Lm" "Chieu nghi giua - dai theo ve (mm)" 'real 1200.0)
                           (list "Bcn" "Chieu nghi giua - be rong (mm; 0 = 2B + 100)" 'real0 0.0 nil '("kieu" "Gap"))
                           (list "c" "Lop bao ve (mm)" 'real 20.0)
                           (list "d1" "Thep chiu luc duoi - d (mm)" 'real 10.0)
                           (list "a1" "Thep chiu luc duoi - buoc (mm)" 'real 150.0)
                           (list "d2" "Thep mu tai gay khuc - d (mm)" 'real 10.0)
                           (list "a2" "Thep mu tai gay khuc - buoc (mm)" 'real 150.0)
                           (list "d3" "Thep phan bo - d (mm)" 'real 6.0)
                           (list "a3" "Thep phan bo - buoc (mm)" 'real 250.0))
                     (sd:kt-fields))))
    (exit))
  (setq name (sd:v "name") ns (mapcar '(lambda (x) (max 2 (fix x))) (sd:parse-spacing (sd:v "nv")))
        r (sd:v "r") g (sd:v "g") t1 (sd:v "t") B (sd:v "B") L1 (sd:v "L1") L2 (sd:v "L2") Lm (sd:v "Lm")
        c (sd:v "c") d1 (sd:v "d1") a1 (sd:v "a1") d2 (sd:v "d2") a2 (sd:v "a2") d3 (sd:v "d3") a3 (sd:v "a3")
        k (sd:v "k") sc (float (sd:v "sc")) tm (sd:v "tm") gap (and (= (sd:v "kieu") "Gap") (cdr ns))
        Bcn (if (> (sd:v "Bcn") 0) (sd:v "Bcn") (+ B B 100.0)) nf (length ns)
        *SD:TNAME* name *SD:TNV* (sd:v "nv") *SD:TKIEU* (sd:v "kieu"))
  (setq al (atan r g) tn (/ r g) cs (cos al) xs1 (/ (- (/ t1 cs) t1) tn))
  ;; kiem tra: ban nghieng moi ve phai ket thuc truoc dau chieu nghi tren 100 mm
  (setq i 0)
  (foreach n ns
    (setq Lb (if (= i (1- nf)) L2 Lm))
    (if (> (/ (+ (- (* n r) t1) (/ t1 cs)) tn) (- (+ (* (1- n) g) Lb) 100 (if (and (< i (1- nf)) (not gap)) (- xs1) 0)))
      (setq bad t))
    (setq i (1+ i)))
  (cond
    ((null ns) (princ "\n[SD] So bac tung ve khong hop le (vd 10 hoac 11,10)."))
    ((or (< L1 300) (< L2 300) (and (cdr ns) (< Lm 300))) (princ "\n[SD] Cac chieu nghi phai >= 300 mm."))
    (bad (princ "\n[SD] Chieu nghi qua ngan so voi chieu day ban thang."))
    ((setq o (sd:getpt "\nDiem chen (mui bac dau tien, mat chieu nghi duoi): " nil))
     (sd:kt-begin (sd:v "mk") name)
     (setq o (sd:w o) px 0.0 py 0.0 i 0 sx 0.0 area 0.0 sof 0.0 rtot 0.0)
     ;; ---- goc tung ve: Thang = noi tiep (px += run + Lm, py += rise); Gap = tach mat cat sang phai, cao do tang dan
     (foreach n ns
       (setq La (if (= i 0) L1 Lm) Lb (if (= i (1- nf)) L2 Lm)
             fl (append fl (list (list (if gap (+ sx La) px) py n La Lb))))
       (setq px (+ px (* (1- n) g) Lm) sx (+ sx La (* (1- n) g) Lb (* 40 sc)) py (+ py (* n r)) rtot (+ rtot (* n r)) i (1+ i)))
     ;; ---- be tong + thep tung ve
     (setq i 0)
     (foreach f (if gap fl (list nil))
       (setq pr (sd:thang-prof (if gap (list f) fl) r g t1)
             poly (append (car pr) (reverse (cadr pr))))
       (sd:pline (mapcar '(lambda (p) (sd:p+ o (car p) (cadr p))) poly) t "SD-BETONG")
       (setq area (+ area (sd:poly-area poly)) sof (+ sof (sd:path-len (cadr pr)))))
     (foreach f fl
       (setq of (sd:p+ o (car f) (cadr f)))
       (sd:thang-ve of (nth 2 f) r g t1 B (nth 3 f) (nth 4 f) (> i 0) (< i (1- nf)) c d1 a1 d2 a2 d3 a3 k sc tm)
       (sd:use-dimstyle sc)
       (sd:thang-dim of (nth 2 f) r g t1 (nth 3 f) (nth 4 f) sc (or gap (null (cdr fl))))
       (if (cdr fl)
         (sd:text (sd:p+ of (/ (* (1- (nth 2 f)) g) 2.0) (+ (* (nth 2 f) r) (* 20 sc))) (strcat "V\\U+1EBE " (itoa (1+ i)))
                  (* 3.0 sc) "MC" "SD-CHU"))
       (setq i (1+ i)))
     ;; ve noi tiep: 1 kich thuoc tong chieu cao o dau tren
     (if (and (cdr fl) (not gap))
       (sd:dim (sd:p+ o (- (+ px L2) Lm) 0) (sd:p+ o (- (+ px L2) Lm) rtot) "V" (sd:p+ o (+ (- (+ px L2) Lm) (* 10 sc)) 0)))
     ;; ---- khoi luong: Thang = mat cat lien tuc x B; Gap = tru chieu nghi giua lap o 2 ve, cong chieu nghi rong Bcn
     (setq nm (1- nf) sa (* 2 nm Lm t1))
     (if gap
       (setq v (/ (+ (* (- area sa) B) (* nm Lm t1 Bcn)) 1e9)
             s (/ (+ (* B (- sof (* 2 nm Lm))) (* nm Lm Bcn) (* B rtot) (* 2.0 (- area sa)) (* nm 2.0 Lm t1)) 1e6))
       (setq v (/ (* area B) 1e9)
             s (/ (+ (* B sof) (* B rtot) (* 2.0 area)) 1e6)))
     (setq info (strcat (if (cdr ns) (strcat (itoa nf) " ve " (sd:join (mapcar 'itoa ns) "+")) (itoa (car ns)))
                        "x" (sd:num r) "/" (sd:num g) ", t=" (sd:num t1) ", B=" (sd:num B)
                        (if (cdr ns) (strcat ", CN giua " (sd:num Lm) (if gap (strcat "x" (sd:num Bcn)) "")) "")))
     (sd:ck-title (sd:p+ o (/ (if gap sx (- (+ px L2) Lm L1)) 2.0) (- (+ t1 (* 40 sc))))
                  (strcat "M\\U+1EB6T C\\U+1EAET TH\\U+00C9P " (if (cdr ns) "C\\U+1EA6U THANG " "V\\U+1EBE THANG ") name " (B=" (sd:num B)
                          (if (cdr ns) (strcat ", " (itoa nf) " v\\U+1EBF" (if gap " g\\U+1EA5p" "")) "") ")")
                  sc name "Thang" k v s info)
     (sd:use-dimstyle *SD:SCALE*)
     (sd:kt-end)))
  (sd:finish))

;;; --------------------------------------------------------------------------
;;;  SDCK - Khai bao khoi luong cau kien bat ky (kich thuoc hoac polyline kin)
;;; --------------------------------------------------------------------------
(defun c:SDCK (/ name typ L1 L2 Hh sv k e ar pe v s pt)
  (sd:begin)
  (if (not (sd:dlg "Khoi luong cau kien (SDCK)"
                   (list (list "name" "Ten cau kien" 'str (cond (*SD:CKN*) ("CK1")))
                         (list "typ" "Loai" 'kw (cond (*SD:CKT*) ("San"))
                               '(("Mong" . "Mong") ("Cot" . "Cot") ("Dam" . "Dam") ("San" . "San") ("Vach" . "Vach / tuong")
                                 ("Thang" . "Cau thang") ("Khac" . "Khac")))
                         (list "cach" "Cach tinh" 'kw "Kichthuoc"
                               '(("Kichthuoc" . "Nhap kich thuoc") ("Polyline" . "Chon polyline kin (dien tich x chieu day)")))
                         (list "L1" "Kich thuoc 1: dai / canh (mm)" 'real 1000.0 nil '("cach" "Kichthuoc"))
                         (list "L2" "Kich thuoc 2: rong / be day (mm)" 'real 1000.0 nil '("cach" "Kichthuoc"))
                         (list "Hh" "Chieu cao / chieu day (mm)" 'real 500.0)
                         (list "sv" "Van khuon 1 CK (m2; -1 = tu tinh)" 'real0 -1.0)
                         (list "tru" "Tru van khuon cho giao (m2 / 1 CK)" 'real0 0.0)
                         (list "k" "So cau kien" 'int 1)
                         (sd:tang-field))))
    (exit))
  (setq name (sd:v "name") typ (sd:v "typ") L1 (sd:v "L1") L2 (sd:v "L2") Hh (sd:v "Hh") sv (sd:v "sv") k (sd:v "k")
        *SD:CKN* name *SD:CKT* typ *SD:TANG* (vl-string-trim " " (sd:v "tang")))
  (if (= (sd:v "cach") "Polyline")
    (if (and (setq e (car (entsel "\nChon polyline kin (mat bang / mat cat cau kien): ")))
             (= (cdr (assoc 0 (entget e))) "LWPOLYLINE"))
      (setq ar (vlax-curve-getArea e) pe (sd:len e)
            v (/ (* ar Hh) 1e9)
            s (cond ((= typ "San") (/ ar 1e6)) (t (/ (* pe Hh) 1e6))))
      (setq v nil))
    (setq v (/ (* L1 L2 Hh) 1e9)
          s (cond ((= typ "Dam") (/ (* L1 (+ L2 Hh Hh)) 1e6))
                  ((= typ "San") (/ (* L1 L2) 1e6))
                  ((= typ "Vach") (/ (* 2.0 L1 Hh) 1e6))
                  (t (/ (* 2.0 (+ L1 L2) Hh) 1e6)))))
  (cond
    ((null v) (princ "\n[SD] Chua chon polyline."))
    ((setq pt (sd:getpt "\nVi tri ghi nhan cau kien: " nil))
     (if (>= sv 0) (setq s sv))
     (setq s (max 0.0 (- s (sd:v "tru"))))
     (sd:ck-title (sd:w pt) (strcat "[" name "] " typ ": V=" (sd:rtos v 3) " m\\U+00B3, VK=" (sd:rtos s 2) " m\\U+00B2")
                  (/ (sd:sc) 2.0) name typ k v s
                  (if ar (strcat "A=" (sd:rtos (/ ar 1e6) 3) "m2 x " (sd:num Hh)) (strcat (sd:num L1) "x" (sd:num L2) "x" (sd:num Hh))))))
  (sd:finish))

;;; --------------------------------------------------------------------------
;;;  SDKL - Xuat khoi luong be tong, van khuon, cot thep sang Excel
;;;  File Excel XML (SpreadsheetML) 3 sheet co cong thuc; neu may co Excel: mo va luu .xlsx
;;; --------------------------------------------------------------------------
;; Chuoi -> XML: ky tu dac biet, \U+XXXX (chu tieng Viet trong LISP) -> &#xXXXX;
(defun sd:xml-esc (s / r i ch)
  (setq r "" i 1)
  (while (<= i (strlen s))
    (setq ch (substr s i 1))
    (cond
      ((and (= ch "\\") (= (strcase (substr s (1+ i) 2)) "U+") (>= (strlen s) (+ i 6)))
       (setq r (strcat r "&#x" (substr s (+ i 3) 4) ";") i (+ i 6)))
      ((= ch "&") (setq r (strcat r "&amp;")))
      ((= ch "<") (setq r (strcat r "&lt;")))
      ((= ch ">") (setq r (strcat r "&gt;")))
      ((= ch "\"") (setq r (strcat r "&quot;")))
      ((> (ascii ch) 127) (setq r (strcat r "&#" (itoa (ascii ch)) ";")))
      (t (setq r (strcat r ch))))
    (setq i (1+ i)))
  r)

;; O Excel: so, chuoi, cong thuc ("=..."), hoac (gia-tri kieu-dinh-dang [gia-tri-tinh-san cua cong thuc])
(defun sd:xcell (v / st cv)
  (if (and v (listp v)) (setq st (cadr v) cv (caddr v) v (car v)))
  (strcat "<Cell" (if st (strcat " ss:StyleID=\"" st "\"") "")
          ;; luon ghi <Data> (ke ca o cong thuc / o trong) de moi trinh doc dem dung cot
          (cond ((and (= (type v) 'STR) (= (substr v 1 1) "="))
                 (strcat " ss:Formula=\"" (sd:xml-esc v) "\"><Data ss:Type=\"Number\">"
                         (if (numberp cv) (rtos cv 2 6) "0") "</Data></Cell>"))
                ((numberp v) (strcat "><Data ss:Type=\"Number\">" (rtos v 2 6) "</Data></Cell>"))
                ((null v) "><Data ss:Type=\"String\"></Data></Cell>")
                (t (strcat "><Data ss:Type=\"String\">" (sd:xml-esc v) "</Data></Cell>")))))

(defun sd:xrow (f cells / s)
  (setq s "<Row>")
  (foreach c cells (setq s (strcat s (sd:xcell c))))
  (write-line (strcat s "</Row>") f))

(defun sd:xsheet (f name widths title rows)
  (write-line (strcat "<Worksheet ss:Name=\"" name "\"><Table>") f)
  (foreach w widths (write-line (strcat "<Column ss:Width=\"" (itoa w) "\"/>") f))
  (sd:xrow f (list (list (car title) "t")))
  (sd:xrow f (list (cadr title)))
  (foreach r rows (sd:xrow f r))
  (write-line "</Table><WorksheetOptions xmlns=\"urn:schemas-microsoft-com:office:excel\"><PageSetup><Layout x:Orientation=\"Landscape\"/></PageSetup><FitToPage/><Print><FitHeight>0</FitHeight><PaperSizeIndex>9</PaperSizeIndex></Print><FreezePanes/><SplitHorizontal>3</SplitHorizontal><TopRowBottomPane>3</TopRowBottomPane><ActivePane>2</ActivePane></WorksheetOptions></Worksheet>" f))

;; Cau kien da khai bao: ((ten loai k v s ghi-chu tang) ...)
(defun sd:kl-cks (/ ss i x r)
  (setq i 0)
  (if (setq ss (ssget "_X" '((-3 ("SD_KL")))))
    (repeat (sslength ss)
      (setq x (mapcar 'cdr (cdadr (assoc -3 (entget (ssname ss i) '("SD_KL"))))) i (1+ i)
            x (append (sd:head 6 x) (list (cond ((nth 6 x)) ("")))))
      (if (not (assoc (car x) r)) (setq r (cons x r)))))
  (reverse r))

;; Dong thep theo cau kien: ((ck so-hieu hinh-dang (kich-thuoc) d L SL/CK soCK) ...), gop dong trung
(defun sd:kl-steel (/ ss i e xd ck rec key old rows)
  (setq i 0)
  (if (setq ss (ssget "_X" '((0 . "CIRCLE") (-3 ("SD_REBAR")))))
    (repeat (sslength ss)
      (setq e (ssname ss i) i (1+ i) xd (mapcar 'cdr (cdadr (assoc -3 (entget e '("SD_REBAR"))))))
      (if (not (sd:tm-orphan-p xd))
        (progn
          (setq ck (cdr (cadr (cadr (assoc -3 (entget e '("SD_CK")))))))
          (if (not ck) (setq ck "(ch\\U+01B0a g\\U+00E1n)"))
          ;; x = (so-hieu hinh-dang (kich-thuoc) d L SL/CK soCK); gop cung so hieu + so CK: cong so thanh
          (foreach x (sd:rec-rows (sd:xd->rec xd))
            (setq key (list ck (nth 0 x) (nth 1 x) (nth 2 x) (nth 3 x) (nth 4 x) (nth 6 x)))
            (if (setq old (assoc key rows))
              (setq rows (subst (cons key (+ (cdr old) (nth 5 x))) old rows))
              (setq rows (cons (cons key (nth 5 x)) rows))))))))
  ;; dong: (ck so-hieu hinh-dang (kich-thuoc) d L SL/CK soCK)
  (sd:sort (mapcar '(lambda (r) (append (sd:head 6 (car r)) (list (cdr r) (nth 6 (car r))))) rows)
           '(lambda (a b) (if (= (car a) (car b)) (sd:mk< (cadr a) (cadr b)) (< (car a) (car b))))))

;; Khoi luong coffa da dang ky (SD_VK): ((ten loai lenh dien-tich-m2 be-tong-m3 (dong...) handle) ...)
;; Cung ten + cung lenh dang ky nhieu lan (ve lai) -> lay lan moi nhat (handle lon nhat).
(defun sd:hex> (a b) (if (= (strlen a) (strlen b)) (> a b) (> (strlen a) (strlen b))))
(defun sd:kl-vk (/ ss i e x x0 h r old)
  (setq i 0)
  (if (setq ss (ssget "_X" '((-3 ("SD_VK")))))
    (repeat (sslength ss)
      (setq e (ssname ss i) i (1+ i) h (cdr (assoc 5 (entget e)))
            x0 (mapcar 'cdr (cdadr (assoc -3 (entget e '("SD_VK")))))
            x x0)
      (setq x (mapcar '(lambda (s) (sd:split s "|")) (cdr (cddddr x)))
            x (list (nth 0 x0) (nth 1 x0) (nth 2 x0) (nth 3 x0) (nth 4 x0)
                    (vl-remove-if '(lambda (r) (= (car r) "@T")) x) h
                    (cond ((cadr (vl-some '(lambda (r) (if (= (car r) "@T") r)) x))) (""))))
      (if (setq old (vl-some '(lambda (y) (if (and (= (car y) (car x)) (= (caddr y) (caddr x))) y)) r))
        (if (sd:hex> h (last old)) (setq r (subst x old r)))
        (setq r (cons x r)))))
  (reverse r))

(defun sd:kg (r) (/ (* (nth 5 r) (nth 6 r) (nth 7 r) 0.00617 (nth 4 r) (nth 4 r)) 1000.0))
(defun sd:dgrp (d) (cond ((<= d 10.0) 0) ((<= d 18.0) 1) (t 2)))

;; Ten loai cau kien hien thi (co dau)
(defun sd:kl-typname (typ)
  (cond ((cdr (assoc typ '(("Mong" . "M\\U+00F3ng") ("Be tong lot" . "B\\U+00EA t\\U+00F4ng l\\U+00F3t") ("Cot" . "C\\U+1ED9t") ("Dam" . "D\\U+1EA7m") ("San" . "S\\U+00E0n")
                           ("Thang" . "C\\U+1EA7u thang") ("Vach" . "V\\U+00E1ch / t\\U+01B0\\U+1EDDng") ("Khac" . "Kh\\U+00E1c")))))
        (typ)))

(defun sd:kl-order (typ) (cond ((vl-position typ '("Mong" "Be tong lot" "Cot" "Dam" "San" "Thang" "Vach" "Khac"))) (99)))

;; Mo file XML bang Excel va luu .xlsx (tra ve T neu duoc)
;; Mo file XML bang Excel, luu .xlsx; tra ve T, hoac chuoi ly do loi
(defun sd:xl-open (xml xlsx / r xl)
  (setq r (vl-catch-all-apply
            '(lambda (/ wb)
               (if (null (setq xl (vlax-get-or-create-object "Excel.Application")))
                 (exit))
               (vlax-put-property xl 'DisplayAlerts :vlax-false)
               (setq wb (vlax-invoke-method (vlax-get-property xl 'Workbooks) 'Open xml))
               (vl-catch-all-apply 'vlax-invoke-method (list wb 'SaveAs xlsx 51))
               (vlax-put-property xl 'DisplayAlerts :vlax-true)
               (vlax-put-property xl 'Visible :vlax-true)
               t)
            nil))
  (if xl (vl-catch-all-apply 'vlax-release-object (list xl)))
  (cond ((null xl) "may khong co Excel (hoac khong tao duoc doi tuong Excel.Application)")
        ((vl-catch-all-error-p r) (vl-catch-all-error-message r))
        (r t)
        ("loi khong ro")))

;; Dong cong (SUBTOTAL) cho bang TongHop: n = so dong du lieu phia tren ("*" = tu R4, khong cong trung dong Cong)
(defun sd:kl-subrow (lab n v st / rg)
  (setq rg (cond ((null n) "=SUM(R4C:R[-1]C)") ((= n "*") "=SUBTOTAL(9,R4C:R[-1]C)") ((strcat "=SUBTOTAL(9,R[-" n "]C:R[-1]C)"))))
  (list (list lab st) nil nil nil nil (list rg st (nth 0 v)) nil (list rg st (nth 1 v))
        (list rg st (nth 2 v)) (list rg st (nth 3 v)) (list rg st (nth 4 v)) (list rg st (nth 5 v))
        (list "=IF(RC6>0,RC12/RC6,0)" st (if (> (car v) 0) (/ (nth 5 v) (car v)) 0.0))))

;; ---- Ma dinh muc (goi y theo dinh muc 1776 / TT 12/2021/TT-BXD - can doi chieu dinh muc ap dung cho du an)
;; khoa: "BT|loai" (m3), "VK|loai" (100 m2), "CT|loai|nhom" (tan), nhom D<=10 / D<=18 / D>18
(defun sd:dm-def ()
  '(("BT|Be tong lot" "AF.11111" "B\\U+00EA t\\U+00F4ng l\\U+00F3t m\\U+00F3ng, \\U+0111\\U+00E1 4x6, chi\\U+1EC1u r\\U+1ED9ng \\U+2264250 cm" "m\\U+00B3")
    ("BT|Mong" "AF.11213" "B\\U+00EA t\\U+00F4ng m\\U+00F3ng, chi\\U+1EC1u r\\U+1ED9ng \\U+2264250 cm, \\U+0111\\U+00E1 1x2" "m\\U+00B3")
    ("BT|Cot" "AF.12213" "B\\U+00EA t\\U+00F4ng c\\U+1ED9t, ti\\U+1EBFt di\\U+1EC7n \\U+22640,1 m\\U+00B2, cao \\U+22646 m, \\U+0111\\U+00E1 1x2" "m\\U+00B3")
    ("BT|Dam" "AF.12313" "B\\U+00EA t\\U+00F4ng x\\U+00E0 d\\U+1EA7m, gi\\U+1EB1ng nh\\U+00E0, \\U+0111\\U+00E1 1x2" "m\\U+00B3")
    ("BT|San" "AF.12413" "B\\U+00EA t\\U+00F4ng s\\U+00E0n m\\U+00E1i, \\U+0111\\U+00E1 1x2" "m\\U+00B3")
    ("BT|Thang" "AF.12513" "B\\U+00EA t\\U+00F4ng c\\U+1EA7u thang th\\U+01B0\\U+1EDDng, \\U+0111\\U+00E1 1x2" "m\\U+00B3")
    ("BT|Vach" "AF.12113" "B\\U+00EA t\\U+00F4ng t\\U+01B0\\U+1EDDng th\\U+1EB3ng, d\\U+00E0y \\U+226445 cm, cao \\U+22646 m, \\U+0111\\U+00E1 1x2" "m\\U+00B3")
    ("BT|Khac" "AF.1" "B\\U+00EA t\\U+00F4ng k\\U+1EBFt c\\U+1EA5u kh\\U+00E1c" "m\\U+00B3")
    ("VK|Mong" "AF.81111" "V\\U+00E1n khu\\U+00F4n m\\U+00F3ng d\\U+00E0i, b\\U+1EC7 m\\U+00E1y" "100 m\\U+00B2")
    ("VK|Cot" "AF.81122" "V\\U+00E1n khu\\U+00F4n c\\U+1ED9t vu\\U+00F4ng, ch\\U+1EEF nh\\U+1EADt" "100 m\\U+00B2")
    ("VK|Dam" "AF.81141" "V\\U+00E1n khu\\U+00F4n x\\U+00E0 d\\U+1EA7m, gi\\U+1EB1ng" "100 m\\U+00B2")
    ("VK|San" "AF.81151" "V\\U+00E1n khu\\U+00F4n s\\U+00E0n m\\U+00E1i" "100 m\\U+00B2")
    ("VK|Thang" "AF.81161" "V\\U+00E1n khu\\U+00F4n c\\U+1EA7u thang th\\U+01B0\\U+1EDDng" "100 m\\U+00B2")
    ("VK|Vach" "AF.81131" "V\\U+00E1n khu\\U+00F4n t\\U+01B0\\U+1EDDng" "100 m\\U+00B2")
    ("VK|Khac" "AF.81" "V\\U+00E1n khu\\U+00F4n k\\U+1EBFt c\\U+1EA5u kh\\U+00E1c" "100 m\\U+00B2")
    ("CT|Mong|D<=10" "AF.61110" "C\\U+1ED1t th\\U+00E9p m\\U+00F3ng, \\U+0111\\U+01B0\\U+1EDDng k\\U+00EDnh \\U+226410 mm" "t\\U+1EA5n")
    ("CT|Mong|D<=18" "AF.61120" "C\\U+1ED1t th\\U+00E9p m\\U+00F3ng, \\U+0111\\U+01B0\\U+1EDDng k\\U+00EDnh \\U+226418 mm" "t\\U+1EA5n")
    ("CT|Mong|D>18" "AF.61130" "C\\U+1ED1t th\\U+00E9p m\\U+00F3ng, \\U+0111\\U+01B0\\U+1EDDng k\\U+00EDnh >18 mm" "t\\U+1EA5n")
    ("CT|Vach|D<=10" "AF.61311" "C\\U+1ED1t th\\U+00E9p t\\U+01B0\\U+1EDDng, \\U+0111\\U+01B0\\U+1EDDng k\\U+00EDnh \\U+226410 mm, cao \\U+22644 m" "t\\U+1EA5n")
    ("CT|Vach|D<=18" "AF.61321" "C\\U+1ED1t th\\U+00E9p t\\U+01B0\\U+1EDDng, \\U+0111\\U+01B0\\U+1EDDng k\\U+00EDnh \\U+226418 mm, cao \\U+22644 m" "t\\U+1EA5n")
    ("CT|Vach|D>18" "AF.61331" "C\\U+1ED1t th\\U+00E9p t\\U+01B0\\U+1EDDng, \\U+0111\\U+01B0\\U+1EDDng k\\U+00EDnh >18 mm, cao \\U+22644 m" "t\\U+1EA5n")
    ("CT|Cot|D<=10" "AF.61411" "C\\U+1ED1t th\\U+00E9p c\\U+1ED9t, tr\\U+1EE5, \\U+0111\\U+01B0\\U+1EDDng k\\U+00EDnh \\U+226410 mm, cao \\U+22644 m" "t\\U+1EA5n")
    ("CT|Cot|D<=18" "AF.61421" "C\\U+1ED1t th\\U+00E9p c\\U+1ED9t, tr\\U+1EE5, \\U+0111\\U+01B0\\U+1EDDng k\\U+00EDnh \\U+226418 mm, cao \\U+22644 m" "t\\U+1EA5n")
    ("CT|Cot|D>18" "AF.61431" "C\\U+1ED1t th\\U+00E9p c\\U+1ED9t, tr\\U+1EE5, \\U+0111\\U+01B0\\U+1EDDng k\\U+00EDnh >18 mm, cao \\U+22644 m" "t\\U+1EA5n")
    ("CT|Dam|D<=10" "AF.61511" "C\\U+1ED1t th\\U+00E9p x\\U+00E0 d\\U+1EA7m, gi\\U+1EB1ng, \\U+0111\\U+01B0\\U+1EDDng k\\U+00EDnh \\U+226410 mm, cao \\U+22644 m" "t\\U+1EA5n")
    ("CT|Dam|D<=18" "AF.61521" "C\\U+1ED1t th\\U+00E9p x\\U+00E0 d\\U+1EA7m, gi\\U+1EB1ng, \\U+0111\\U+01B0\\U+1EDDng k\\U+00EDnh \\U+226418 mm, cao \\U+22644 m" "t\\U+1EA5n")
    ("CT|Dam|D>18" "AF.61531" "C\\U+1ED1t th\\U+00E9p x\\U+00E0 d\\U+1EA7m, gi\\U+1EB1ng, \\U+0111\\U+01B0\\U+1EDDng k\\U+00EDnh >18 mm, cao \\U+22644 m" "t\\U+1EA5n")
    ("CT|San|D<=10" "AF.61711" "C\\U+1ED1t th\\U+00E9p s\\U+00E0n m\\U+00E1i, \\U+0111\\U+01B0\\U+1EDDng k\\U+00EDnh \\U+226410 mm, cao \\U+226416 m" "t\\U+1EA5n")
    ("CT|San|D<=18" "AF.61721" "C\\U+1ED1t th\\U+00E9p s\\U+00E0n m\\U+00E1i, \\U+0111\\U+01B0\\U+1EDDng k\\U+00EDnh >10 mm, cao \\U+226416 m" "t\\U+1EA5n")
    ("CT|San|D>18" "AF.61721" "C\\U+1ED1t th\\U+00E9p s\\U+00E0n m\\U+00E1i, \\U+0111\\U+01B0\\U+1EDDng k\\U+00EDnh >10 mm, cao \\U+226416 m" "t\\U+1EA5n")
    ("CT|Thang|D<=10" "AF.61811" "C\\U+1ED1t th\\U+00E9p c\\U+1EA7u thang, \\U+0111\\U+01B0\\U+1EDDng k\\U+00EDnh \\U+226410 mm, cao \\U+22644 m" "t\\U+1EA5n")
    ("CT|Thang|D<=18" "AF.61821" "C\\U+1ED1t th\\U+00E9p c\\U+1EA7u thang, \\U+0111\\U+01B0\\U+1EDDng k\\U+00EDnh >10 mm, cao \\U+22644 m" "t\\U+1EA5n")
    ("CT|Thang|D>18" "AF.61821" "C\\U+1ED1t th\\U+00E9p c\\U+1EA7u thang, \\U+0111\\U+01B0\\U+1EDDng k\\U+00EDnh >10 mm, cao \\U+22644 m" "t\\U+1EA5n")
    ("CT|Khac|D<=10" "AF.6" "C\\U+1ED1t th\\U+00E9p k\\U+1EBFt c\\U+1EA5u kh\\U+00E1c, \\U+0111\\U+01B0\\U+1EDDng k\\U+00EDnh \\U+226410 mm" "t\\U+1EA5n")
    ("CT|Khac|D<=18" "AF.6" "C\\U+1ED1t th\\U+00E9p k\\U+1EBFt c\\U+1EA5u kh\\U+00E1c, \\U+0111\\U+01B0\\U+1EDDng k\\U+00EDnh \\U+226418 mm" "t\\U+1EA5n")
    ("CT|Khac|D>18" "AF.6" "C\\U+1ED1t th\\U+00E9p k\\U+1EBFt c\\U+1EA5u kh\\U+00E1c, \\U+0111\\U+01B0\\U+1EDDng k\\U+00EDnh >18 mm" "t\\U+1EA5n")))

;; Bang ma dinh muc: doc <ban ve>_MaDinhMuc.csv (Khoa;Ma hieu;Ten;Don vi - ten / don vi trong = mac dinh);
;; chua co file -> ghi file mac dinh de nguoi dung sua. Tra ve ((khoa ma ten dv) ...)
(defun sd:dm-table (/ fn f l x tb e)
  (setq fn (sd:csv-name "_MaDinhMuc.csv") tb (sd:dm-def))
  (if (sd:fexists fn)
    (if (setq f (sd:open fn "r"))
      (progn
        (while (setq l (read-line f))
          (setq x (sd:split l ";"))
          (if (and (cadr x) (setq e (assoc (car x) tb)))
            (setq tb (subst (list (car e) (vl-string-trim " " (cadr x))
                                  (if (and (caddr x) (/= (vl-string-trim " " (caddr x)) "")) (caddr x) (caddr e))
                                  (if (and (cadddr x) (/= (vl-string-trim " " (cadddr x)) "")) (cadddr x) (cadddr e)))
                            e tb))))
        (setq fn (sd:close f))))
    (if (setq f (sd:open fn "w"))
      (progn
        (write-line "Khoa;Ma hieu;Ten cong viec (trong = mac dinh);Don vi (trong = mac dinh)" f)
        (foreach e tb (write-line (strcat (car e) ";" (cadr e) ";;") f))
        (setq fn (sd:close f))
        (princ (strcat "\n[SD] Da tao bang ma dinh muc mac dinh: " fn " (sua ma hieu roi xuat lai).")))))
  tb)
(defun sd:dm-get (tb key / e)
  (cond ((setq e (assoc key tb)))
        ((setq e (assoc (strcat (substr key 1 3) "Khac" (if (vl-string-search "|D" key) (substr key (1+ (vl-string-search "|D" key))) "")) tb)))
        ((list key "" key ""))))

;; Thu tu tang tu nhien: tach tien to chu + so (T2 < T10, B1 < T1 theo chu cai), "(chua gan)" cuoi
(defun sd:nat-key (s / i c)
  (setq i 1)
  (while (and (<= i (strlen s)) (not (wcmatch (substr s i 1) "#"))) (setq i (1+ i)))
  (list (strcase (substr s 1 (1- i))) (if (<= i (strlen s)) (atoi (substr s i)) -1) s))
(defun sd:fl< (a b / x y)
  (setq x (sd:nat-key a) y (sd:nat-key b))
  (cond ((= a b) nil) ((= a "(ch\\U+01B0a g\\U+00E1n)") nil) ((= b "(ch\\U+01B0a g\\U+00E1n)") t)
        ((/= (car x) (car y)) (< (car x) (car y)))
        ((/= (cadr x) (cadr y)) (< (cadr x) (cadr y)))
        (t (< a b))))

(defun c:SDKL (/ cks steel names g e rows i fn f ds tot n xlsx vk fls hasfl fl gn sub agg key tb typs pt trows j q)
  (sd:begin)
  (sd:tag-sync-all)
  (sd:tm-dup-report)
  (if (not (sd:dlg "Xuat khoi luong sang Excel (SDKL)"
                   (list (list "note" "Be tong + van khuon: cau kien ve bang lenh khai trien hoac SDCK; thep: moi ky hieu thep" 'note nil)
                         (list "xl" "Mo Excel va luu file .xlsx (neu may co Excel)" 'tog t)
                         (list "dm" "Them sheet ma dinh muc (doc / tao file _MaDinhMuc.csv)" 'tog t)
                         (list "bang" "Ve bang tong hop vao ban ve" 'tog nil))))
    (exit))
  ;; cks: ((ten loai k v s ghi-chu nguon-VK tang) ...)
  (setq cks (mapcar '(lambda (c) (list (nth 0 c) (nth 1 c) (nth 2 c) (nth 3 c) (nth 4 c) (nth 5 c) "H\\U+00ECnh h\\U+1ECDc" (nth 6 c))) (sd:kl-cks))
        steel (sd:kl-steel) vk (sd:kl-vk))
  ;; van khuon tu lenh coffa (SD_VK) thay cho uoc tinh hinh hoc; cau kien chi co coffa -> dong moi
  (foreach x vk
    (if (setq e (assoc (car x) cks))
      ;; da co nhan khoi luong: giu be tong cua nhan, van khuon = tong cac lenh coffa cung ten
      ;; chi co coffa ("(coffa)"): cong ca be tong cua cac lenh coffa cung ten
      (setq cks (subst (list (nth 0 e) (nth 1 e) (nth 2 e)
                             (+ (nth 3 e) (if (= (nth 5 e) "(coffa)") (nth 4 x) 0.0))
                             (+ (if (= (nth 6 e) "Coffa") (nth 4 e) 0.0) (nth 3 x)) (nth 5 e) "Coffa"
                             (if (= (nth 7 e) "") (nth 7 x) (nth 7 e)))
                       e cks))
      (setq cks (append cks (list (list (car x) (cadr x) 1 (nth 4 x) (nth 3 x) "(coffa)" "Coffa" (nth 7 x)))))))
  (if (and (null cks) (null steel))
    (princ "\n[SD] Ban ve chua co cau kien (SDMONGTHEP, SDCOTTHEP, SDDAMDUNG, SDSANTHEP, SDTHANGTHEP, SDCK) hay ky hieu thep.")
    (progn
      ;; thep theo cau kien va nhom duong kinh
      (foreach r steel
        (if (not (setq e (assoc (car r) g))) (setq e (list (car r) 0.0 0.0 0.0) g (cons e g)))
        (setq n (sd:dgrp (nth 4 r))
              g (subst (sd:replace-nth (1+ n) (+ (nth (1+ n) e) (sd:kg r)) e) e g)))
      (foreach r g (if (not (assoc (car r) cks)) (setq cks (append cks (list (list (car r) "-" 1 0.0 0.0 "" "" ""))))))
      ;; nhom theo tang neu co cau kien gan tang
      (setq hasfl (vl-some '(lambda (c) (/= (nth 7 c) "")) cks))
      (if hasfl
        (setq cks (mapcar '(lambda (c) (if (= (nth 7 c) "") (sd:replace-nth 7 "(ch\\U+01B0a g\\U+00E1n)" c) c)) cks)))
      (foreach c cks (if (not (member (nth 7 c) fls)) (setq fls (cons (nth 7 c) fls))))
      (setq fls (sd:sort fls 'sd:fl<))
      (setq cks (sd:sort cks '(lambda (a b)
                                (cond ((/= (nth 7 a) (nth 7 b)) (sd:fl< (nth 7 a) (nth 7 b)))
                                      ((= (sd:kl-order (cadr a)) (sd:kl-order (cadr b))) (< (car a) (car b)))
                                      (t (< (sd:kl-order (cadr a)) (sd:kl-order (cadr b))))))))
      (setq fn (sd:csv-name "_KhoiLuong.xml") xlsx (sd:csv-name "_KhoiLuong.xlsx"))
      (if (not (setq f (sd:open fn "w")))
        (princ (strcat "\n[SD] Khong ghi duoc " fn " (file dang mo?)."))
        (progn
          (write-line "<?xml version=\"1.0\" encoding=\"UTF-8\"?><?mso-application progid=\"Excel.Sheet\"?>" f)
          (write-line (strcat "<Workbook xmlns=\"urn:schemas-microsoft-com:office:spreadsheet\" xmlns:o=\"urn:schemas-microsoft-com:office:office\""
                              " xmlns:x=\"urn:schemas-microsoft-com:office:excel\" xmlns:ss=\"urn:schemas-microsoft-com:office:spreadsheet\">") f)
          (write-line (strcat "<Styles><Style ss:ID=\"Default\"><Font ss:FontName=\"Arial\" ss:Size=\"10\"/></Style>"
                              "<Style ss:ID=\"t\"><Font ss:FontName=\"Arial\" ss:Size=\"14\" ss:Bold=\"1\"/></Style>"
                              "<Style ss:ID=\"h\"><Alignment ss:Horizontal=\"Center\" ss:Vertical=\"Center\" ss:WrapText=\"1\"/>"
                              "<Borders><Border ss:Position=\"Bottom\" ss:LineStyle=\"Continuous\" ss:Weight=\"1\"/></Borders>"
                              "<Font ss:FontName=\"Arial\" ss:Bold=\"1\"/><Interior ss:Color=\"#D9E1F2\" ss:Pattern=\"Solid\"/></Style>"
                              "<Style ss:ID=\"n2\"><NumberFormat ss:Format=\"#,##0.00\"/></Style>"
                              "<Style ss:ID=\"n3\"><NumberFormat ss:Format=\"#,##0.000\"/></Style>"
                              "<Style ss:ID=\"n0\"><NumberFormat ss:Format=\"#,##0\"/></Style>"
                              "<Style ss:ID=\"g\"><Font ss:FontName=\"Arial\" ss:Bold=\"1\" ss:Color=\"#1F4E79\"/></Style>"
                              "<Style ss:ID=\"c\"><Font ss:FontName=\"Arial\" ss:Italic=\"1\" ss:Bold=\"1\"/><NumberFormat ss:Format=\"#,##0.00\"/>"
                              "<Interior ss:Color=\"#EDEDED\" ss:Pattern=\"Solid\"/></Style>"
                              "<Style ss:ID=\"s\"><Font ss:FontName=\"Arial\" ss:Bold=\"1\"/><NumberFormat ss:Format=\"#,##0.00\"/>"
                              "<Interior ss:Color=\"#FFF2CC\" ss:Pattern=\"Solid\"/></Style></Styles>") f)
          ;; ---- sheet 1: tong hop theo cau kien (nhom theo tang: dong tieu de tang + dong cong SUBTOTAL)
          (setq rows nil i 0 tot (list 0.0 0.0 0.0 0.0 0.0 0.0) fl nil gn 0 sub nil)
          (foreach c (append cks (list nil))
            (if (and hasfl (or (null c) (/= (nth 7 c) fl)))
              (progn
                (if fl
                  (setq rows (append rows (list (sd:kl-subrow (strcat "C\\U+1ED9ng " fl) (itoa gn) sub "c")))))
                (if c (setq rows (append rows (list (list nil (list (strcat "T\\U+1EA6NG: " (nth 7 c)) "g"))))
                            fl (nth 7 c) gn 0 sub (list 0.0 0.0 0.0 0.0 0.0 0.0)))))
            (if c
              (progn
                (setq i (1+ i) gn (1+ gn) e (cond ((cdr (assoc (car c) g))) ('(0.0 0.0 0.0)))
                      n (list (* (caddr c) (nth 3 c)) (* (caddr c) (nth 4 c)) (car e) (cadr e) (caddr e) (apply '+ e))
                      tot (mapcar '+ tot n) sub (if sub (mapcar '+ sub n)))
                (setq rows (append rows (list (append (list i (car c) (sd:kl-typname (cadr c)) (caddr c) (list (nth 3 c) "n3") (list "=RC4*RC5" "n3" (nth 0 n))
                                                            (list (nth 4 c) "n2") (list "=RC4*RC7" "n2" (nth 1 n))
                                                            (list (car e) "n2") (list (cadr e) "n2") (list (caddr e) "n2")
                                                            (list "=SUM(RC9:RC11)" "n2" (nth 5 n))
                                                            (list "=IF(RC6>0,RC12/RC6,0)" "n2" (if (> (car n) 0) (/ (nth 5 n) (car n)) 0.0))
                                                            (if (= (nth 5 c) "(coffa)") "" (nth 5 c)) (nth 6 c))
                                                      (if hasfl (list (nth 7 c))))))))))
          (setq rows (append (list (mapcar '(lambda (x) (list x "h"))
                                           (append (list "STT" "C\\U+1EA5u ki\\U+1EC7n" "Lo\\U+1EA1i" "S\\U+1ED1 CK" "B\\U+00EA t\\U+00F4ng 1 CK (m\\U+00B3)" "B\\U+00EA t\\U+00F4ng (m\\U+00B3)"
                                                         "V\\U+00E1n khu\\U+00F4n 1 CK (m\\U+00B2)" "V\\U+00E1n khu\\U+00F4n (m\\U+00B2)" "Th\\U+00E9p \\U+00D8\\U+226410 (kg)" "Th\\U+00E9p \\U+00D8\\U+226418 (kg)"
                                                         "Th\\U+00E9p \\U+00D8>18 (kg)" "T\\U+1ED5ng th\\U+00E9p (kg)" "H\\U+00E0m l\\U+01B0\\U+1EE3ng (kg/m\\U+00B3)" "K\\U+00EDch th\\U+01B0\\U+1EDBc" "Ngu\\U+1ED3n v\\U+00E1n khu\\U+00F4n")
                                                   (if hasfl (list "T\\U+1EA7ng")))))
                             rows
                             (list (sd:kl-subrow "T\\U+1ED4NG" (if hasfl "*" nil) tot "s"))))
          (sd:xsheet f "TongHop" (append '(30 80 70 40 75 70 80 75 70 70 70 75 75 130 80) (if hasfl '(60)))
                     (list "B\\U+1EA2NG T\\U+1ED4NG H\\U+1EE2P KH\\U+1ED0I L\\U+01AF\\U+1EE2NG B\\U+00CA T\\U+00D4NG - V\\U+00C1N KHU\\U+00D4N - C\\U+1ED0T TH\\U+00C9P"
                           (strcat "B\\U+1EA3n v\\U+1EBD: " (getvar "DWGNAME") " - ng\\U+00E0y " (sd:today) ". Th\\U+00E9p \\U+0111\\U+00E3 nh\\U+00E2n s\\U+1ED1 c\\U+1EA5u ki\\U+1EC7n; h\\U+00E0m l\\U+01B0\\U+1EE3ng = t\\U+1ED5ng th\\U+00E9p / b\\U+00EA t\\U+00F4ng. "
                                   "V\\U+00E1n khu\\U+00F4n: Coffa = t\\U+1EEB l\\U+1EC7nh coffa (thi\\U+1EBFt k\\U+1EBF), H\\U+00ECnh h\\U+1ECDc = \\U+01B0\\U+1EDBc t\\U+00EDnh theo k\\U+00EDch th\\U+01B0\\U+1EDBc."
                                   (if hasfl " Nh\\U+00F3m theo t\\U+1EA7ng: d\\U+00F2ng C\\U+1ED9ng d\\U+00F9ng SUBTOTAL, d\\U+00F2ng T\\U+1ED4NG kh\\U+00F4ng c\\U+1ED9ng tr\\U+00F9ng." "")))
                     rows)
          ;; ---- sheet: tong hop theo tang
          (if hasfl
            (progn
              (setq rows (list (mapcar '(lambda (x) (list x "h"))
                                       (list "T\\U+1EA7ng" "B\\U+00EA t\\U+00F4ng (m\\U+00B3)" "V\\U+00E1n khu\\U+00F4n (m\\U+00B2)" "Th\\U+00E9p \\U+00D8\\U+226410 (kg)" "Th\\U+00E9p \\U+00D8\\U+226418 (kg)" "Th\\U+00E9p \\U+00D8>18 (kg)"
                                             "T\\U+1ED5ng th\\U+00E9p (kg)" "H\\U+00E0m l\\U+01B0\\U+1EE3ng (kg/m\\U+00B3)"))))
              (foreach x fls
                (setq n (list 0.0 0.0 0.0 0.0 0.0))
                (foreach c cks
                  (if (= (nth 7 c) x)
                    (setq e (cond ((cdr (assoc (car c) g))) ('(0.0 0.0 0.0)))
                          n (mapcar '+ n (list (* (caddr c) (nth 3 c)) (* (caddr c) (nth 4 c)) (car e) (cadr e) (caddr e))))))
                (setq rows (append rows (list (list x (list "=SUMIF(TongHop!C16,RC1,TongHop!C6)" "n3" (nth 0 n))
                                                    (list "=SUMIF(TongHop!C16,RC1,TongHop!C8)" "n2" (nth 1 n))
                                                    (list "=SUMIF(TongHop!C16,RC1,TongHop!C9)" "n2" (nth 2 n))
                                                    (list "=SUMIF(TongHop!C16,RC1,TongHop!C10)" "n2" (nth 3 n))
                                                    (list "=SUMIF(TongHop!C16,RC1,TongHop!C11)" "n2" (nth 4 n))
                                                    (list "=SUM(RC4:RC6)" "n2" (+ (nth 2 n) (nth 3 n) (nth 4 n)))
                                                    (list "=IF(RC2>0,RC7/RC2,0)" "n2"
                                                          (if (> (car n) 0) (/ (+ (nth 2 n) (nth 3 n) (nth 4 n)) (car n)) 0.0)))))))
              (setq rows (append rows (list (list (list "T\\U+1ED4NG" "s") (list "=SUM(R4C:R[-1]C)" "s" (nth 0 tot)) (list "=SUM(R4C:R[-1]C)" "s" (nth 1 tot))
                                                  (list "=SUM(R4C:R[-1]C)" "s" (nth 2 tot)) (list "=SUM(R4C:R[-1]C)" "s" (nth 3 tot))
                                                  (list "=SUM(R4C:R[-1]C)" "s" (nth 4 tot)) (list "=SUM(R4C:R[-1]C)" "s" (nth 5 tot))
                                                  (list "=IF(RC2>0,RC7/RC2,0)" "s" (if (> (car tot) 0) (/ (nth 5 tot) (car tot)) 0.0))))))
              (sd:xsheet f "TheoTang" '(80 75 80 75 75 75 80 80) (list "T\\U+1ED4NG H\\U+1EE2P KH\\U+1ED0I L\\U+01AF\\U+1EE2NG THEO T\\U+1EA6NG" "C\\U+00F4ng th\\U+1EE9c SUMIF theo c\\U+1ED9t T\\U+1EA7ng c\\U+1EE7a sheet TongHop") rows)))
          ;; ---- sheet: khoi luong theo ma dinh muc (theo tang neu co)
          (if (sd:v "dm")
            (progn
              (setq tb (sd:dm-table) rows (list (mapcar '(lambda (x) (list x "h"))
                                                        (list "STT" "M\\U+00E3 hi\\U+1EC7u" "T\\U+00EAn c\\U+00F4ng vi\\U+1EC7c" "\\U+0110\\U+01A1n v\\U+1ECB" "Kh\\U+1ED1i l\\U+01B0\\U+1EE3ng" "T\\U+1EA7ng" "Lo\\U+1EA1i c\\U+1EA5u ki\\U+1EC7n")))
                    i 0)
              (foreach x (if hasfl fls (list nil))
                (if hasfl (setq rows (append rows (list (list nil (list (strcat "T\\U+1EA6NG: " x) "g"))))))
                ;; agg: ((loai bt vk s1 s2 s3) ...) theo thu tu loai
                (setq agg nil)
                (foreach c cks
                  (if (or (null x) (= (nth 7 c) x))
                    (progn
                      (setq e (cond ((cdr (assoc (car c) g))) ('(0.0 0.0 0.0)))
                            n (list (* (caddr c) (nth 3 c)) (* (caddr c) (nth 4 c)) (car e) (cadr e) (caddr e)))
                      (if (setq q (assoc (cadr c) agg))
                        (setq agg (subst (cons (car q) (mapcar '+ (cdr q) n)) q agg))
                        (setq agg (append agg (list (cons (cadr c) n))))))))
                (foreach q agg
                  (setq key (if (member (car q) '("Be tong lot" "Mong" "Cot" "Dam" "San" "Thang" "Vach")) (car q) "Khac") j 0)
                  (foreach w (list (list "BT" 1 "C6" 1.0 nil) (list "VK" 2 "C8" 100.0 nil)
                                   (list "CT" 3 "C9" 1000.0 "D<=10") (list "CT" 4 "C10" 1000.0 "D<=18") (list "CT" 5 "C11" 1000.0 "D>18"))
                    (if (and (> (nth (cadr w) q) 1e-9) (not (and (= (car w) "VK") (= key "Be tong lot"))))
                      (progn
                        (setq e (sd:dm-get tb (strcat (car w) "|" key (if (nth 4 w) (strcat "|" (nth 4 w)) ""))) i (1+ i))
                        (setq rows (append rows (list (list i (cadr e) (caddr e) (cadddr e)
                                                            (list (strcat (if hasfl
                                                                            (strcat "=SUMIFS(TongHop!" (caddr w) ",TongHop!C3,RC7,TongHop!C16,RC6)")
                                                                            (strcat "=SUMIF(TongHop!C3,RC7,TongHop!" (caddr w) ")"))
                                                                          (if (/= (nth 3 w) 1.0) (strcat "/" (itoa (fix (nth 3 w)))) ""))
                                                                  "n3" (/ (nth (cadr w) q) (nth 3 w)))
                                                            (if hasfl x "") (sd:kl-typname (car q)))))))))))
              (sd:xsheet f "DinhMuc" '(35 70 300 50 80 60 80)
                         (list "KH\\U+1ED0I L\\U+01AF\\U+1EE2NG THEO M\\U+00C3 \\U+0110\\U+1ECANH M\\U+1EE8C"
                               (strcat "M\\U+00E3 hi\\U+1EC7u g\\U+1EE3i \\U+00FD (\\U+0110M 1776 / TT 12/2021/TT-BXD) - \\U+0111\\U+1ED1i chi\\U+1EBFu \\U+0111\\U+1ECBnh m\\U+1EE9c \\U+00E1p d\\U+1EE5ng; s\\U+1EEDa trong file "
                                       (vl-filename-base (getvar "DWGNAME")) "_MaDinhMuc.csv r\\U+1ED3i xu\\U+1EA5t l\\U+1EA1i."))
                         rows)))
          ;; ---- sheet: chi tiet thep
          (setq rows (list (mapcar '(lambda (x) (list x "h"))
                                   (list "C\\U+1EA5u ki\\U+1EC7n" "SH" "H\\U+00ECnh d\\U+1EA1ng" "K\\U+00EDch th\\U+01B0\\U+1EDBc (mm)" "\\U+00D8 (mm)" "D\\U+00E0i 1 thanh (mm)" "SL / CK"
                                         "S\\U+1ED1 CK" "T\\U+1ED5ng SL" "T\\U+1ED5ng d\\U+00E0i (m)" "Kh\\U+1ED1i l\\U+01B0\\U+1EE3ng (kg)"))))
          (setq n (list 0.0 0.0))
          (foreach r steel
            (setq e (list (* (nth 6 r) (nth 7 r)) (/ (* (nth 5 r) (nth 6 r) (nth 7 r)) 1000.0) (sd:kg r))
                  n (list (+ (car n) (cadr e)) (+ (cadr n) (caddr e))))
            (setq rows (append rows (list (list (nth 0 r) (nth 1 r) (nth 2 r) (sd:join (mapcar 'sd:num (nth 3 r)) "/")
                                                (nth 4 r) (list (nth 5 r) "n0") (nth 6 r) (nth 7 r) (list "=RC7*RC8" nil (car e))
                                                (list "=RC6*RC9/1000" "n2" (cadr e)) (list "=RC10*0.00617*RC5^2" "n2" (caddr e)))))))
          (setq rows (append rows (list (list (list "T\\U+1ED4NG" "s") nil nil nil nil nil nil nil nil
                                              (list "=SUM(R4C:R[-1]C)" "s" (car n)) (list "=SUM(R4C:R[-1]C)" "s" (cadr n))))))
          (sd:xsheet f "ThepChiTiet" '(80 35 60 110 40 70 45 45 50 70 80)
                     (list "B\\U+1EA2NG TH\\U+1ED0NG K\\U+00CA C\\U+1ED0T TH\\U+00C9P CHI TI\\U+1EBET" "Kh\\U+1ED1i l\\U+01B0\\U+1EE3ng = t\\U+1ED5ng d\\U+00E0i \\U+00D7 0.00617 \\U+00D7 \\U+00D8\\U+00B2")
                     rows)
          ;; ---- sheet: theo duong kinh
          (foreach r steel (if (not (member (nth 4 r) ds)) (setq ds (cons (nth 4 r) ds))))
          (setq rows (list (mapcar '(lambda (x) (list x "h")) (list "\\U+00D8 (mm)" "T\\U+1ED5ng d\\U+00E0i (m)" "Kh\\U+1ED1i l\\U+01B0\\U+1EE3ng (kg)" "Nh\\U+00F3m"))))
          (foreach d (vl-sort ds '<)
            (setq e (list 0.0 0.0))
            (foreach r steel
              (if (equal (nth 4 r) d 1e-6)
                (setq e (list (+ (car e) (/ (* (nth 5 r) (nth 6 r) (nth 7 r)) 1000.0)) (+ (cadr e) (sd:kg r))))))
            (setq rows (append rows (list (list d (list "=SUMIF(ThepChiTiet!C5,RC1,ThepChiTiet!C10)" "n2" (car e))
                                                (list "=SUMIF(ThepChiTiet!C5,RC1,ThepChiTiet!C11)" "n2" (cadr e))
                                                (nth (sd:dgrp d) '("\\U+00D8\\U+226410" "10<\\U+00D8\\U+226418" "\\U+00D8>18")))))))
          (setq rows (append rows (list (list (list "T\\U+1ED4NG" "s") (list "=SUM(R4C:R[-1]C)" "s" (car n))
                                              (list "=SUM(R4C:R[-1]C)" "s" (cadr n))))))
          (sd:xsheet f "TheoDuongKinh" '(50 80 90 70) (list "T\\U+1ED4NG H\\U+1EE2P C\\U+1ED0T TH\\U+00C9P THEO \\U+0110\\U+01AF\\U+1EDCNG K\\U+00CDNH" "") rows)
          ;; ---- sheet 4, 5: vat tu coffa (chi tiet + tong hop theo hang muc)
          (if vk
            (progn
              (setq rows (list (mapcar '(lambda (x) (list x "h"))
                                       (list "C\\U+1EA5u ki\\U+1EC7n" "Lo\\U+1EA1i" "L\\U+1EC7nh" "H\\U+1EA1ng m\\U+1EE5c" "Quy c\\U+00E1ch" "\\U+0110V" "Kh\\U+1ED1i l\\U+01B0\\U+1EE3ng")))
                    ds nil)
              (foreach x vk
                (foreach r (nth 5 x)
                  (setq n (distof (cadddr r) 2))
                  (setq rows (append rows (list (list (car x) (sd:kl-typname (cadr x)) (caddr x) (car r) (cadr r) (caddr r)
                                                      (if n (list n "n2") (cadddr r))))))
                  (if n
                    (if (setq e (assoc (list (car r) (cadr r) (caddr r)) ds))
                      (setq ds (subst (cons (car e) (+ (cdr e) n)) e ds))
                      (setq ds (append ds (list (cons (list (car r) (cadr r) (caddr r)) n))))))))
              (sd:xsheet f "VatTuCoffa" '(80 70 90 150 120 40 80)
                         (list "V\\U+1EACT T\\U+01AF COFFA THEO C\\U+1EA4U KI\\U+1EC6N" "T\\U+1EEB b\\U+1EA3ng kh\\U+1ED1i l\\U+01B0\\U+1EE3ng c\\U+1EE7a c\\U+00E1c l\\U+1EC7nh coffa (l\\U+1EA7n v\\U+1EBD m\\U+1EDBi nh\\U+1EA5t m\\U+1ED7i c\\U+1EA5u ki\\U+1EC7n)")
                         rows)
              (setq rows (list (mapcar '(lambda (x) (list x "h")) (list "H\\U+1EA1ng m\\U+1EE5c" "Quy c\\U+00E1ch" "\\U+0110V" "T\\U+1ED5ng kh\\U+1ED1i l\\U+01B0\\U+1EE3ng"))))
              (foreach e ds
                (setq rows (append rows (list (list (car (car e)) (cadr (car e)) (caddr (car e))
                                                    (list "=SUMIFS(VatTuCoffa!C7,VatTuCoffa!C4,RC1,VatTuCoffa!C5,RC2,VatTuCoffa!C6,RC3)"
                                                          "n2" (cdr e)))))))
              (sd:xsheet f "TongVatTuCoffa" '(150 120 40 100) (list "T\\U+1ED4NG H\\U+1EE2P V\\U+1EACT T\\U+01AF COFFA" "") rows)))
          (write-line "</Workbook>" f)
          (setq fn (sd:close f))
          ;; ---- tom tat dong lenh
          (princ (strcat "\n[SD] " (itoa (length cks)) " cau kien" (if hasfl (strcat ", " (itoa (length fls)) " tang") "")
                         ": be tong " (sd:rtos (car tot) 3) " m3, van khuon "
                         (sd:rtos (cadr tot) 2) " m2, thep " (sd:rtos (nth 5 tot) 1) " kg."
                         "\n[SD] Da ghi: " fn))
          (if (sd:v "xl")
            (princ (if (= (setq e (sd:xl-open fn xlsx)) t)
                     (strcat "\n[SD] Da mo Excel va luu: " xlsx)
                     (strcat "\n[SD] Khong mo duoc Excel tu dong (" e "): mo file " fn " bang Excel (Open), roi Save As .xlsx."))))
          ;; ---- bang tong hop ve vao ban ve (theo tang neu co)
          (if (and (sd:v "bang") (setq pt (sd:getpt "\nDiem chen bang tong hop (goc trai tren): " nil)))
            (progn
              (setq trows nil fl nil sub nil i 0)
              (foreach c (append cks (list nil))
                (if (and hasfl (or (null c) (/= (nth 7 c) fl)))
                  (progn
                    (if fl (setq trows (append trows (list (list "R" (list "" (strcat "C\\U+1ED9ng " fl) "" ""
                                                                           (sd:rtos (nth 0 sub) 3) (sd:rtos (nth 1 sub) 2) (sd:rtos (nth 5 sub) 1)) nil)))))
                    (if c (setq trows (append trows (list (list "G" (strcat "T\\U+1EA6NG: " (nth 7 c)))))
                                fl (nth 7 c) sub (list 0.0 0.0 0.0 0.0 0.0 0.0)))))
                (if c
                  (setq i (1+ i) e (cond ((cdr (assoc (car c) g))) ('(0.0 0.0 0.0)))
                        n (list (* (caddr c) (nth 3 c)) (* (caddr c) (nth 4 c)) (car e) (cadr e) (caddr e) (apply '+ e))
                        sub (if sub (mapcar '+ sub n))
                        trows (append trows (list (list "R" (list (itoa i) (car c) (sd:kl-typname (cadr c)) (itoa (caddr c))
                                                                  (sd:rtos (nth 0 n) 3) (sd:rtos (nth 1 n) 2) (sd:rtos (nth 5 n) 1)) nil))))))
              (setq trows (append trows (list (list "R" (list "" "T\\U+1ED4NG" "" "" (sd:rtos (nth 0 tot) 3) (sd:rtos (nth 1 tot) 2)
                                                              (sd:rtos (nth 5 tot) 1)) nil))))
              (sd:table2 (sd:w pt) "B\\U+1EA2NG T\\U+1ED4NG H\\U+1EE2P KH\\U+1ED0I L\\U+01AF\\U+1EE2NG B\\U+00CA T\\U+00D4NG - V\\U+00C1N KHU\\U+00D4N - C\\U+1ED0T TH\\U+00C9P"
                         '(("STT" 10) ("C\\U+1EA4U KI\\U+1EC6N" 26) ("LO\\U+1EA0I" 22) ("S\\U+1ED0 CK" 12) ("B\\U+00CA T\\U+00D4NG (m\\U+00B3)" 24) ("V\\U+00C1N KHU\\U+00D4N (m\\U+00B2)" 26) ("TH\\U+00C9P (kg)" 22))
                         trows -1 (sd:sc))
              (princ "\n[SD] Da ve bang tong hop (chay lai SDKL de cap nhat).")))))))
  (sd:finish))

;;; --------------------------------------------------------------------------
;;;  SDTOIUU - Toi uu cat thep tu cay thuong pham (Best Fit Decreasing)
;;; --------------------------------------------------------------------------
;; items: ((chieu-dai . so-luong) ...) giam dan. Moi doan chiem (L + kerf),
;; suc chua 1 cay = cap + kerf (doan cuoi khong can mach cat).
;; Tra ve danh sach cay: (con-lai doan1 doan2 ...)
(defun sd:bfd (items cap kerf / bins need q best bidx i m)
  (foreach it items
    (setq need (+ (car it) kerf) q (cdr it))
    (while (> q 0)
      (setq best nil bidx nil i 0)
      (foreach b bins
        (if (and (>= (car b) (- need 1e-6)) (or (null best) (< (car b) (car best))))
          (setq best b bidx i))
        (setq i (1+ i)))
      (if (null best)
        (setq best (list (+ cap kerf))
              bins (append bins (list best))
              bidx (1- (length bins))))
      ;; cay tot nhat van la tot nhat sau khi them doan cung loai -> them 1 lan nhieu doan
      (setq m (min q (fix (/ (+ (car best) 1e-6) need))))
      (setq bins (sd:replace-nth bidx (cons (- (car best) (* m need))
                                            (append (cdr best) (sd:repeat (car it) m)))
                                 bins)
            q (- q m))))
  bins)

(defun c:SDTOIUU (/ ss data cap kerf reuse byd e items bins pats left nb req
                    stock waste nre lre kgbuy tbuy treq rows lines over pt fn f d key)
  (sd:begin)
  (if (not (sd:dlg "Toi uu cat thep (SDTOIUU)"
                   (list (list "cap" "Chieu dai cay thep thuong pham (mm)" 'real (sd:cfg "STOCK" 11700.0))
                         (list "kerf" "Be rong mach cat (mm)" 'real0 (sd:cfg "KERF" 0.0))
                         (list "reuse" "Doan thua tai su dung toi thieu (mm)" 'real (sd:cfg "REUSE" 1000.0)))))
    (exit))
  (setq cap   (sd:v "cap")
        kerf  (sd:v "kerf")
        reuse (sd:v "reuse"))
  (if (not (setq ss (sd:select-rebars)))
    (princ "\n[SD] Khong tim thay ky hieu thep nao (dung lenh SDTHEP de tao).")
    (progn
      (setq data (sd:read-rebars ss))
      ;; gom doan cat theo duong kinh: byd = ((d (L . sl) ...) ...)
      (foreach r data
        (foreach L (cond ((nth 7 r)) ((list (nth 3 r))))
          (if (> L (+ cap 1e-6))
            (setq over (cons (strcat (car r) " (D" (sd:num (nth 2 r)) ", L=" (sd:rtos L 0) ")") over))
            (progn
              (if (not (setq e (assoc (nth 2 r) byd)))
                (setq e (list (nth 2 r)) byd (cons e byd)))
              (setq items (cdr e)
                    items (if (assoc L items)
                            (subst (cons L (+ (cdr (assoc L items)) (* (nth 1 r) (nth 4 r))))
                                   (assoc L items) items)
                            (cons (cons L (* (nth 1 r) (nth 4 r))) items)))
              (setq byd (subst (cons (car e) items) e byd))))))
      (setq byd (sd:sort byd '(lambda (a b) (< (car a) (car b))))
            tbuy 0.0 treq 0.0)
      (foreach e byd
        (setq d     (car e)
              items (sd:sort (cdr e) '(lambda (a b) (> (car a) (car b))))
              bins  (sd:bfd items cap kerf)
              pats  nil nre 0 lre 0.0
              req   (apply '+ (mapcar '(lambda (x) (* (car x) (cdr x))) items)))
        ;; gom so do cat giong nhau
        (foreach b bins
          (setq left (if (> (car b) 1e-6) (max 0.0 (- (car b) kerf)) 0.0)
                key  (sd:pcs-str (cdr b) "\\U+00D7"))   ; doan trong cay da giam dan
          (if (>= left reuse) (setq nre (1+ nre) lre (+ lre left)))
          (if (assoc key pats)
            (setq pats (subst (list key (1+ (cadr (assoc key pats))) left (cadddr (assoc key pats)))
                              (assoc key pats) pats))
            (setq pats (cons (list key 1 left (sd:pcs-str (cdr b) "x")) pats))))
        (setq pats  (sd:sort pats '(lambda (a b) (> (cadr a) (cadr b))))
              nb    (length bins)
              stock (* nb cap)
              waste (- stock req)
              kgbuy (* (/ stock 1000.0) 0.00617 d d)
              tbuy  (+ tbuy kgbuy)
              treq  (+ treq (* (/ req 1000.0) 0.00617 d d)))
        (foreach p pats
          (setq rows (cons (list "R" (list (strcat "%%c" (sd:num d)) (car p) (itoa (cadr p))
                                           (sd:rtos (caddr p) 0)) nil)
                           rows)
                lines (cons (sd:join (list (sd:num d) (cadddr p)
                                           (itoa (cadr p)) (sd:rtos (caddr p) 0)) ";")
                            lines)))
        (setq rows (cons (list "W" (strcat "%%c" (sd:num d) ": " (itoa nb) " c\\U+00E2y \\U+00D7 " (sd:num (/ cap 1000.0))
                                           " m; c\\U+1EA7n " (sd:rtos (/ req 1000.0) 2) " m; d\\U+01B0 "
                                           (sd:rtos (/ waste 1000.0) 2) " m ("
                                           (sd:rtos (if (> stock 0) (/ (* 100.0 waste) stock) 0.0) 1)
                                           "%), trong \\U+0111\\U+00F3 " (itoa nre) " \\U+0111o\\U+1EA1n >= " (sd:num reuse)
                                           " t\\U+00E1i s\\U+1EED d\\U+1EE5ng = " (sd:rtos (/ lre 1000.0) 2) " m; KL mua "
                                           (sd:rtos kgbuy 1) " kg"))
                         rows))
        (princ (strcat "\n D" (sd:num d) ": " (itoa nb) " cay, can " (sd:rtos (/ req 1000.0) 2)
                       " m, hao hut " (sd:rtos (if (> stock 0) (/ (* 100.0 waste) stock) 0.0) 1) "%")))
      (setq rows (reverse rows)
            rows (append rows (list (list "W" (strcat "T\\U+1ED4NG: KL mua " (sd:rtos tbuy 1) " kg; KL c\\U+1EA7n "
                                                      (sd:rtos treq 1) " kg; hao h\\U+1EE5t "
                                                      (sd:rtos (if (> tbuy 0) (/ (* 100.0 (- tbuy treq)) tbuy) 0.0) 1)
                                                      "% (m\\U+1EA1ch c\\U+1EAFt " (sd:num kerf) " mm)")))))
      (princ (strcat "\n TONG: KL mua " (sd:rtos tbuy 1) " kg, KL can " (sd:rtos treq 1) " kg"))
      (if over
        (princ (strcat "\n[!] Doan dai hon cay thep, khong dua vao toi uu: " (sd:join (reverse over) "; "))))
      (if (and byd (setq pt (sd:getpt "\nDiem chen bang toi uu (goc trai tren): " nil)))
        (sd:table2 pt (strcat "B\\U+1EA2NG T\\U+1ED0I \\U+01AFU C\\U+1EAET TH\\U+00C9P (C\\U+00C2Y " (sd:num (/ cap 1000.0)) " m)")
                   '(("\\U+0110K" 12) ("S\\U+01A0 \\U+0110\\U+1ED2 C\\U+1EAET 1 C\\U+00C2Y (mm)" 100) ("S\\U+1ED0 C\\U+00C2Y" 16) ("D\\U+01AF/C\\U+00C2Y (mm)" 22))
                   rows -1 (sd:sc)))
      (setq fn (sd:csv-name "_ToiUuCatThep.csv"))
      (if (setq f (sd:open fn "w"))
        (progn
          (write-line "DK(mm);So do cat 1 cay (mm);So cay;Du/cay (mm)" f)
          (foreach l (reverse lines) (write-line l f))
          (setq fn (sd:close f))
          (princ (strcat "\n[SD] Da xuat: " fn))))))
  (sd:finish))

;;; --------------------------------------------------------------------------
;;;  SDBANMA - Ban ma / ban de thep co lo bulong
;;; --------------------------------------------------------------------------
(defun sd:positions (L e n / dx i r)
  (if (= n 1)
    (list (/ L 2.0))
    (progn
      (setq dx (/ (- L e e) (1- n)) i 0)
      (repeat n (setq r (cons (+ e (* i dx)) r) i (1+ i)))
      (reverse r))))

(defun c:SDBANMA (/ ts name B H tk nx ny ex ey d0 c o xs ys kl k)
  (sd:begin)
  (setq ts (float *SD:DETSCALE*))
  (if (not (sd:dlg "Ban ma / ban de (SDBANMA)"
                   (list (list "name" "Ten ban ma" 'str (cond (*SD:BNAME*) ("BM1")))
                         (list "B" "Chieu rong B - theo X (mm)" 'real (cond (*SD:BB*) (300.0)))
                         (list "H" "Chieu cao H - theo Y (mm)" 'real (cond (*SD:BH*) (400.0)))
                         (list "t" "Chieu day t (mm)" 'real (cond (*SD:BT*) (20.0)))
                         (list "nx" "So cot lo theo X" 'int 2)
                         (list "ny" "So hang lo theo Y" 'int 2)
                         (list "ex" "Tam lo den mep theo X (mm)" 'real 50.0)
                         (list "ey" "Tam lo den mep theo Y (mm)" 'real 50.0)
                         (list "d0" "Duong kinh lo (mm)" 'real 22.0))))
    (exit))
  (setq name (sd:v "name") B (sd:v "B") H (sd:v "H") tk (sd:v "t") nx (sd:v "nx") ny (sd:v "ny")
        ex (sd:v "ex") ey (sd:v "ey") d0 (sd:v "d0"))
  (setq *SD:BNAME* name *SD:BB* B *SD:BH* H *SD:BT* tk)
  (if (setq c (sd:getpt "\nTam ban ma: " nil))
    (progn
      (setq o  (sd:p+ c (/ B -2.0) (/ H -2.0))
            xs (sd:positions B ex nx)
            ys (sd:positions H ey ny)
            k  (+ (/ d0 2.0) (* 2 ts)))
      (sd:rect o B H "SD-THEP-HINH")
      (foreach x xs
        (foreach y ys
          (sd:circle (sd:p+ o x y) (/ d0 2.0) "SD-BULONG")
          (sd:line (sd:p+ o (- x k) y) (sd:p+ o (+ x k) y) "SD-TRUC")
          (sd:line (sd:p+ o x (- y k)) (sd:p+ o x (+ y k)) "SD-TRUC")))
      (sd:use-dimstyle ts)
      (sd:dimchain (mapcar '(lambda (x) (sd:p+ o x 0)) (append '(0.0) xs (list B))) "H" (sd:p+ o 0 (* -6 ts)))
      (sd:dim o (sd:p+ o B 0) "H" (sd:p+ o 0 (* -13 ts)))
      (sd:dimchain (mapcar '(lambda (y) (sd:p+ o 0 y)) (append '(0.0) ys (list H))) "V" (sd:p+ o (* -6 ts) 0))
      (sd:dim o (sd:p+ o 0 H) "V" (sd:p+ o (* -13 ts) 0))
      (setq kl (* B H tk 7.85e-6))
      (sd:text (sd:p+ o (/ B 2.0) (* -20 ts))
               (strcat name ": PL" (sd:num tk) "\\U+00D7" (sd:num B) "\\U+00D7" (sd:num H))
               (* 3.0 ts) "MC" "SD-CHU")
      (sd:text (sd:p+ o (/ B 2.0) (* -25 ts))
               (strcat (itoa (* nx ny)) " l\\U+1ED7 %%c" (sd:num d0) " - KL = " (sd:rtos kl 2) " kg")
               (* 2.5 ts) "MC" "SD-CHU")
      (sd:use-dimstyle *SD:SCALE*)
      (princ (strcat "\n[SD] " name ": khoi luong " (sd:rtos kl 2) " kg."))))
  (sd:finish))

;;; --------------------------------------------------------------------------
;;;  SDIH - Tiet dien thep hinh I / H (to hop hoac can nong)
;;; --------------------------------------------------------------------------
(defun c:SDIH (/ ts typ h b tw tf c o A g)
  (sd:begin)
  (setq ts (float *SD:DETSCALE*))
  (if (not (sd:dlg "Tiet dien thep I / H (SDIH)"
                   (list (list "typ" "Loai tiet dien" 'kw "H" '("H" "I"))
                         (list "h" "Chieu cao h (mm)" 'real (cond (*SD:IH*) (300.0)))
                         (list "b" "Be rong canh b (mm)" 'real (cond (*SD:IB*) (150.0)))
                         (list "tw" "Chieu day bung tw (mm)" 'real (cond (*SD:ITW*) (6.5)))
                         (list "tf" "Chieu day canh tf (mm)" 'real (cond (*SD:ITF*) (9.0))))))
    (exit))
  (setq typ (sd:v "typ") h (sd:v "h") b (sd:v "b") tw (sd:v "tw") tf (sd:v "tf"))
  (setq *SD:IH* h *SD:IB* b *SD:ITW* tw *SD:ITF* tf)
  (if (setq c (sd:getpt "\nTam tiet dien: " nil))
    (progn
      (sd:pline (mapcar '(lambda (p) (sd:p+ c (car p) (cadr p)))
                        (list (list (/ b -2) (/ h -2)) (list (/ b 2) (/ h -2))
                              (list (/ b 2) (+ (/ h -2) tf)) (list (/ tw 2) (+ (/ h -2) tf))
                              (list (/ tw 2) (- (/ h 2) tf)) (list (/ b 2) (- (/ h 2) tf))
                              (list (/ b 2) (/ h 2)) (list (/ b -2) (/ h 2))
                              (list (/ b -2) (- (/ h 2) tf)) (list (/ tw -2) (- (/ h 2) tf))
                              (list (/ tw -2) (+ (/ h -2) tf)) (list (/ b -2) (+ (/ h -2) tf))))
                t "SD-THEP-HINH")
      (setq o (sd:p+ c (/ b -2) (/ h -2))
            A (+ (* 2 b tf) (* (- h tf tf) tw))
            g (* A 0.00785))
      (sd:use-dimstyle ts)
      (sd:dim o (sd:p+ o b 0) "H" (sd:p+ o 0 (* -8 ts)))
      (sd:dim (sd:p+ o b 0) (sd:p+ o b h) "V" (sd:p+ o (+ b (* 8 ts)) 0))
      (sd:text (sd:p+ c 0 (- (/ h -2) (* 16 ts)))
               (strcat typ (sd:num h) "\\U+00D7" (sd:num b) "\\U+00D7" (sd:num tw) "\\U+00D7" (sd:num tf))
               (* 3.0 ts) "MC" "SD-CHU")
      (sd:text (sd:p+ c 0 (- (/ h -2) (* 21 ts)))
               (strcat "A = " (sd:rtos (/ A 100.0) 2) " cm\\U+00B2; g = " (sd:rtos g 2) " kg/m")
               (* 2.5 ts) "MC" "SD-CHU")
      (sd:use-dimstyle *SD:SCALE*)))
  (sd:finish))

;;; ==========================================================================
;;;  OP LAT DA GRANITE / GACH
;;;  XDATA "SD_TILE": ma VL, loai (F nguyen / C cat chu nhat / D cat dac biet),
;;;  ma vien, w, h, dien tich, so pat, ten VL, W danh nghia, H danh nghia
;;; ==========================================================================
(defun sd:ms () (vla-get-ModelSpace (sd:doc)))
(defun sd:2d (p) (list (car p) (cadr p)))

;; Xoay, doi toa do cuc bo (goc o, goc xoay a) <-> WCS
(defun sd:rot (p a)
  (list (- (* (car p) (cos a)) (* (cadr p) (sin a)))
        (+ (* (car p) (sin a)) (* (cadr p) (cos a)))))
(defun sd:l2w (o a p / r) (setq r (sd:rot p a)) (list (+ (car o) (car r)) (+ (cadr o) (cadr r))))
(defun sd:w2l (o a p) (sd:rot (list (- (car p) (car o)) (- (cadr p) (cadr o))) (- a)))

;; Dinh cua polyline kin (doan cong chia 8)
(defun sd:curve-pts (e / o n i k pts m q d)
  (setq o (vlax-ename->vla-object e)
        n (fix (+ 0.5 (vlax-curve-getEndParam e))) i 0)
  (repeat n
    (if (equal (vla-GetBulge o i) 0.0 1e-9)
      (if (setq q (vlax-curve-getPointAtParam e i)) (setq pts (cons (sd:2d q) pts)))
      (progn
        (setq k 0 m (max 4 (min 72 (fix (+ 1.0 (/ (* 4.0 (atan (abs (vla-GetBulge o i)))) (/ pi 36.0)))))))
        (repeat m
          (if (setq q (vlax-curve-getPointAtParam e (+ i (/ k (float m))))) (setq pts (cons (sd:2d q) pts)))
          (setq k (1+ k)))))
    (setq i (1+ i)))
  (setq pts (reverse pts))
  ;; vlax-curve khong tra duoc diem (polyline loi / dinh trung): doc thang cac dinh (10) tu du lieu
  (if (< (length pts) 3)
    (progn
      (setq pts nil)
      (foreach d (entget e) (if (= (car d) 10) (setq pts (cons (list (cadr d) (caddr d)) pts))))
      (setq pts (reverse pts))))
  pts)

(defun sd:inpoly (p pts / x y in a)
  (setq x (car p) y (cadr p) a (last pts))
  (foreach b pts
    (if (and (/= (> (cadr a) y) (> (cadr b) y))
             (< x (+ (car a) (/ (* (- (car b) (car a)) (- y (cadr a))) (- (cadr b) (cadr a))))))
      (setq in (not in)))
    (setq a b))
  in)

;; Canh cua cac vong bao: (p1 p2 xmin ymin xmax ymax)
(defun sd:edges (loops / r a)
  (foreach lp loops
    (setq a (last lp))
    (foreach b lp
      (setq r (cons (list a b (min (car a) (car b)) (min (cadr a) (cadr b))
                          (max (car a) (car b)) (max (cadr a) (cadr b))) r)
            a b)))
  r)

;; Phan loai vien: "F" nam tron trong vung, "P" bi cat, nil nam ngoai
(defun sd:tile-class (cs outer holes loops edges / x0 y0 x1 y1 cross cen sides)
  (setq x0 (apply 'min (mapcar 'car cs)) x1 (apply 'max (mapcar 'car cs))
        y0 (apply 'min (mapcar 'cadr cs)) y1 (apply 'max (mapcar 'cadr cs))
        sides (mapcar 'list cs (append (cdr cs) (list (car cs)))))
  (foreach e edges
    (if (and (not cross) (<= (nth 2 e) x1) (>= (nth 4 e) x0) (<= (nth 3 e) y1) (>= (nth 5 e) y0))
      (foreach s sides
        (if (inters (car s) (cadr s) (car e) (cadr e) t) (setq cross t)))))
  (cond (cross "P")
        ((vl-some '(lambda (lp) (sd:inpoly (car lp) cs)) loops) "P")
        ((progn (setq cen (list (/ (+ x0 x1) 2.0) (/ (+ y0 y1) 2.0)))
                (and (sd:inpoly cen outer) (not (vl-some '(lambda (h) (sd:inpoly cen h)) holes))))
         "F")))

(defun sd:objarr (lst)
  (vlax-make-variant
    (vlax-safearray-fill (vlax-make-safearray vlax-vbObject (cons 0 (1- (length lst)))) lst)))

(defun sd:region (e / r)
  (setq r (vl-catch-all-apply 'vla-AddRegion
            (list (sd:ms) (sd:objarr (list (vlax-ename->vla-object e))))))
  (if (not (vl-catch-all-error-p r)) (car (vlax-safearray->list (vlax-variant-value r)))))

;; Noi cac doan thang thanh vong kin
(defun sd:chain (segs / loops pts found)
  (while segs
    (setq pts (list (car (car segs)) (cadr (car segs))) segs (cdr segs) found t)
    (while (and found segs)
      (setq found nil)
      (foreach s segs
        (if (not found)
          (cond ((equal (car s) (last pts) 1e-4)
                 (setq pts (append pts (list (cadr s))) segs (vl-remove s segs) found t))
                ((equal (cadr s) (last pts) 1e-4)
                 (setq pts (append pts (list (car s))) segs (vl-remove s segs) found t))))))
    (if (equal (car pts) (last pts) 1e-4) (setq pts (reverse (cdr (reverse pts)))))
    (setq loops (cons pts loops)))
  loops)

(defun sd:tan (a) (/ (sin a) (cos a)))
;; Noi doan thang + cung thanh vong kin: segs = ((p1 p2 bulge) ...); tra ve ds vong, moi vong ((diem bulge-tu-diem-den-diem-ke) ...)
(defun sd:chain-b (segs / loops lp cur found)
  (while segs
    (setq lp (list (list (car (car segs)) (caddr (car segs)))) cur (cadr (car segs)) segs (cdr segs) found T)
    (while (and found segs)
      (setq found nil)
      (foreach s segs
        (if (not found)
          (cond ((equal (car s) cur 1e-4)
                 (setq lp (cons (list (car s) (caddr s)) lp) cur (cadr s) segs (vl-remove s segs) found T))
                ((equal (cadr s) cur 1e-4)
                 (setq lp (cons (list (cadr s) (- (caddr s))) lp) cur (car s) segs (vl-remove s segs) found T))))))
    (setq loops (cons (reverse lp) loops)))
  loops)

;; LWPOLYLINE kin co bulge (cung tron): lp = ((diem bulge) ...)
(defun sd:plinebulge (lp lay)
  (if (>= (length lp) 3)
    (entmake (append (list '(0 . "LWPOLYLINE") '(100 . "AcDbEntity") (cons 8 lay)
                           '(100 . "AcDbPolyline") (cons 90 (length lp)) '(70 . 1))
                     (apply 'append (mapcar '(lambda (v) (list (list 10 (car (car v)) (cadr (car v))) (cons 42 (cadr v)))) lp))))))

;; Region -> polyline (bien thang, hoac co cung: polyline co bulge). Tra ve list ename.
(defun sd:region->ents (rg lay / ex objs res)
  (setq ex (vl-catch-all-apply 'vla-Explode (list rg)))
  (if (vl-catch-all-error-p ex)
    (progn (vla-put-Layer rg lay) (list (vlax-vla-object->ename rg)))
    (progn
      (setq objs (vlax-safearray->list (vlax-variant-value ex)))
      (cond
        ((vl-every '(lambda (o) (= (vla-get-ObjectName o) "AcDbLine")) objs)
         (foreach lp (sd:chain (mapcar '(lambda (o) (list (sd:2d (vlax-get o 'StartPoint))
                                                          (sd:2d (vlax-get o 'EndPoint))))
                                       objs))
           (sd:pline lp t lay)
           (setq res (cons (entlast) res)))
         (foreach o objs (vla-Delete o))
         (vla-Delete rg)
         res)
        ;; bien co cung tron: doan thang + cung -> polyline co bulge (truoc day giu nguyen region nen manh cung bi mat / chia 0)
        ((vl-every '(lambda (o) (member (vla-get-ObjectName o) '("AcDbLine" "AcDbArc"))) objs)
         (foreach lp (sd:chain-b
                       (mapcar '(lambda (o)
                                  (if (= (vla-get-ObjectName o) "AcDbLine")
                                    (list (sd:2d (vlax-get o 'StartPoint)) (sd:2d (vlax-get o 'EndPoint)) 0.0)
                                    (list (sd:2d (vlax-get o 'StartPoint)) (sd:2d (vlax-get o 'EndPoint))
                                          (* (if (< (caddr (vlax-get o 'Normal)) 0.0) -1.0 1.0)
                                             (sd:tan (/ (rem (+ (- (vla-get-EndAngle o) (vla-get-StartAngle o)) (* 4.0 pi)) (* 2.0 pi)) 4.0))))))
                               objs))
           (sd:plinebulge lp lay)
           (setq res (cons (entlast) res)))
         (foreach o objs (vla-Delete o))
         (vla-Delete rg)
         res)
        ((vl-every '(lambda (o) (= (vla-get-ObjectName o) "AcDbRegion")) objs)
         (vla-Delete rg)
         (apply 'append (mapcar '(lambda (o) (sd:region->ents o lay)) objs)))
        (t
         (foreach o objs (vla-Delete o))
         (vla-put-Layer rg lay)
         (list (vlax-vla-object->ename rg)))))))

;; shp: "R" vien chu nhat (ve gia cong theo w x h), "G" theo hinh that (chevron, vat...)
(defun sd:tile-xd (mat typ pc pw ph ar anc name wn hn fa thk shp)
  (list -3 (list "SD_TILE" (cons 1000 mat) (cons 1000 typ) (cons 1000 pc)
                 (cons 1040 pw) (cons 1040 ph) (cons 1040 ar) (cons 1070 anc)
                 (cons 1000 name) (cons 1040 wn) (cons 1040 hn)
                 (cons 1040 fa) (cons 1040 thk) (cons 1000 (cond (shp) ("R"))))))

(defun sd:put-xd (e xd) (entmod (append (entget e) (list xd))))

;; Pat neo (op kho): 4 pat khi rong >= 400, 2 pat khi nho hon, 0 khi canh < 150
;; o, a = he toa do cuc bo; lo = goc trai duoi vien (cuc bo). Tra ve so pat.
(defun sd:anchors (o a lo w h sc / xs)
  (cond ((< (min w h) 150.0) 0)
        (t
         (setq xs (if (>= w 400.0)
                    (list (max 100.0 (/ w 5.0)) (- w (max 100.0 (/ w 5.0))))
                    (list (/ w 2.0))))
         (foreach x xs
           (foreach y (list 0.0 h)
             (sd:dot (sd:l2w o a (list (+ (car lo) x) (+ (cadr lo) y))) (* 1.5 sc) "SD-PAT")))
         (* 2 (length xs)))))

(defun sd:tile-th (w h sc) (min (* 2.0 sc) (max (* 0.4 (min w h)) (* 0.8 sc))))

;;; --------------------------------------------------------------------------
;;;  Tien ich hinh hoc cho op lat
;;; --------------------------------------------------------------------------
(defun sd:head (n lst / r) (repeat n (setq r (cons (car lst) r) lst (cdr lst))) (reverse r))
(defun sd:tail (n lst) (repeat n (setq lst (cdr lst))) lst)
(defun sd:remove-nth (i lst / j r)
  (setq j -1)
  (foreach x lst (if (/= (setq j (1+ j)) i) (setq r (cons x r))))
  (reverse r))
(defun sd:area (pts / s a)
  (setq s 0.0 a (last pts))
  (foreach b pts (setq s (+ s (- (* (car a) (cadr b)) (* (car b) (cadr a)))) a b))
  (/ s 2.0))
(defun sd:centroid (pts)
  (list (/ (apply '+ (mapcar 'car pts)) (length pts)) (/ (apply '+ (mapcar 'cadr pts)) (length pts))))

;; Cat da giac (toa do cuc bo) bang duong x = const, giu phia lon hon (gt=T) hoac nho hon
(defun sd:ix (a b x / k)
  (setq k (/ (- x (car a)) (- (car b) (car a))))
  (list x (+ (cadr a) (* k (- (cadr b) (cadr a))))))
(defun sd:clipx (pts x gt / r a ina inb)
  (setq a (last pts))
  (foreach b pts
    (setq ina (if gt (>= (car a) x) (<= (car a) x))
          inb (if gt (>= (car b) x) (<= (car b) x)))
    (if inb
      (progn (if (not ina) (setq r (cons (sd:ix a b x) r))) (setq r (cons b r)))
      (if ina (setq r (cons (sd:ix a b x) r))))
    (setq a b))
  (reverse r))

;; Offset polyline kin vao trong (inward = T) hoac ra ngoai mot khoang d.
;; d = 0 -> tra ve chinh no. Doi tuong tam duoc xoa trong sd:finish.
(defun sd:offset (e d inward / o a0 r objs best)
  (if (<= d 1e-6)
    e
    (progn
      (setq o (vlax-ename->vla-object e) a0 (vla-get-Area o))
      (foreach s '(1.0 -1.0)
        (if (not best)
          (progn
            (setq r (vl-catch-all-apply 'vla-Offset (list o (* s d))))
            (if (not (vl-catch-all-error-p r))
              (progn
                (setq objs (vlax-safearray->list (vlax-variant-value r)))
                (if (if inward (< (vla-get-Area (car objs)) a0) (> (vla-get-Area (car objs)) a0))
                  (setq best (car (sd:sort objs '(lambda (x y) (> (vla-get-Area x) (vla-get-Area y)))))))
                (foreach x objs (if (not (eq x best)) (vla-Delete x))))))))
      (if best
        (progn (setq *SD:TMP* (cons best *SD:TMP*)) (vlax-vla-object->ename best))))))

;; Sinh vien trong toa do cuc bo: (da-giac goc-phu goc-trai-duoi rong cao)
;; goc-trai-duoi = nil voi vien khong chu nhat (chevron)
(defun sd:rectpts (x y w h) (list (list x y) (list (+ x w) y) (list (+ x w) (+ y h)) (list x (+ y h))))
(defun sd:rect-tile (x y w h) (list (sd:rectpts x y w h) 0.0 (list x y) w h))

(defun sd:gen-grid (lx0 lx1 ly0 ly1 W H jt al off / px py ox oy k s i0 i1 r)
  (setq px (+ W jt) py (+ H jt)
        ox (cond ((= al "Tam") (/ W -2.0)) ((= al "Goc") 0.0) (t (/ jt 2.0)))
        oy (cond ((= al "Tam") (/ H -2.0)) ((= al "Goc") 0.0) (t (/ jt 2.0)))
        k  (- (fix (/ (- ly0 oy) py)) 2))
  (while (<= (+ oy (* k py)) ly1)
    (setq s  (* px (rem (* k off) 1.0))
          i0 (- (fix (/ (- lx0 ox s) px)) 2)
          i1 (+ (fix (/ (- lx1 ox s) px)) 1))
    (while (<= i0 i1)
      (setq r (cons (sd:rect-tile (+ ox s (* i0 px)) (+ oy (* k py)) W H) r) i0 (1+ i0)))
    (setq k (1+ k)))
  r)

;; Xuong ca 90 do: mang tinh tien t1 = (b',b'), t2 = (-a',a'); moi nut 1 vien nam + 1 vien dung
(defun sd:gen-herring (lx0 lx1 ly0 ly1 W H jt / a b a1 b1 cs ks ms k k1 m m0 m1 x y r)
  (setq a  (max W H) b (min W H) a1 (+ a jt) b1 (+ b jt)
        cs (list (list lx0 ly0) (list lx1 ly0) (list lx1 ly1) (list lx0 ly1))
        ks (mapcar '(lambda (p) (/ (+ (car p) (cadr p)) (* 2.0 b1))) cs)
        ms (mapcar '(lambda (p) (/ (- (cadr p) (car p)) (* 2.0 a1))) cs)
        k  (- (fix (apply 'min ks)) 2) k1 (+ (fix (apply 'max ks)) 2)
        m0 (- (fix (apply 'min ms)) 2) m1 (+ (fix (apply 'max ms)) 2))
  (while (<= k k1)
    (setq m m0)
    (while (<= m m1)
      (setq x (- (* k b1) (* m a1)) y (+ (* k b1) (* m a1)))
      (foreach tl (list (list x y a b) (list (+ x a1) (- (+ y b1) a1) b a))
        (if (and (<= (car tl) lx1) (>= (+ (car tl) (caddr tl)) lx0)
                 (<= (cadr tl) ly1) (>= (+ (cadr tl) (cadddr tl)) ly0))
          (setq r (cons (apply 'sd:rect-tile tl) r))))
      (setq m (1+ m)))
    (setq k (1+ k)))
  r)

;; Chevron (xuong ca vat): vien binh hanh, 2 dau cat song song duong song (goc vat th).
;; W = dai mui-mui, H = be rong vien. Cot j tren x = j(c+mach), cot chan doc len, cot le doc xuong.
(defun sd:gen-chevron (lx0 lx1 ly0 ly1 W H jt th / tn c e p cx j j1 x0 k y up r)
  (setq tn (/ (sin th) (cos th))
        c  (* (- W (* H tn)) (cos th))
        e  (/ H (cos th))
        p  (+ e (/ jt (cos th)))
        cx (+ c jt)
        j  (- (fix (/ lx0 cx)) 2) j1 (+ (fix (/ lx1 cx)) 2))
  (while (<= j j1)
    (setq x0 (* j cx) up (= (rem (abs j) 2) 0)
          k  (- (fix (/ (- ly0 (* c tn) e) p)) 2))
    (while (<= (* k p) (+ ly1 1.0))
      (setq y (* k p))
      (setq r (cons (list (if up
                            (list (list x0 y) (list (+ x0 c) (+ y (* c tn)))
                                  (list (+ x0 c) (+ y (* c tn) e)) (list x0 (+ y e)))
                            (list (list x0 (+ y (* c tn))) (list (+ x0 c) y)
                                  (list (+ x0 c) (+ y e)) (list x0 (+ y (* c tn) e))))
                          (if up th (- th)) nil W H)
                    r)
            k (1+ k)))
    (setq j (1+ j)))
  r)

;; Ve vien vien giua eo va ei, tra ve ban ghi vien (ents w h dt loai tam lo fo fa)
(defun sd:draw-border (eo ei blen bw jt / rb res)
  (if (and eo ei (setq rb (sd:border-pieces eo ei blen jt)))
    (foreach b rb
      (sd:pline (car b) t "SD-GACH-VIEN")
      (setq res (cons (list (list (entlast)) (nth 1 b) (nth 2 b) (nth 3 b)
                            (sd:rect-typ (nth 1 b) (nth 2 b) (nth 3 b) (list blen bw))
                            (nth 4 b) (nth 5 b) (nth 6 b) (nth 7 b))
                      res)))
    (princ "\n[SD] Khong chia duoc vien vien (duong bao co cung tron hoac canh qua ngan)."))
  res)

;; Vien vien giua 2 duong offset (eo ngoai, ei trong): chia moi canh thanh vien dai lb,
;; doi xung giua canh, goc vat mitre. Tra ve ban ghi (poly w h dt tam lo fo fa) hoac nil.
(defun sd:border-pieces (eo ei lb jt / ol il n i j k best fo fa q ql smin smax tt nn s0 a b lp res ok)
  (setq ol (sd:curve-pts eo) il (sd:curve-pts ei) ok t)
  (if (/= (length ol) (length il))
    nil
    (progn
      (setq i 0)
      (foreach p il
        (if (or (null best) (< (distance p (car ol)) (car best))) (setq best (list (distance p (car ol)) i)))
        (setq i (1+ i)))
      (setq il (append (sd:tail (cadr best) il) (sd:head (cadr best) il)))
      (if (> (distance (cadr ol) (cadr il)) (distance (cadr ol) (last il)))
        (setq il (cons (car il) (reverse (cdr il)))))
      (setq n (length ol) i 0)
      (repeat n
        (setq j  (rem (1+ i) n)
              fo (nth i ol)
              fa (angle (nth i ol) (nth j ol))
              q  (list (nth i ol) (nth j ol) (nth j il) (nth i il))
              ql (mapcar '(lambda (p) (sd:w2l fo fa p)) q))
        ;; canh trong phai cung chieu canh ngoai (khong bi suy bien)
        (if (<= (- (car (nth 2 ql)) (car (nth 3 ql))) 0) (setq ok nil))
        (setq smin (apply 'min (mapcar 'car ql)) smax (apply 'max (mapcar 'car ql))
              tt   (- smax smin)
              nn   (fix (+ (/ (+ tt jt) (+ lb jt)) 0.999999))
              s0   (- smin (/ (- (* nn (+ lb jt)) jt tt) 2.0))
              k    0)
        (repeat nn
          (setq a (max smin (+ s0 (* k (+ lb jt)))) b (min smax (+ s0 (* k (+ lb jt)) lb)) k (1+ k))
          (if (> (- b a) 1.0)
            (progn
              (setq lp (sd:clipx (sd:clipx ql a t) b nil))
              (if (and (> (length lp) 2) (> (abs (sd:area lp)) 100.0))
                (setq res (cons (list (mapcar '(lambda (p) (sd:l2w fo fa p)) lp)
                                      (- (apply 'max (mapcar 'car lp)) (apply 'min (mapcar 'car lp)))
                                      (- (apply 'max (mapcar 'cadr lp)) (apply 'min (mapcar 'cadr lp)))
                                      (abs (sd:area lp))
                                      (sd:l2w fo fa (sd:centroid lp))
                                      (list (apply 'min (mapcar 'car lp)) (apply 'min (mapcar 'cadr lp)))
                                      fo fa)
                                res))))))
        (setq i (1+ i)))
      (if ok res))))

;; Gan XDATA cho 1 vien (vong dau = vien chinh, cac vong sau = lo khoet, loai "X")
(defun sd:tag-piece (p code mat name wn hn thk anct / i)
  (setq i 0)
  (foreach x (car p)
    (sd:put-xd x (sd:tile-xd mat (if (= i 0) (nth 4 p) "X") code (nth 1 p) (nth 2 p) (nth 3 p)
                             (if (= i 0) anct 0) name wn hn (nth 8 p) thk (nth 9 p)))
    (setq i (1+ i))))

;; Danh ma vien: loai F -> ma VL; vien cat gom theo kich thuoc -> MA-C1, MA-C2... (lon truoc)
;; ban ghi p = (ents w h dt loai tam lo fo fa). Tra ve (so-ma so-pat)
(defun sd:code-pieces (pieces mat name wn hn thk anc sc / grp key e cnt tc anct nanc)
  (setq nanc 0 cnt 0)
  (foreach p pieces
    (if (= (nth 4 p) "F")
      (progn
        (setq anct (if anc (sd:anchors (nth 7 p) (nth 8 p) (nth 6 p) (nth 1 p) (nth 2 p) sc) 0)
              nanc (+ nanc anct))
        (sd:tag-piece p mat mat name wn hn thk anct))
      (progn
        (setq key (if (= (nth 4 p) "C")
                    (list "C" (fix (+ 0.5 (max (nth 1 p) (nth 2 p)))) (fix (+ 0.5 (min (nth 1 p) (nth 2 p)))) 0)
                    (list "D" (fix (+ 0.5 (nth 1 p))) (fix (+ 0.5 (nth 2 p))) (fix (/ (nth 3 p) 1000.0)))))
        (if (setq e (assoc key grp))
          (setq grp (subst (cons key (cons p (cdr e))) e grp))
          (setq grp (cons (list key p) grp))))))
  (setq grp (sd:sort grp '(lambda (a b) (> (* (nth 1 (car a)) (nth 2 (car a)))
                                         (* (nth 1 (car b)) (nth 2 (car b)))))))
  (foreach g grp
    (setq cnt (1+ cnt) tc (strcat mat "-C" (itoa cnt)))
    (foreach p (cdr g)
      (setq anct (if (and anc (= (nth 4 p) "C"))
                   (sd:anchors (nth 7 p) (nth 8 p) (nth 6 p) (nth 1 p) (nth 2 p) sc) 0)
            nanc (+ nanc anct))
      (sd:tag-piece p tc mat name wn hn thk anct)
      (if (not *SD:NOLBLC*) (sd:text (sd:2d (nth 5 p)) tc (sd:tile-th (nth 1 p) (nth 2 p) sc) "MC" "SD-CHU"))))
  (list cnt nanc))

(defun sd:rect-typ (w h ar full)
  (cond ((not (equal ar (* w h) (* 0.002 ar))) "D")
        ((and full (equal (max w h) (max (car full) (cadr full)) 0.5)
                   (equal (min w h) (min (car full) (cadr full)) 0.5)) "F")
        (t "C")))

;;; --------------------------------------------------------------------------
;;;  SDGACH - Chia gach / da: thang, so le, xuong ca; vien vien; khe sat tuong
;;; --------------------------------------------------------------------------
;; Cac polyline vien tao ra sau thuc the e0 (layer SD-GACH / SD-GACH-CAT / SD-GACH-VIEN, kin)
(defun sd:gach-new (e0 / e r ed)
  (setq e (if e0 (entnext e0) (entnext)))
  (while e
    (setq ed (entget e))
    (if (and ed (= (cdr (assoc 0 ed)) "LWPOLYLINE")
             (member (cdr (assoc 8 ed)) '("SD-GACH" "SD-GACH-CAT" "SD-GACH-VIEN"))
             (= 1 (logand 1 (cdr (assoc 70 ed)))))
      (setq r (cons e r)))
    (setq e (entnext e)))
  (reverse r))

(defun c:SDGACH (/ e0 sc es outer-e ssh i e holes-e mat name W H thk jt gap pat off ang al o anc lblf
                   bord bmat bw blen eo ei ef hf outer holes loops edges R tr C pa cen ents vp
                   lpts lx0 lx1 ly0 ly1 tiles lo tw th cs cls nf nanc pieces bpieces wl hl anct rc rb
                   cva hbord fa ta mx my mc)
  (sd:begin)
  (setq sc (sd:sc))
  (setq es (if *SD:GBATCH* (list *SD:GOUTER*) (entsel "\nChon duong bao vung op lat (polyline kin, mat tuong / mep san): ")))
  (if (not (and es (= (cdr (assoc 0 (entget (car es)))) "LWPOLYLINE")
                (vlax-curve-isClosed (car es))))
    (princ "\n[SD] Can chon 1 polyline kin (dung PLINE, RECTANG hoac BOUNDARY de tao).")
    (progn
      (setq outer-e (car es))
      (if *SD:GBATCH*
        (setq holes-e *SD:GHOLES*)
        (progn
          (princ "\nChon cac lo / vat can ben trong (cot, hop ky thuat, cua...) <Enter neu khong co>: ")
          (if (setq ssh (ssget '((0 . "LWPOLYLINE"))))
            (progn
              (setq i 0)
              (repeat (sslength ssh)
                (setq e (ssname ssh i) i (1+ i))
                (if (and (not (eq e outer-e)) (vlax-curve-isClosed e)) (setq holes-e (cons e holes-e))))))))
      (if (not *SD:GBATCH*) (sd:vl-pick))
      ;; thong so vien (hop thoai)
      (if (not (sd:dlg "Chia vien op lat (SDGACH)"
                       (list (list "mat" "Ma vat lieu" 'str (cond (*SD:GCODE*) ("G1")))
                             (list "name" "Ten vat lieu" 'str (cond (*SD:GNAME*) ("Granite 600x600x20")))
                             (list "W" "Vien thanh pham - ngang W (mm)" 'real (cond (*SD:GW*) (600.0)))
                             (list "H" "Vien thanh pham - dung H (mm)" 'real (cond (*SD:GH*) (600.0)))
                             (list "thk" "Chieu day da / gach (mm)" 'real (cond (*SD:GT*) (20.0)))
                             (list "jt" "Be rong mach / ron (mm)" 'real0 (cond (*SD:GJ*) ((sd:cfg "RON-CU" 2.0))))
                             (list "gap" "Khe sat tuong va quanh lo (mm)" 'real0 (cond (*SD:GGAP*) (0.0)))
                             (list "pat" "Kieu lat" 'kw (cond (*SD:GPAT*) ("Thang"))
                                   '(("Thang" . "Thang") ("Sole" . "So le") ("Xuongca" . "Xuong ca 90 do")
                                     ("Chevron" . "Chevron (xuong ca vat)")))
                             (list "off" "Do so le (0.5 = 1/2 vien)" 'real 0.5 nil '("pat" "Sole"))
                             (list "cva" "Goc vat chevron (do)" 'real (cond (*SD:GCVA*) (45.0)) nil '("pat" "Chevron"))
                             (list "ang" "Goc xoay (do)" 'real0 0.0)
                             (list "al" "Diem bat dau dat o" 'kw "Mach" '(("Mach" . "Mach") ("Tam" . "Tam vien") ("Goc" . "Goc vien"))
                                   '("pat" "Thang" "Sole"))
                             (list "bord" "Lat vien vien quanh mep" 'tog nil)
                             (list "hbord" "Lat vien vien quanh cot / lo" 'tog nil)
                             (list "bmat" "Ma vien vien" 'str (cond (*SD:BCODE*) ("V1")))
                             (list "bw" "Be rong vien vien (mm)" 'real (cond (*SD:BW*) (150.0)))
                             (list "blen" "Chieu dai 1 vien vien (mm)" 'real (cond (*SD:BLEN*) (600.0)))
                             (list "anc" "Ve pat neo (op kho)" 'tog nil)
                             (list "lblf" "Ghi ma len vien nguyen" 'tog nil)
                             (list "lblc" "Ghi ma len vien cat / vien le (G1-C1...)" 'tog t)
                             (list "anh" "Cat anh tam da that vao cac vien (khai bao nhu SDANHDA)" 'tog nil)
                             (list "chieu" "Chieu van tren vien (cat anh tam da)" 'kw (cond (*SD:ICHIEU*) ("Toiuu"))
                                   '(("Toiuu" . "Tu xoay 90 do de it hao") ("Doc" . "Van theo canh dai vien") ("Ngang" . "Van vuong goc canh dai") ("Chinh" . "Van theo huong vien chinh (chon 1 vien, moi vien deu 1 huong)")))
                             (list "xep" "Cach xep vien vao tam da (cat anh)" 'kw (cond (*SD:IXEP*) ("Toiuu"))
                                   '(("Toiuu" . "It hao nhat: cat xuyen, manh nho lap vao phe lieu") ("Thutu" . "Theo thu tu lat (van gan nhau)")
                                     ("Duongviem" . "Chay doc duong vien (van lien tuc)"))))))
        (exit))
      (setq mat (sd:v "mat") name (sd:v "name") W (sd:v "W") H (sd:v "H") thk (sd:v "thk") jt (sd:v "jt")
            gap (sd:v "gap") pat (sd:v "pat") *SD:GPAT* pat al (sd:v "al")
            bord (sd:v "bord") hbord (and holes-e (sd:v "hbord"))
            bmat (sd:v "bmat") bw (sd:v "bw") blen (sd:v "blen") anc (sd:v "anc") lblf (sd:v "lblf")
            *SD:NOLBLC* (not (sd:v "lblc"))
            *SD:BCODE* bmat *SD:BW* bw *SD:BLEN* blen
            ang (* pi (/ (sd:v "ang") 180.0)))
      (if (and (member pat '("Xuongca" "Chevron")) (equal W H 0.5))
        (progn (princ "\n[SD] Xuong ca / chevron can vien chu nhat (W khac H). Chuyen ve lat thang.")
               (setq pat "Thang")))
      (if (= pat "Chevron")
        (progn
          (setq cva (* pi (/ (sd:v "cva") 180.0)) *SD:GCVA* (sd:v "cva"))
          (if (or (>= cva (/ pi 2)) (<= (- (max W H) (* (min W H) (/ (sin cva) (cos cva)))) 0))
            (progn (princ "\n[SD] Vien qua ngan so voi goc vat (can W > H.tan(goc)). Chuyen ve lat thang.")
                   (setq pat "Thang")))))
      (setq off (if (= pat "Sole") (sd:v "off") 0.0))
      (if (not (member pat '("Thang" "Sole"))) (setq al "Mach"))
      (setq o (if *SD:GBATCH* *SD:GSTART* (sd:getpt "\nDiem bat dau chia <Enter = tam vung>: " nil)) e0 (entlast))
      (setq *SD:GCODE* mat *SD:GNAME* name *SD:GW* W *SD:GH* H *SD:GJ* (sd:cfg-put "RON-CU" jt) *SD:GGAP* gap *SD:GT* thk)
      (if (not *SD:GBATCH*) (sd:vl-save mat name W H thk jt gap pat))
      ;; duong bao vung lat chinh = bao ngoai offset vao (khe + vien + mach); lo offset ra (khe)
      (setq ef (sd:offset outer-e (+ gap (if bord (+ bw jt) 0.0)) t)
            hf (vl-remove nil (mapcar '(lambda (x) (sd:offset x (+ gap (if hbord (+ bw jt) 0.0)) nil)) holes-e)))
      (if (null ef) (progn (princ "\n[SD] Khong offset duoc duong bao (vung qua hep?).") (exit)))
      (if (null o)
        (setq o (sd:centroid (list (car (sd:bbox (sd:curve-pts ef))) (cadr (sd:bbox (sd:curve-pts ef)))))))
      (setq o (sd:2d o))
      ;; ---- vien vien
      (if bord
        (setq bpieces (sd:draw-border (sd:offset outer-e gap t) (sd:offset outer-e (+ gap bw) t) blen bw jt)))
      ;; ---- vien quanh cot / lo (bat dau tu mep lo + khe, chay ra ngoai)
      (if hbord
        (foreach x holes-e
          (setq bpieces (append bpieces
                                (sd:draw-border (sd:offset x gap nil) (sd:offset x (+ gap bw) nil) blen bw jt)))))
      ;; ---- vung lat chinh
      (setq outer (sd:curve-pts ef)
            holes (mapcar 'sd:curve-pts hf)
            loops (cons outer holes)
            edges (sd:edges loops)
            R     (sd:region ef))
      (if (null R) (progn (princ "\n[SD] Khong tao duoc region tu duong bao (tu cat nhau?).") (exit)))
      (foreach x hf (if (setq tr (sd:region x)) (vla-Boolean R 2 tr)))
      (setq lpts (mapcar '(lambda (p) (sd:w2l o ang p)) outer)
            lx0 (apply 'min (mapcar 'car lpts)) lx1 (apply 'max (mapcar 'car lpts))
            ly0 (apply 'min (mapcar 'cadr lpts)) ly1 (apply 'max (mapcar 'cadr lpts))
            tiles (cond ((= pat "Xuongca") (sd:gen-herring lx0 lx1 ly0 ly1 W H jt))
                        ((= pat "Chevron") (sd:gen-chevron lx0 lx1 ly0 ly1 (max W H) (min W H) jt cva))
                        (t (sd:gen-grid lx0 lx1 ly0 ly1 W H jt al off)))
            nf 0 nanc 0)
      (princ (strcat "\nDang xu ly " (itoa (length tiles)) " vi tri vien..."))
      (foreach tl tiles
        (setq lo (nth 2 tl) tw (nth 3 tl) th (nth 4 tl) fa (+ ang (nth 1 tl))
              cs (mapcar '(lambda (p) (sd:l2w o ang p)) (car tl))
              ta (abs (sd:area (car tl)))
              cls (sd:tile-class cs outer holes loops edges))
        (if (= cls "P")
          (progn
            (sd:pline cs t "SD-GACH-CAT")
            (setq e (entlast) tr (sd:region e))
            (entdel e)
            (setq C (vla-Copy R))
            (vla-Boolean C 1 tr)
            (setq pa (vla-get-Area C))
            (cond ((< pa 100.0) (vla-Delete C) (setq cls nil))
                  ((>= pa (* 0.999 ta)) (vla-Delete C) (setq cls "F"))
                  (t
                   (setq cen  (vlax-safearray->list (vlax-variant-value (vla-get-Centroid C)))
                         ents (sd:region->ents C "SD-GACH-CAT")
                         vp   nil)
                   (foreach x ents
                     (if (= (cdr (assoc 0 (entget x))) "LWPOLYLINE")
                       (foreach g (entget x)
                         (if (= (car g) 10) (setq vp (cons (sd:w2l o fa (cdr g)) vp))))))
                   (if (null vp) (setq vp (mapcar '(lambda (p) (sd:w2l o fa p)) cs)))
                   (setq wl (- (apply 'max (mapcar 'car vp)) (apply 'min (mapcar 'car vp)))
                         hl (- (apply 'max (mapcar 'cadr vp)) (apply 'min (mapcar 'cadr vp))))
                   (setq pieces (cons (list ents wl hl pa
                                            (if (= (length ents) 1) (sd:rect-typ wl hl pa nil) "D")
                                            cen
                                            (list (apply 'min (mapcar 'car vp)) (apply 'min (mapcar 'cadr vp)))
                                            o fa)
                                      pieces))))))
        (if (= cls "F")
          (progn
            (setq anct (if (and anc lo) (sd:anchors o ang lo tw th sc) 0))
            (sd:mk-tile-poly "SD-GACH" cs
                           (sd:tile-xd mat "F" mat tw th ta anct name W H fa thk (if lo "R" "G")))
            (setq nf (1+ nf) nanc (+ nanc anct))
            (if lblf
              (sd:text (sd:centroid cs) mat (sd:tile-th tw th sc) "MC" "SD-CHU")))))
      ;; ---- danh dau vien bat dau (layer SD-DIEMBD): vien nam tai goc luoi (theo "Diem bat dau dat o"), X xuyen vien + vong tron tai diem bat dau
      (if (and (not *SD:GBATCH*) (member pat '("Thang" "Sole")))
        (progn
          (sd:make-layer "SD-DIEMBD" 3 "Continuous" 25)
          (setq mx (cond ((= al "Tam") (/ W -2.0)) ((= al "Goc") 0.0) (t (/ jt 2.0)))
                my (cond ((= al "Tam") (/ H -2.0)) ((= al "Goc") 0.0) (t (/ jt 2.0)))
                mc (mapcar '(lambda (q) (sd:l2w o ang q))
                           (list (list mx my) (list (+ mx W) my) (list (+ mx W) (+ my H)) (list mx (+ my H)))))
          (sd:pline mc t "SD-DIEMBD")
          (sd:line (append (list (car (nth 0 mc)) (cadr (nth 0 mc))) '(0.0)) (append (list (car (nth 2 mc)) (cadr (nth 2 mc))) '(0.0)) "SD-DIEMBD")
          (sd:line (append (list (car (nth 1 mc)) (cadr (nth 1 mc))) '(0.0)) (append (list (car (nth 3 mc)) (cadr (nth 3 mc))) '(0.0)) "SD-DIEMBD")
          (entmake (list '(0 . "CIRCLE") '(8 . "SD-DIEMBD") (cons 10 (list (car o) (cadr o) 0.0)) (cons 40 (* 3.0 sc))))
          (sd:text (sd:centroid mc) "BAT DAU" (* 2.5 sc) "MC" "SD-DIEMBD")
          (princ "\n[SD] Da danh dau vien bat dau (layer SD-DIEMBD, mau xanh la); tat/xoa layer nay khi khong can.")))
      (setq rc (sd:code-pieces pieces mat name W H thk anc sc))
      (if bpieces (setq rb (sd:code-pieces bpieces bmat (strcat "Vien " name) blen bw thk anc sc)))
      (setq *SD:NOLBLC* nil)
      (princ (strcat "\n[SD] " mat ": dien tich lat " (sd:rtos (/ (vla-get-Area R) 1e6) 2) " m2; "
                     (itoa nf) " vien nguyen; " (itoa (length pieces)) " vien cat (" (itoa (car rc)) " ma)"
                     (if bpieces (strcat "; vien " bmat ": " (itoa (length bpieces)) " vien ("
                                         (itoa (car rb)) " ma cat)") "")
                     (if anc (strcat "; " (itoa (+ nanc (cadr rc) (if bpieces (cadr rb) 0))) " pat") "")
                     ". Dung SDGACHTK / SDDATHO / SDGIACONG de thong ke, cat da tho, ve gia cong."))
      (vla-Delete R)
      (if (sd:v "anh")
        (progn (setq *SD:ICHIEU* (cond ((sd:v "chieu")) ("Toiuu")) *SD:IXEP* (cond ((sd:v "xep")) ("Toiuu")))
               (sd:anhda (sd:gach-new e0))))))
  (sd:finish))

(defun sd:bbox (pts)
  (list (list (apply 'min (mapcar 'car pts)) (apply 'min (mapcar 'cadr pts)))
        (list (apply 'max (mapcar 'car pts)) (apply 'max (mapcar 'cadr pts)))))

;;; --------------------------------------------------------------------------
;;;  SDGACHTK - Bang thong ke vien op lat + du tru so vien dat hang
;;; --------------------------------------------------------------------------
(defun sd:pc-idx (pc / p) (if (setq p (vl-string-search "-C" pc)) (atoi (substr pc (+ p 3))) 0))
(defun sd:addcnt (x n lst / e)
  (if (setq e (assoc x lst)) (subst (cons x (+ (cdr e) n)) e lst) (cons (cons x n) lst)))
(defun sd:desc (lst) (sd:sort lst '(lambda (a b) (> (car a) (car b)))))

(defun c:SDGACHTK (/ flt ss i xd key g grp mats kerf loss trows lines recs n nf nc ar anct
                     items1 items2 W H wl hl b1 b2 need order pt fn f)
  (sd:begin)
  (setq flt '((-3 ("SD_TILE"))))
  (princ "\nChon cac vien (tao bang SDGACH) <Enter = tat ca trong ban ve>: ")
  (if (not (setq ss (cond ((ssget flt)) ((ssget "_X" flt)))))
    (princ "\n[SD] Khong tim thay vien nao (dung lenh SDGACH de chia vien).")
    (progn
      (if (not (sd:dlg "Thong ke vien op lat (SDGACHTK)"
                       (list (list "kerf" "Be rong mach cat may (mm)" 'real0 3.0)
                             (list "loss" "Hao hut van chuyen / vo (%)" 'real0 3.0))))
        (exit))
      (setq kerf (sd:v "kerf") loss (sd:v "loss"))
      ;; grp: (khoa SL ename xd), xd = (maVL loai maVien w h dt pat ten W H goc day)
      (setq grp (sd:tile-groups ss))
      (foreach g grp (if (not (member (car (nth 3 g)) mats)) (setq mats (cons (car (nth 3 g)) mats))))
      (foreach mat (vl-sort mats '<)
        (setq recs (vl-remove-if-not '(lambda (g) (= (car (nth 3 g)) mat)) grp)
              recs (sd:sort recs
                     '(lambda (a b)
                        (if (/= (= (nth 1 (nth 3 a)) "F") (= (nth 1 (nth 3 b)) "F"))
                          (= (nth 1 (nth 3 a)) "F")
                          (< (sd:pc-idx (nth 2 (nth 3 a))) (sd:pc-idx (nth 2 (nth 3 b)))))))
              nf 0 nc 0 ar 0.0 anct 0 items1 nil items2 nil
              W (nth 8 (nth 3 (car recs))) H (nth 9 (nth 3 (car recs))))
        (foreach g recs
          (setq xd (nth 3 g) n (nth 1 g) wl (nth 3 xd) hl (nth 4 xd)
                ar (+ ar (* n (nth 5 xd))) anct (+ anct (* n (nth 6 xd))))
          ;; dua vien ve cung phuong voi vien nguyen W x H (vd vien dung trong xuong ca)
          (if (or (> wl (+ W 0.5)) (> hl (+ H 0.5))) (setq wl (nth 4 xd) hl (nth 3 xd)))
          (setq trows (cons (list "R" (list (nth 2 xd)
                                            (cond ((= (nth 1 xd) "F") "Nguy\\U+00EAn")
                                                  ((= (nth 1 xd) "C") "C\\U+1EAFt CN")
                                                  (t "C\\U+1EAFt \\U+0110B"))
                                            (strcat (sd:rtos wl 0) "\\U+00D7" (sd:rtos hl 0))
                                            (itoa n) (sd:rtos (/ (nth 5 xd) 1e6) 3)
                                            (sd:rtos (/ (* n (nth 5 xd)) 1e6) 2) (itoa (* n (nth 6 xd))))
                                  nil)
                            trows)
                lines (cons (sd:join (list mat (nth 2 xd) (nth 1 xd) (sd:rtos wl 0) (sd:rtos hl 0)
                                           (itoa n) (sd:rtos (/ (nth 5 xd) 1e6) 4)
                                           (sd:rtos (/ (* n (nth 5 xd)) 1e6) 3) (itoa (* n (nth 6 xd))))
                                     ";")
                            lines))
          ;; ghep doan cat tu vien nguyen: dai theo W (cao du H) hoac dai theo H (rong du W)
          (if (= (nth 1 xd) "F")
            (setq nf (+ nf n))
            (progn
              (setq nc (+ nc n))
              (cond ((>= hl (- H 0.5)) (setq items1 (sd:addcnt wl n items1)))
                    ((>= wl (- W 0.5)) (setq items2 (sd:addcnt hl n items2)))
                    (t (setq items1 (sd:addcnt wl n items1)))))))
        (setq b1    (length (sd:bfd (sd:desc items1) W kerf))
              b2    (length (sd:bfd (sd:desc items2) H kerf))
              need  (+ nf b1 b2)
              order (fix (+ (* need (+ 1.0 (/ loss 100.0))) 0.999999)))
        (setq trows (cons (list "W" (strcat mat " (" (nth 7 (nth 3 (car recs))) ") - " (sd:rtos (/ ar 1e6) 2) " m\\U+00B2 \\U+1ED1p l\\U+00E1t; " (itoa nf)
                                            " vi\\U+00EAn nguy\\U+00EAn + " (itoa nc) " vi\\U+00EAn c\\U+1EAFt (gh\\U+00E9p t\\U+1EEB "
                                            (itoa (+ b1 b2)) " vi\\U+00EAn)" (if (> anct 0) (strcat "; " (itoa anct) " p\\U+00E1t") "")))
                          trows)
              trows (cons (list "W" (strcat "   \\U+0110\\U+1EB7t h\\U+00E0ng " (sd:num W) "\\U+00D7" (sd:num H) ": " (itoa need)
                                            " + hao h\\U+1EE5t " (sd:num loss) "% = " (itoa order) " vi\\U+00EAn = "
                                            (sd:rtos (/ (* order W H) 1e6) 2) " m\\U+00B2"))
                          trows))
        (princ (strcat "\n " mat ": " (itoa nf) " vien nguyen, " (itoa nc) " vien cat -> dat "
                       (itoa order) " vien (" (sd:rtos (/ (* order W H) 1e6) 2) " m2)")))
      (setq trows (reverse trows))
      (if (setq pt (sd:getpt "\nDiem chen bang (goc trai tren): " nil))
        (sd:table2 pt "B\\U+1EA2NG TH\\U+1ED0NG K\\U+00CA VI\\U+00CAN \\U+1ED0P L\\U+00C1T"
                   '(("M\\U+00C3" 22) ("LO\\U+1EA0I" 20) ("K\\U+00CDCH TH\\U+01AF\\U+1EDAC (mm)" 32) ("SL" 12)
                     ("DT 1 VI\\U+00CAN (m\\U+00B2)" 26) ("T\\U+1ED4NG DT (m\\U+00B2)" 24) ("P\\U+00C1T" 14))
                   trows -1 (sd:sc)))
      (setq fn (sd:csv-name "_ThongKeOpLat.csv"))
      (if (setq f (sd:open fn "w"))
        (progn
          (write-line "Ma VL;Ma vien;Loai (F nguyen/C cat CN/D cat dac biet);Rong (mm);Cao (mm);SL;DT 1 vien (m2);Tong DT (m2);Pat" f)
          (foreach l (reverse lines) (write-line l f))
          (setq fn (sd:close f))
          (princ (strcat "\n[SD] Da xuat: " fn))))))
  (sd:finish))

;;; --------------------------------------------------------------------------
;;;  SDCATDU - Cat du: vien cat nao, canh nao sat tuong / vat can phai cat dai ra de ra cong truong be lai cho khit
;;;  Canh bien = canh khong co vien khac nam sat ben ngoai. Moi canh bien cua vien cat duoc cong them "du" mm.
;;; --------------------------------------------------------------------------
(defun sd:cd-bbox (pts) (list (apply 'min (mapcar 'car pts)) (apply 'min (mapcar 'cadr pts)) (apply 'max (mapcar 'car pts)) (apply 'max (mapcar 'cadr pts))))
;; rec = (bbox pts ...): diem p co nam trong vien do khong
(defun sd:cd-in (p rec)
  (and (>= (car p) (car (car rec))) (<= (car p) (caddr (car rec))) (>= (cadr p) (cadr (car rec))) (<= (cadr p) (cadddr (car rec)))
       (sd:inpoly p (cadr rec))))
;; Cac canh bien cua da giac pts: (a b dai goc diem-ngoai); recs = (ename bbox pts xd) cua moi vien; d = khoang thu ra ngoai (mm)
(defun sd:cd-edges (pts self recs d / a r dx dy ln nx ny mx my p1 p2 po)
  (setq a (last pts))
  (foreach b pts
    (setq dx (- (car b) (car a)) dy (- (cadr b) (cadr a)) ln (sqrt (+ (* dx dx) (* dy dy))) po nil)
    (if (> ln 20.0)
      (progn
        (setq nx (/ (- dy) ln) ny (/ dx ln) mx (/ (+ (car a) (car b)) 2.0) my (/ (+ (cadr a) (cadr b)) 2.0)
              p1 (list (+ mx (* d nx)) (+ my (* d ny))) p2 (list (- mx (* d nx)) (- my (* d ny)))
              po (cond ((and (sd:inpoly p1 pts) (not (sd:inpoly p2 pts))) p2)
                       ((and (sd:inpoly p2 pts) (not (sd:inpoly p1 pts))) p1)))
        (if (and po (not (vl-some '(lambda (rc) (and (not (equal (car rc) self)) (sd:cd-in po (cdr rc)))) recs)))
          (setq r (cons (list a b ln (angle a b) po) r)))))
    (setq a b))
  (reverse r))
(defun sd:cd-clear (lay / ss i)
  (if (setq ss (ssget "_X" (list (cons 8 lay))))
    (progn (setq i 0) (repeat (sslength ss) (entdel (ssname ss i)) (setq i (1+ i))))))
;; Diem p (2D) cach net tuong nao do khong qua kc mm (walls = danh sach ename LINE / POLYLINE / ARC...)
(defun sd:cd-near (p walls kc)
  (vl-some '(lambda (w / q) (and (setq q (vlax-curve-getClosestPointTo w (list (car p) (cadr p) 0.0))) (< (distance p (sd:2d q)) kc))) walls))
;; dien tich da giac (mm2)
(defun sd:cd-area (pts / a s)
  (setq a (last pts) s 0.0)
  (foreach b pts (setq s (+ s (- (* (car a) (cadr b)) (* (car b) (cadr a)))) a b))
  (/ (abs s) 2.0))

;; Cac layer SD-CAODO-BAC-<mm> dang co trong ban ve: ((ten . mm) ...)
(defun sd:cd-bac-layers (/ l r nm)
  (setq l (tblnext "LAYER" t))
  (while l
    (setq nm (cdr (assoc 2 l)))
    (if (and (> (strlen nm) 13) (= (strcase (substr nm 1 13)) "SD-CAODO-BAC-") (> (atof (substr nm 14)) 0.0))
      (setq r (cons (cons nm (atof (substr nm 14))) r)))
    (setq l (tblnext "LAYER")))
  r)

;; Ghi chu rui ro khi cat du, ghi len ban ve (layer SD-CATDU-GHICHU); pt = goc tren trai
(defun sd:cd-notes (pt du kc nxt ncdo sc / lay h y notes n)
  (setq lay (sd:make-layer "SD-CATDU-GHICHU" 2 "Continuous" 18) h (* 2.5 sc) y 0.0 n 0)
  (sd:cd-clear lay)
  (setq notes
    (list (strcat "D\\U+01B0 m\\U+1EB7c \\U+0111\\U+1ECBnh " (sd:num du) " mm; kho\\U+1EA3ng s\\U+00E1t n\\U+00E9t quy t\\U+1EAFc " (sd:num kc) " mm; " (itoa ncdo) " layer \\U+0111\\U+1ED5i cao \\U+0111\\U+1ED9 SD-CAODO-BAC-mm \\U+0111\\U+01B0\\U+1EE3c nh\\U+1EADn.")
          "1. D\\U+01B0 l\\U+00E0 s\\U+1ED1 c\\U+1ED1 \\U+0111\\U+1ECBnh theo b\\U+1EA3n v\\U+1EBD thi\\U+1EBFt k\\U+1EBF. T\\U+01B0\\U+1EDDng hi\\U+1EC7n tr\\U+1EA1ng l\\U+1EC7ch / kh\\U+00F4ng vu\\U+00F4ng: \\U+0111o laser t\\U+1EA1i c\\U+00F4ng tr\\U+01B0\\U+1EDDng tr\\U+01B0\\U+1EDBc khi c\\U+1EAFt \\U+0111\\U+00E1."
          "2. Ron ho\\U+1EB7c khe l\\U+1EDBn h\\U+01A1n 8 mm (khe co gi\\U+00E3n, ron h\\U+1ED3 b\\U+01A1i) c\\U+00F3 th\\U+1EC3 b\\U+1ECB nh\\U+1EADn nh\\U+1EA7m l\\U+00E0 c\\U+1EA1nh bi\\U+00EAn v\\U+00E0 c\\U+1ED9ng d\\U+01B0 th\\U+1EEBa."
          (strcat "3. C\\U+1EA1nh s\\U+00E1t t\\U+01B0\\U+1EDDng x\\U+00E9t theo \\U+0111i\\U+1EC3m gi\\U+1EEFa c\\U+1EA1nh: c\\U+1EA1nh ch\\U+1EC9 s\\U+00E1t m\\U+1ED9t ph\\U+1EA7n v\\U+1EABn c\\U+1ED9ng d\\U+01B0 c\\U+1EA3 c\\U+1EA1nh; t\\U+01B0\\U+1EDDng v\\U+1EBD l\\U+1EC7ch qu\\U+00E1 " (sd:num kc) " mm so v\\U+1EDBi c\\U+1EA1nh vi\\U+00EAn b\\U+1ECB b\\U+1ECF s\\U+00F3t.")
          "4. S\\U+00E0n d\\U+1ED1c: k\\U+00EDch th\\U+01B0\\U+1EDBc l\\U+00E0 h\\U+00ECnh chi\\U+1EBFu b\\U+1EB1ng, ch\\U+01B0a nh\\U+00E2n chi\\U+1EC1u d\\U+00E0i th\\U+1EADt (tham kh\\U+1EA3o: d\\U+1ED1c 1:7 d\\U+00E0i th\\U+00EAm ~8 mm tr\\U+00EAn 1200, d\\U+1ED1c 1:3 ~65 mm)."
          "5. M\\U+1EB7t \\U+0111\\U+1EE9ng (\\U+1ED1p th\\U+00E0nh h\\U+1ED3, ch\\U+00E2n ng\\U+01B0\\U+1EE1ng) n\\U+1EB1m ngo\\U+00E0i l\\U+1EC7nh: t\\U+00EDnh ri\\U+00EAng."
          "6. KT c\\U+1EAFt \\U+0111\\U+00E3 c\\U+1ED9ng d\\U+01B0 ch\\U+01B0a so v\\U+1EDBi kh\\U+1ED5 t\\U+1EA5m \\U+0111\\U+00E1 th\\U+1EADt: ki\\U+1EC3m tra tr\\U+01B0\\U+1EDBc khi x\\U+1EBFp t\\U+1EA5m."
          "7. Vi\\U+00EAn s\\U+00E1t hai t\\U+01B0\\U+1EDDng c\\U+1ED9ng c\\U+1EA3 hai d\\U+01B0; vi\\U+00EAn kh\\U+00F4ng ch\\U+1EEF nh\\U+1EADt t\\U+00EDnh theo khung bao: ki\\U+1EC3m tra b\\U+1EB1ng tay."
          (if (> nxt 0) (strcat "8. C\\U+00F3 " (itoa nxt) " c\\U+1EA1nh xi\\U+00EAn: k\\U+00EDch th\\U+01B0\\U+1EDBc c\\U+1EAFt trong b\\U+1EA3ng CH\\U+01AFA c\\U+1ED9ng d\\U+01B0 c\\U+1EE7a c\\U+00E1c c\\U+1EA1nh n\\U+00E0y.") "8. C\\U+1EA1nh xi\\U+00EAn (n\\U+1EBFu c\\U+00F3): k\\U+00EDch th\\U+01B0\\U+1EDBc c\\U+1EAFt ch\\U+01B0a c\\U+1ED9ng d\\U+01B0.")
          "9. N\\U+00E9t SD-CAODO-BAC-mm l\\U+00E0 b\\U+1EA3n sao: s\\U+1EEDa n\\U+00E9t g\\U+1ED1c ph\\U+1EA3i ch\\U+1EA1y l\\U+1EA1i SDBACCAODO, x\\U+00F3a layer c\\U+0169 tr\\U+01B0\\U+1EDBc khi copy l\\U+1EA1i."))
  (sd:text pt "GHI CH\\U+00DA R\\U+1EE6I RO KHI C\\U+1EAET D\\U+01AF (SDCATDU) - \\U+0111\\U+1ED1i chi\\U+1EBFu hi\\U+1EC7n tr\\U+1EA1ng tr\\U+01B0\\U+1EDBc khi c\\U+1EAFt" (* 3.5 sc) "L" lay)
  (foreach l notes
    (setq n (1+ n))
    (sd:text (sd:p+ (sd:2d pt) 0 (- (* n 5.0 sc))) l h "L" lay))
  (princ (strcat "\n[SD] \\U+0110\\U+00E3 ghi " (itoa (1+ (length notes))) " d\\U+00F2ng ghi ch\\U+00FA r\\U+1EE7i ro l\\U+00EAn layer SD-CATDU-GHICHU.")))

(defun sd:cd-box-hit (a b g)
  (and (<= (- (car a) g) (caddr b)) (>= (+ (caddr a) g) (car b)) (<= (- (cadr a) g) (cadddr b)) (>= (+ (cadddr a) g) (cadr b))))
(defun sd:cd-box-add (a b)
  (list (min (car a) (car b)) (min (cadr a) (cadr b)) (max (caddr a) (caddr b)) (max (cadddr a) (cadddr b))))
;; gop cac hop (bbox) cham / sat nhau (khoang g) thanh cum
(defun sd:cd-cluster (boxes g / done r b hit rest)
  (setq r boxes done nil)
  (while (not done)
    (setq done t rest nil)
    (foreach b r
      (setq hit (vl-some '(lambda (x) (if (sd:cd-box-hit b x g) x)) rest))
      (if hit
        (setq rest (cons (sd:cd-box-add b hit) (vl-remove hit rest)) done nil)
        (setq rest (cons b rest))))
    (setq r rest))
  r)
;; Dam may (revision cloud) quanh hop bbox, cung ra ngoai; chord = do dai day cung mm
(defun sd:cd-cloud (bx m chord lay / x0 y0 x1 y1 pts n k a b len)
  (setq x0 (- (car bx) m) y0 (- (cadr bx) m) x1 (+ (caddr bx) m) y1 (+ (cadddr bx) m))
  (foreach seg (list (list (list x0 y0) (list x1 y0)) (list (list x1 y0) (list x1 y1)) (list (list x1 y1) (list x0 y1)) (list (list x0 y1) (list x0 y0)))
    (setq a (car seg) b (cadr seg) len (distance a b) n (max 1 (fix (+ 0.5 (/ len chord)))) k 0)
    (repeat n
      (setq pts (cons (list (+ (car a) (* (/ k (float n)) (- (car b) (car a)))) (+ (cadr a) (* (/ k (float n)) (- (cadr b) (cadr a))))) pts) k (1+ k))))
  (setq pts (reverse pts))
  (entmake (append (list '(0 . "LWPOLYLINE") '(100 . "AcDbEntity") (cons 8 lay) '(100 . "AcDbPolyline") (cons 90 (length pts)) '(70 . 1))
                   (apply 'append (mapcar '(lambda (p) (list (list 10 (car p) (cadr p)) (cons 42 0.6))) pts)))))

(defun c:SDCATDU (/ ss i e xd pts recs du mk rows key lay rc fr ang eds nl ns nx w h w2 h2 rel ed ea r trows lines pt fn f nvien lastmat ht mx my ux uy ul sc desc tuong kc rules nfree plines fn2 f2 ss2 nb eds2 mm ru kv lyr wl tk md dl ds mc cl ncdo mcl mayk bx nxt)
  (sd:begin)
  (if (setq ss (sd:select-tiles "\nCh\\U+1ECDn c\\U+00E1c vi\\U+00EAn (Enter = t\\U+1EA5t c\\U+1EA3 trong b\\U+1EA3n v\\U+1EBD): "))
    (if (sd:dlg "C\\U+1EAFt d\\U+01B0 s\\U+00E1t t\\U+01B0\\U+1EDDng (SDCATDU)"
                (list (list "du" "Ch\\U+1EEBa d\\U+01B0 m\\U+1EB7c \\U+0111\\U+1ECBnh m\\U+1ED7i c\\U+1EA1nh (mm; d\\U+00F9ng khi quy t\\U+1EAFc b\\U+00EAn d\\U+01B0\\U+1EDBi kh\\U+00F4ng ghi mm)" 'real (sd:cfg "CD-DU" 10.0))
                      (list "tuong" "Quy t\\U+1EAFc theo layer: layer=mm c\\U+00E1ch nhau d\\U+1EA5u ; (VD *MUIBAC*=20;*THANHHO*=15;*TUONG*=10). Ch\\U+1EC9 c\\U+1EA1nh s\\U+00E1t c\\U+00E1c n\\U+00E9t \\U+0111\\U+00F3 m\\U+1EDBi ch\\U+1EEBa d\\U+01B0. Tr\\U+1ED1ng = m\\U+1ECDi c\\U+1EA1nh bi\\U+00EAn \\U+0111\\U+1EC1u ch\\U+1EEBa d\\U+01B0" 'str (sd:cfg "CD-TUONG" ""))
                      (list "kc" "C\\U+1EA1nh coi l\\U+00E0 s\\U+00E1t khi c\\U+00E1ch n\\U+00E9t c\\U+1EE7a quy t\\U+1EAFc kh\\U+00F4ng qu\\U+00E1 (mm)" 'real0 (sd:cfg "CD-KC" 30.0))
                      (list "cdo" "T\\U+1EF1 nh\\U+1EADn c\\U+00E1c n\\U+00E9t \\U+0111\\U+1ED5i cao \\U+0111\\U+1ED9 (layer SD-CAODO-BAC-mm do SDBACCAODO t\\U+1EA1o): c\\U+1EA1nh s\\U+00E1t n\\U+00E9t \\U+0111\\U+00F3 ch\\U+1EEBa d\\U+01B0 theo s\\U+1ED1 mm c\\U+1EE7a layer" 'tog t)
                      (list "may" "Khoanh \\U+0111\\U+00E1m m\\U+00E2y quanh khu v\\U+1EF1c c\\U+00F3 ch\\U+1EEBa d\\U+01B0 (layer SD-CATDU-MAY)" 'kw (sd:cfg "CD-MAY" "Cum") '(("Cum" . "Theo c\\U+1EE5m vi\\U+00EAn li\\U+1EC1n k\\U+1EC1") ("Tung" . "T\\U+1EEBng vi\\U+00EAn") ("Khong" . "Kh\\U+00F4ng khoanh")))
                      (list "mk" "V\\U+1EBD g\\U+1EA1ch \\U+0111\\U+1ECF v\\U+00E0 ghi +d\\U+01B0 tr\\U+00EAn t\\U+1EEBng c\\U+1EA1nh (layer SD-CATDU)" 'tog t)))
      (progn
        (setq du (sd:cfg-put "CD-DU" (sd:v "du")) mk (sd:v "mk") mayk (sd:cfg-put "CD-MAY" (cond ((sd:v "may")) ("Cum"))) sc (sd:sc) i 0 nfree 0 ncdo 0 nxt 0
              tuong (vl-string-trim " " (cond ((sd:cfg-put "CD-TUONG" (cond ((sd:v "tuong")) (""))))))
              kc (sd:cfg-put "CD-KC" (cond ((sd:v "kc")) (30.0))))
        ;; quy tac: layer=mm; moi quy tac = (layer mm danh-sach-ename)
        (foreach tk (sd:split tuong ";")
          (setq tk (vl-string-trim " " tk))
          (if (/= tk "")
            (progn
              (setq kv (sd:split tk "=") lyr (vl-string-trim " " (car kv)) mm (if (and (cadr kv) (> (atof (cadr kv)) 0.0)) (atof (cadr kv)) du) wl nil)
              (if (setq ss2 (ssget "_X" (list '(0 . "LINE,LWPOLYLINE,POLYLINE,ARC,CIRCLE,SPLINE") (cons 8 lyr))))
                (progn
                  (setq i 0)
                  (repeat (sslength ss2) (setq wl (cons (ssname ss2 i) wl) i (1+ i)))
                  (setq rules (cons (list lyr mm wl) rules)))
                (princ (strcat "\n[SD] Kh\\U+00F4ng th\\U+1EA5y n\\U+00E9t n\\U+00E0o tr\\U+00EAn layer " lyr ": b\\U+1ECF quy t\\U+1EAFc n\\U+00E0y."))))))
        (setq rules (reverse rules))
        ;; nut doi cao do: layer SD-CAODO-BAC-<mm>, uu tien hon quy tac tay
        (if (sd:v "cdo")
          (foreach cl (sd:cd-bac-layers)
            (if (setq ss2 (ssget "_X" (list '(0 . "LINE,LWPOLYLINE,POLYLINE,ARC") (cons 8 (car cl)))))
              (progn (setq wl nil i 0)
                     (repeat (sslength ss2) (setq wl (cons (ssname ss2 i) wl) i (1+ i)))
                     (setq rules (cons (list (car cl) (cdr cl) wl) rules) ncdo (1+ ncdo))))))
        (setq i 0)
        (repeat (sslength ss)
          (setq e (ssname ss i) i (1+ i) xd (mapcar 'cdr (cdadr (assoc -3 (entget e '("SD_TILE"))))))
          (if (and (>= (length xd) 12) (/= (nth 1 xd) "X"))
            (progn (setq pts (sd:curve-pts e))
                   (if (>= (length pts) 3) (setq recs (cons (list e (sd:cd-bbox pts) pts xd) recs))))))
        (sd:ho-warn '("CD-DU"))
        (setq lay (sd:make-layer "SD-CATDU" 1 "Continuous" 18) nvien 0)
        (sd:cd-clear lay)
        (sd:cd-clear "SD-CATDU-MAY")
        (foreach rc recs
          (setq xd (nth 3 rc) pts (nth 2 rc))
          (if (/= (nth 1 xd) "F")
            (progn
              (setq eds (sd:cd-edges pts (car rc) recs 8.0))
              ;; moi canh bien nhan them mm chua du (phan tu thu 6): theo quy tac dau tien co net trong khoang kc; khong quy tac nao khop = canh tu do, khong chua du
              (if (or (/= tuong "") rules)
                (progn
                  (setq nb (length eds) eds2 nil)
                  (foreach ed eds
                    (setq mm nil md (list (/ (+ (car (car ed)) (car (cadr ed))) 2.0) (/ (+ (cadr (car ed)) (cadr (cadr ed))) 2.0)))
                    (foreach ru rules (if (and (sd:cd-near md (nth 2 ru) kc) (or (null mm) (> (cadr ru) mm))) (setq mm (cadr ru))))
                    (if (and (null mm) (= tuong "")) (setq mm du))
                    (if mm (setq eds2 (cons (append ed (list mm)) eds2))))
                  (setq eds (reverse eds2) nfree (+ nfree (- nb (length eds)))))
                (setq eds (mapcar '(lambda (ed) (append ed (list du))) eds)))
              (if eds
                (progn
                  (setq fr (sd:tile-frame pts) ang (car fr) w (cadr fr) h (caddr fr) nl 0 ns 0 nx 0 dl 0.0 ds 0.0 ht (sd:tile-th w h sc))
                  (foreach ed eds
                    (setq rel (abs (rem (- (cadddr ed) ang) pi)))
                    (cond ((or (< rel 0.06) (> rel (- pi 0.06))) (setq nl (1+ nl) dl (+ dl (nth 5 ed))))
                          ((< (abs (- rel (/ pi 2.0))) 0.06) (setq ns (1+ ns) ds (+ ds (nth 5 ed))))
                          (t (setq nx (1+ nx))))
                    (if mk
                      (progn
                        (sd:line (car ed) (cadr ed) lay)
                        (setq mx (/ (+ (car (car ed)) (car (cadr ed))) 2.0) my (/ (+ (cadr (car ed)) (cadr (cadr ed))) 2.0)
                              ux (- mx (car (nth 4 ed))) uy (- my (cadr (nth 4 ed))) ul (max 1e-6 (sqrt (+ (* ux ux) (* uy uy)))))
                        (sd:text (list (+ mx (* 1.2 ht (/ ux ul))) (+ my (* 1.2 ht (/ uy ul)))) (strcat "+" (sd:num (nth 5 ed))) ht "MC" lay))))
                  (setq nxt (+ nxt nx))
                  (setq mc (cond ((sd:mv-get (car rc))) ((nth 2 xd))))
                  (setq mcl (cons (sd:cd-bbox pts) mcl))
                  (setq nvien (1+ nvien) w2 (+ w ds) h2 (+ h dl)
                        plines (cons (sd:join (list (nth 0 xd) mc (sd:rtos (car (cadddr fr)) 0) (sd:rtos (cadr (cadddr fr)) 0)
                                                    (sd:rtos w 0) (sd:rtos h 0) (itoa nl) (itoa ns) (itoa nx) (sd:rtos dl 0) (sd:rtos ds 0) (sd:rtos w2 0) (sd:rtos h2 0)) ";")
                                     plines)
                        key (strcat (nth 0 xd) "|" mc "|" (sd:rtos w2 0) "|" (sd:rtos h2 0) "|" (itoa nl) (itoa ns) (itoa nx)))
                  (if (setq r (assoc key rows))
                    (setq rows (subst (list key (nth 1 r) (nth 2 r) (nth 3 r) (nth 4 r) (nth 5 r) (nth 6 r) (nth 7 r) (nth 8 r) (nth 9 r) (1+ (nth 10 r)) (nth 11 r) (nth 12 r)) r rows))
                    (setq rows (cons (list key (nth 0 xd) mc w h nl ns nx w2 h2 1 dl ds) rows))))))))
        (if (and mcl (/= mayk "Khong"))
          (progn
            (sd:make-layer "SD-CATDU-MAY" 1 "Continuous" 25)
            (foreach bx (if (= mayk "Cum") (sd:cd-cluster mcl 60.0) mcl)
              (sd:cd-cloud bx (* 4.0 sc) (* 8.0 sc) "SD-CATDU-MAY"))
            (princ (strcat "\n[SD] \\U+0110\\U+00E3 khoanh \\U+0111\\U+00E1m m\\U+00E2y " (if (= mayk "Cum") "theo c\\U+1EE5m" "t\\U+1EEBng vi\\U+00EAn") " tr\\U+00EAn layer SD-CATDU-MAY."))))
        (if (null rows)
          (princ "\n[SD] Kh\\U+00F4ng c\\U+00F3 vi\\U+00EAn c\\U+1EAFt n\\U+00E0o c\\U+00F3 c\\U+1EA1nh s\\U+00E1t t\\U+01B0\\U+1EDDng / v\\U+1EADt c\\U+1EA3n.")
          (progn
            (setq rows (sd:sort rows '(lambda (a b) (< (car a) (car b)))) lastmat nil)
            (foreach r rows
              (if (/= (nth 1 r) lastmat)
                (setq trows (cons (list "W" (strcat "V\\U+1EADt li\\U+1EC7u " (nth 1 r))) trows) lastmat (nth 1 r)))
              (setq desc (sd:join (vl-remove nil (list (if (> (nth 5 r) 0) (strcat (itoa (nth 5 r)) " c\\U+1EA1nh d\\U+00E0i (+" (sd:num (nth 11 r)) ")"))
                                                       (if (> (nth 6 r) 0) (strcat (itoa (nth 6 r)) " c\\U+1EA1nh ng\\U+1EAFn (+" (sd:num (nth 12 r)) ")"))
                                                       (if (> (nth 7 r) 0) (strcat (itoa (nth 7 r)) " c\\U+1EA1nh xi\\U+00EAn*")))) ", "))
              (setq trows (cons (list "R" (list (nth 2 r) (strcat (sd:rtos (nth 3 r) 0) "\\U+00D7" (sd:rtos (nth 4 r) 0)) desc
                                                (strcat (sd:rtos (nth 8 r) 0) "\\U+00D7" (sd:rtos (nth 9 r) 0)) (itoa (nth 10 r)))
                                      nil)
                                trows)
                    lines (cons (sd:join (list (nth 1 r) (nth 2 r) (sd:rtos (nth 3 r) 0) (sd:rtos (nth 4 r) 0) (itoa (nth 5 r)) (itoa (nth 6 r)) (itoa (nth 7 r)) (sd:rtos (nth 11 r) 0) (sd:rtos (nth 12 r) 0)
                                               (sd:rtos (nth 8 r) 0) (sd:rtos (nth 9 r) 0) (itoa (nth 10 r))) ";")
                                lines)))
            (setq trows (reverse trows))
            (if (> nxt 0) (princ (strcat "\n[!] " (itoa nxt) " c\\U+1EA1nh xi\\U+00EAn c\\U+00F3 v\\U+1EBD d\\U+01B0 nh\\U+01B0ng KT c\\U+1EAFt trong b\\U+1EA3ng ch\\U+01B0a c\\U+1ED9ng d\\U+01B0 c\\U+1EE7a c\\U+00E1c c\\U+1EA1nh n\\U+00E0y: t\\U+1EF1 ki\\U+1EC3m l\\U+1EA1i b\\U+1EB1ng tay.")))
            (if (> ncdo 0) (princ (strcat "\n[SD] \\U+0110\\U+00E3 nh\\U+1EADn " (itoa ncdo) " layer \\U+0111\\U+1ED5i cao \\U+0111\\U+1ED9 SD-CAODO-BAC-mm.")))
            (princ (strcat "\n[SD] " (itoa nvien) " vi\\U+00EAn c\\U+1EAFt c\\U+00F3 c\\U+1EA1nh ch\\U+1EEBa d\\U+01B0 (g\\U+1EA1ch \\U+0111\\U+1ECF + s\\U+1ED1 mm tr\\U+00EAn layer SD-CATDU)."
                           (if (> nfree 0) (strcat " " (itoa nfree) " c\\U+1EA1nh bi\\U+00EAn kh\\U+00F4ng s\\U+00E1t n\\U+00E9t n\\U+00E0o c\\U+1EE7a quy t\\U+1EAFc (m\\U+00E9p h\\U+1EDF, c\\U+1EEDa...) kh\\U+00F4ng ch\\U+1EEBa d\\U+01B0.") "")))
            (if (setq pt (sd:getpt "\n\\U+0110i\\U+1EC3m ch\\U+00E8n b\\U+1EA3ng (g\\U+00F3c tr\\U+00E1i tr\\U+00EAn) <b\\U+1ECF qua>: " nil))
              (sd:table2 pt "B\\U+1EA2NG C\\U+1EAET D\\U+01AF (KT C\\U+1EAET \\U+0110\\U+00C3 C\\U+1ED8NG D\\U+01AF)"
                         '(("M\\U+00C3 VI\\U+00CAN" 24) ("KT THI\\U+1EBET K\\U+1EBE (mm)" 32) ("C\\U+1EA0NH CH\\U+1EEAA D\\U+01AF" 38) ("KT C\\U+1EAET (mm)" 30) ("SL" 12))
                         trows -1 sc))
            (if (setq pt (sd:getpt "\n\\U+0110i\\U+1EC3m ch\\U+00E8n ghi ch\\U+00FA r\\U+1EE7i ro c\\U+1EAFt d\\U+01B0 (g\\U+00F3c tr\\U+00E1i tr\\U+00EAn) <b\\U+1ECF qua>: " nil))
              (sd:cd-notes pt du kc nxt ncdo sc))
            (setq fn (sd:csv-name "_CatDu.csv"))
            (if (setq f (sd:open fn "w"))
              (progn
                (write-line "Ma VL;Ma vien;Rong TK;Cao TK;Canh dai;Canh ngan;Canh xien;Du canh dai;Du canh ngan;Rong cat;Cao cat;SL" f)
                (foreach l (reverse lines) (write-line l f))
                (setq fn (sd:close f))
                (princ (strcat "\n[SD] \\U+0110\\U+00E3 xu\\U+1EA5t: " fn))))
            ;; danh sach tung vien (toa do tam de tim lai tren ban ve / lam tem)
            (setq fn2 (sd:csv-name "_CatDuTungVien.csv"))
            (if (setq f2 (sd:open fn2 "w"))
              (progn
                (write-line "Ma VL;Ma vien;X tam;Y tam;Rong TK;Cao TK;Canh dai;Canh ngan;Canh xien;Du canh dai;Du canh ngan;Rong cat;Cao cat" f2)
                (foreach l (reverse plines) (write-line l f2))
                (setq fn2 (sd:close f2))
                (princ (strcat "\n[SD] \\U+0110\\U+00E3 xu\\U+1EA5t: " fn2)))))))))
  (sd:finish))

;;; --------------------------------------------------------------------------
;;;  SDDUTOAN - Du toan tien theo don gia m2: moi ma vat lieu mot don gia (nho lai lan sau), dien tich tinh tu polyline vien
;;; --------------------------------------------------------------------------
(defun sd:money (x / s c)
  (setq x (+ x 0.5) s "")
  (while (>= x 1000.0)
    (setq c (fix (rem x 1000.0)) x (/ (- x (rem x 1000.0)) 1000.0)
          s (strcat "." (if (< c 100) "0" "") (if (< c 10) "0" "") (itoa c) s)))
  (strcat (itoa (fix x)) s))

(defun c:SDDUTOAN (/ ss i e xd pts recs mats ar prices fields k mat hao cong vat gia am tong tien trows lines pt fn f tda tcong sub tvat)
  (sd:begin)
  (if (setq ss (sd:select-tiles "\nCh\\U+1ECDn c\\U+00E1c vi\\U+00EAn c\\U+1EE7a ph\\U+01B0\\U+01A1ng \\U+00E1n c\\U+1EA7n d\\U+1EF1 to\\U+00E1n <Enter = t\\U+1EA5t c\\U+1EA3 trong b\\U+1EA3n v\\U+1EBD>: "))
    (progn
      (setq i 0)
      (repeat (sslength ss)
        (setq e (ssname ss i) i (1+ i) xd (mapcar 'cdr (cdadr (assoc -3 (entget e '("SD_TILE"))))))
        (if (and (>= (length xd) 12) (/= (nth 1 xd) "X") (>= (length (setq pts (sd:curve-pts e))) 3))
          (if (setq am (assoc (nth 0 xd) ar))
            (setq ar (subst (cons (car am) (+ (cdr am) (/ (sd:cd-area pts) 1e6))) am ar))
            (setq ar (cons (cons (nth 0 xd) (/ (sd:cd-area pts) 1e6)) ar)))))
      (setq ar (vl-sort ar '(lambda (a b) (< (car a) (car b)))) prices (sd:cfg "DT-GIA" nil) k 0)
      (if (null ar)
        (princ "\n[SD] Kh\\U+00F4ng c\\U+00F3 vi\\U+00EAn n\\U+00E0o \\U+0111\\U+1EC3 d\\U+1EF1 to\\U+00E1n.")
        (progn
          (foreach m ar
            (setq fields (cons (list (strcat "g" (itoa k)) (strcat "\\U+0110\\U+01A1n gi\\U+00E1 " (car m) " (\\U+0111\\U+1ED3ng/m\\U+00B2) - di\\U+1EC7n t\\U+00EDch " (sd:rtos (cdr m) 2) " m\\U+00B2") 'real0
                                     (cond ((cdr (assoc (car m) prices))) (0.0)))
                               fields)
                  k (1+ k)))
          (setq fields (append (reverse fields)
                               (list (list "hao" "Hao h\\U+1EE5t khi mua (%)" 'real0 (sd:cfg "DT-HAO" 5.0))
                                     (list "cong" "\\U+0110\\U+01A1n gi\\U+00E1 c\\U+00F4ng l\\U+00E1t / \\U+1ED1p (\\U+0111\\U+1ED3ng/m\\U+00B2, 0 = kh\\U+00F4ng t\\U+00EDnh)" 'real0 (sd:cfg "DT-CONG" 0.0))
                                     (list "vat" "VAT (%, 0 = ch\\U+01B0a VAT)" 'real0 (sd:cfg "DT-VAT" 0.0)))))
          (if (sd:dlg "D\\U+1EF1 to\\U+00E1n ti\\U+1EC1n theo \\U+0111\\U+01A1n gi\\U+00E1 m\\U+00B2 (SDDUTOAN)" fields)
            (progn
              (setq hao (sd:cfg-put "DT-HAO" (sd:v "hao")) cong (sd:cfg-put "DT-CONG" (sd:v "cong")) vat (sd:cfg-put "DT-VAT" (sd:v "vat"))
                    k 0 tda 0.0 tcong 0.0 prices nil)
              (foreach m ar
                (setq gia (sd:v (strcat "g" (itoa k))) k (1+ k)
                      prices (cons (cons (car m) gia) prices)
                      mat (* (cdr m) (+ 1.0 (/ hao 100.0)))
                      tien (* mat gia) tda (+ tda tien) tcong (+ tcong (* (cdr m) cong))
                      trows (cons (list "R" (list (car m) (sd:rtos (cdr m) 2) (sd:rtos mat 2) (sd:money gia) (sd:money tien)) nil) trows)
                      lines (cons (sd:join (list (car m) (sd:rtos (cdr m) 3) (sd:rtos mat 3) (sd:rtos gia 0) (sd:rtos tien 0)) ";") lines)))
              (sd:cfg-put "DT-GIA" prices)
              (setq sub (+ tda tcong) tvat (* sub (/ vat 100.0)) tong (+ sub tvat) trows (reverse trows))
              (setq trows (append trows
                                  (list (list "S" "C\\U+1ED9ng ti\\U+1EC1n \\U+0111\\U+00E1" (sd:money tda)))
                                  (if (> cong 0.0) (list (list "S" "C\\U+00F4ng l\\U+00E1t / \\U+1ED1p" (sd:money tcong))))
                                  (if (> vat 0.0) (list (list "S" (strcat "VAT " (sd:num vat) "%") (sd:money tvat))))
                                  (list (list "S" "T\\U+1ED4NG C\\U+1ED8NG (\\U+0111\\U+1ED3ng)" (sd:money tong)))))
              (princ (strcat "\n[SD] D\\U+1EF1 to\\U+00E1n: " (sd:money tong) " \\U+0111\\U+1ED3ng (\\U+0111\\U+00E1 " (sd:money tda) (if (> cong 0.0) (strcat ", c\\U+00F4ng " (sd:money tcong)) "") (if (> vat 0.0) (strcat ", VAT " (sd:money tvat)) "") ")."))
              (if (setq pt (sd:getpt "\n\\U+0110i\\U+1EC3m ch\\U+00E8n b\\U+1EA3ng (g\\U+00F3c tr\\U+00E1i tr\\U+00EAn) <b\\U+1ECF qua>: " nil))
                (sd:table2 pt "D\\U+1EF0 TO\\U+00C1N TI\\U+1EC0N \\U+0110\\U+00C1"
                           '(("V\\U+1EACT LI\\U+1EC6U" 30) ("DT L\\U+00C1T (m\\U+00B2)" 24) ("DT MUA (m\\U+00B2)" 24) ("\\U+0110\\U+01A0N GI\\U+00C1 (\\U+0111/m\\U+00B2)" 30) ("TH\\U+00C0NH TI\\U+1EC0N (\\U+0111)" 36))
                           trows -1 (sd:sc)))
              (setq fn (sd:csv-name "_DuToan.csv"))
              (if (setq f (sd:open fn "w"))
                (progn
                  (write-line "Ma VL;DT lat (m2);DT mua (m2);Don gia (d/m2);Thanh tien (d)" f)
                  (foreach l (reverse lines) (write-line l f))
                  (write-line (strcat "Cong tien da;;;;" (sd:rtos tda 0)) f)
                  (write-line (strcat "Cong lat;;;;" (sd:rtos tcong 0)) f)
                  (write-line (strcat "VAT;;;;" (sd:rtos tvat 0)) f)
                  (write-line (strcat "Tong cong;;;;" (sd:rtos tong 0)) f)
                  (setq fn (sd:close f))
                  (princ (strcat "\n[SD] \\U+0110\\U+00E3 xu\\U+1EA5t: " fn))))))))))
  (sd:finish))

;;; --------------------------------------------------------------------------
;;;  SDKHAOSAT - Dung phong tu so do khao sat hien trang (file CSV cua tool khao-sat-hien-trang / may do laser):
;;;  room,ab,bc,cd,da,ac,bd,height,openings_m2,source,date,note  (4 canh lien nhau + duong cheo AC dung hinh, BD de kiem tra khep)
;;;  Hang tin cay: A du 4 canh + 2 cheo va cheo khep; B 1 cheo (AC); C khong cheo (gia dinh goc B vuong); X cheo BD lech qua nguong; D thieu canh / khong khep.
;;; --------------------------------------------------------------------------
(defun sd:ks-side (a c p) (- (* (- (car c) (car a)) (- (cadr p) (cadr a))) (* (- (cadr c) (cadr a)) (- (car p) (car a)))))

;; Dung tu giac tu 4 canh + cheo AC (A goc toa do, B tren truc x). Tra ve (4-dinh gia-dinh-vuong) hoac chuoi loi
(defun sd:ks-build (ab bc cd da ac / a0 bb cc asm x y2 dx dy d aa h2 h xm ym c1 c2 dd)
  (setq a0 (list 0.0 0.0) bb (list ab 0.0))
  (if (and ac (> ac 0.0))
    (progn (setq x (/ (- (+ (* ab ab) (* ac ac)) (* bc bc)) (* 2.0 ab)) y2 (- (* ac ac) (* x x)))
           (if (>= y2 0.0) (setq cc (list x (sqrt y2)))))
    (setq cc (list ab bc) asm t))
  (if (null cc)
    "AB, BC, AC khong tao duoc tam giac"
    (progn
      (setq dx (car cc) dy (cadr cc) d (sqrt (+ (* dx dx) (* dy dy)))
            aa (/ (+ (- (* da da) (* cd cd)) (* d d)) (* 2.0 d)) h2 (- (* da da) (* aa aa)))
      (if (< h2 0.0) (setq h2 (if (<= (sqrt (- h2)) 30.0) 0.0)))
      (if (null h2)
        "so do khong khep duoc (kiem tra lai canh / duong cheo)"
        (progn
          (setq h (sqrt h2) xm (/ (* aa dx) d) ym (/ (* aa dy) d)
                c1 (list (+ xm (/ (* h dy) d)) (- ym (/ (* h dx) d)))
                c2 (list (- xm (/ (* h dy) d)) (+ ym (/ (* h dx) d)))
                dd (if (< (* (sd:ks-side a0 cc c1) (sd:ks-side a0 cc bb)) 0.0) c1 c2))
          (list (list a0 bb cc dd) asm))))))

;; v = (ab bc cd da ac bd) mm (nil = khong do). Tra ve (hang ghi-chu 4-dinh dien-tich-mm2)
(defun sd:ks-grade (v tol / r pts asm bd dev notes)
  (cond
    ((vl-some '(lambda (x) (or (null x) (<= x 0.0))) (list (nth 0 v) (nth 1 v) (nth 2 v) (nth 3 v)))
     (list "D" (list "thieu canh (can du 4 canh AB BC CD DA)") nil 0.0))
    (t
     (if (< (max (nth 0 v) (nth 1 v) (nth 2 v) (nth 3 v)) 100.0) (setq notes (list "moi canh < 100 mm: co the so do dang la met (chon don vi m)")))
     (setq r (sd:ks-build (nth 0 v) (nth 1 v) (nth 2 v) (nth 3 v) (nth 4 v)))
     (if (= (type r) 'STR)
       (list "D" (cons r notes) nil 0.0)
       (progn
         (setq pts (car r) asm (cadr r) bd (nth 5 v))
         (cond
           (asm (list "C" (cons "chua do cheo AC: gia dinh goc B vuong" notes) pts (sd:cd-area pts)))
           ((and bd (> bd 0.0))
            (setq dev (- (distance (nth 1 pts) (nth 3 pts)) bd))
            (if (> (abs dev) tol)
              (list "X" (cons (strcat "cheo BD tinh " (sd:rtos (distance (nth 1 pts) (nth 3 pts)) 0) " khac do " (sd:rtos bd 0) " (" (sd:rtos dev 0) " mm): do lai") notes) pts (sd:cd-area pts))
              (list "A" notes pts (sd:cd-area pts))))
           (t (list "B" (cons "bo sung cheo BD de kiem tra khep goc" notes) pts (sd:cd-area pts)))))))))

(defun sd:ks-num (s) (if (and s (/= (vl-string-trim " " s) "")) (atof (vl-string-translate "," "." s))))

;; Doc CSV so do: ((ten (ab bc cd da ac bd) ghichu) ...) don vi mm theo he so k
(defun sd:ks-read (fn k / f ln sep cells hdr idx rows col nm v n)
  (if (setq f (sd:open fn "r"))
    (progn
      (setq n 0)
      (while (setq ln (read-line f))
        (setq n (1+ n) ln (vl-string-trim " \t\r" ln))
        (if (and (= n 1) (>= (strlen ln) 3) (= (ascii ln) 239)) (setq ln (substr ln 4)))
        (if (/= ln "")
          (progn
            (if (null sep) (setq sep (cond ((vl-string-search ";" ln) ";") ((vl-string-search "\t" ln) "\t") (","))))
            (setq cells (sd:csv-split ln sep))
            (cond
              ((null hdr)
               (if (= (strcase (car cells)) "ROOM")
                 (setq hdr (mapcar 'strcase cells))
                 (princ "\n[SD] Dong tieu de phai bat dau bang room (room,ab,bc,cd,da,ac,bd,...).")))
              (t
               (setq nm (car cells))
               (if (and (/= nm "") (/= (strcase (substr nm 1 5)) "VI_DU"))
                 (progn
                   (setq v nil)
                   (foreach col '("AB" "BC" "CD" "DA" "AC" "BD")
                     (setq idx (vl-position col hdr)
                           v (cons (if (and idx (< idx (length cells)) (sd:ks-num (nth idx cells))) (* k (sd:ks-num (nth idx cells)))) v)))
                   (setq idx (vl-position "NOTE" hdr)
                         rows (cons (list nm (reverse v) (if (and idx (< idx (length cells))) (nth idx cells) "")) rows)))))))))
      (sd:close f)
      (reverse rows))))

(defun c:SDKHAOSAT (/ fn unit k tol dung gap rows lay x0 y0 x y rowh n cnt tot r g gr drew pts bb w h dx dy ctr sc lines nm pt)
  (sd:begin)
  (if (setq fn (getfiled "Chon file so do khao sat (.csv: room,ab,bc,cd,da,ac,bd,...)" "" "csv" 4))
    (if (sd:dlg "Dung phong tu so do khao sat (SDKHAOSAT)"
                (list (list "unit" "Don vi so do trong file" 'kw (sd:cfg "KS-UNIT" "mm") '(("mm" . "mm") ("cm" . "cm") ("m" . "met")))
                      (list "tol" "Nguong lech cheo BD / canh (mm)" 'real (sd:cfg "KS-TOL" 10.0))
                      (list "dung" "Dung cac phong hang" 'kw (sd:cfg "KS-DUNG" "AB")
                            '(("A" . "Chi hang A (du 4 canh + 2 cheo, khep) - dung cho shop drawing") ("AB" . "A va B (co cheo AC)") ("ABC" . "A, B, C (C gia dinh goc vuong)") ("Tat" . "Ca hang X (cheo lech): chi de xem")))
                      (list "gap" "Khoang cach giua cac phong khi xep (mm)" 'real (sd:cfg "KS-GAP" 2000.0))))
      (progn
        (setq unit (sd:cfg-put "KS-UNIT" (sd:v "unit")) tol (sd:cfg-put "KS-TOL" (sd:v "tol")) dung (sd:cfg-put "KS-DUNG" (sd:v "dung"))
              gap (sd:cfg-put "KS-GAP" (sd:v "gap")) sc (sd:sc)
              k (cond ((= unit "cm") 10.0) ((= unit "m") 1000.0) (1.0))
              rows (sd:ks-read fn k))
        (if (null rows)
          (princ "\n[SD] Khong doc duoc phong nao trong file.")
          (if (setq pt (sd:getpt "\nDiem chen phong dau tien (goc trai duoi): " nil))
            (progn
              (setq lay (sd:make-layer "SD-PHONG" 3 "Continuous" 25) x0 (car pt) y0 (cadr pt) x x0 y y0 rowh 0.0 cnt 0 drew 0 tot 0.0)
              (foreach r rows
                (setq g (sd:ks-grade (cadr r) tol) gr (car g) cnt (1+ cnt) nm (car r)
                      lines (cons (list nm gr (cadr g) (cadddr g)) lines))
                (if (and (caddr g) (wcmatch gr (cond ((= dung "A") "A") ((= dung "AB") "[AB]") ((= dung "ABC") "[ABC]") ("[ABCX]"))))
                  (progn
                    (setq pts (caddr g) bb (sd:cd-bbox pts) w (- (caddr bb) (car bb)) h (- (cadddr bb) (cadr bb)))
                    (if (and (> (- x x0) 0.0) (> (+ (- x x0) w) 80000.0)) (setq x x0 y (- y rowh gap) rowh 0.0))
                    (setq dx (- x (car bb)) dy (- y (cadr bb)))
                    (sd:pline (mapcar '(lambda (q) (list (+ (car q) dx) (+ (cadr q) dy))) pts) t lay)
                    (setq ctr (list (+ (car bb) dx (/ w 2.0)) (+ (cadr bb) dy (/ h 2.0))))
                    (sd:text ctr (strcat nm "  [" gr "]") (* 3.0 sc) "MC" lay)
                    (sd:text (list (car ctr) (- (cadr ctr) (* 5.0 sc))) (strcat "S = " (sd:rtos (/ (cadddr g) 1e6) 2) " m\\U+00B2") (* 2.5 sc) "MC" lay)
                    (setq x (+ x w gap) rowh (max rowh h) drew (1+ drew) tot (+ tot (cadddr g))))))
              (princ (strcat "\n[SD] Khao sat: " (itoa cnt) " phong, dung " (itoa drew) " phong (hang " dung "), tong " (sd:rtos (/ tot 1e6) 2) " m\\U+00B2 (tu toa do dung hinh)."))
              (foreach l (reverse lines)
                (if (or (/= (cadr l) "A") (caddr l))
                  (princ (strcat "\n  " (car l) " [" (cadr l) "]" (if (caddr l) (strcat ": " (sd:join (caddr l) "; ")) "")))))
              (princ "\n   Dung polyline phong lam bien cho SDGACH / SDLOT / SDRAITAM. Shop drawing op lat chi nen dung phong hang A; B, C can do them cheo truoc khi dat vat tu.")))))))
  (sd:finish))

;;; --------------------------------------------------------------------------
;;;  SDCHIABAC - Chia bac thang tu cao do: cao do hoan thien 2 san (so voi +-0.000 cong trinh) + so bac tung ve ->
;;;  chieu cao bac (lam tron, don phan lech vao cac bac tren cung hoac duoi cung), bang cao do hoan thien / ket cau cua tung bac va chieu nghi
;;; --------------------------------------------------------------------------
;; n bac, tong chieu cao total (mm), tron = buoc lam tron (mm, 0 = giu so le), top = T don phan lech len cac bac tren cung, nil = duoi cung.
;; Tra ve danh sach n chieu cao bac (mm) tu duoi len, tong dung bang total
(defun sd:cb-heights (n total tron top / base r diff m k res i lst h sg)
  (setq base (/ total n))
  (if (<= tron 0.0)
    (repeat n (setq lst (cons base lst)))
    (progn
      (setq r (* tron (fix (+ 0.5 (/ base tron)))) diff (- total (* r n))
            m (fix (+ (if (< diff 0.0) -0.5 0.5) (/ diff tron))) k (abs m) sg (if (< m 0) -1.0 1.0)
            res (- diff (* m tron)) i 0)
      (repeat n
        (setq h r)
        (if (if top (>= i (- n k)) (< i k)) (setq h (+ h (* sg tron))))
        (if (= i (if top (1- n) 0)) (setq h (+ h res)))
        (setq lst (cons h lst) i (1+ i)))
      (setq lst (reverse lst))))
  lst)

;; Hang bang cao do: ((nhan cao-do-hoan-thien cao-do-ket-cau cao-bac ghi-chu) ...); flights = so bac tung ve; lop = day da + vua (mm)
(defun sd:cb-rows (z0 hs flights lop / z k r nf j h)
  (setq z z0 k 0 nf 0)
  (foreach fl flights
    (setq nf (1+ nf))
    (repeat fl
      (setq h (nth k hs) z (+ z h) k (1+ k))
      (setq r (cons (list (strcat "B\\U+1EACC " (itoa k)) z (- z lop) h "") r)))
    (if (< nf (length flights))
      (setq r (cons (list (strcat "CHI\\U+1EBEU NGH\\U+1EC8 " (itoa nf)) z (- z lop) nil "") r))))
  (reverse r))

(defun sd:cb-flights (s / r v)
  (foreach tk (sd:split s ",")
    (setq v (atoi (vl-string-trim " " tk)))
    (if (> v 0) (setq r (cons v r))))
  (reverse r))

(defun c:SDCHIABAC (/ z0 z1 chia fl n total tron top da vua lop hs rows trows pt hmin hmax nom st)
  (sd:begin)
  (if (sd:dlg "Chia b\\U+1EADc thang t\\U+1EEB cao \\U+0111\\U+1ED9 (SDCHIABAC)"
              (list (list "z0" "Cao \\U+0111\\U+1ED9 ho\\U+00E0n thi\\U+1EC7n s\\U+00E0n d\\U+01B0\\U+1EDBi so v\\U+1EDBi \\U+00B10.000 c\\U+00F4ng tr\\U+00ECnh (m)" 'real (sd:cfg "CB-Z0" 0.0))
                    (list "z1" "Cao \\U+0111\\U+1ED9 ho\\U+00E0n thi\\U+1EC7n s\\U+00E0n tr\\U+00EAn (m)" 'real (sd:cfg "CB-Z1" 3.5))
                    (list "chia" "S\\U+1ED1 b\\U+1EADc t\\U+1EEBng v\\U+1EBF, c\\U+00E1ch nhau d\\U+1EA5u ph\\U+1EA9y (VD 10,11; m\\U+1ED9t v\\U+1EBF: 21). Chi\\U+1EBFu ngh\\U+1EC9 n\\U+1EB1m gi\\U+1EEFa c\\U+00E1c v\\U+1EBF" 'str (sd:cfg "CB-CHIA" "21"))
                    (list "tron" "L\\U+00E0m tr\\U+00F2n chi\\U+1EC1u cao b\\U+1EADc t\\U+1EDBi (mm; 0 = gi\\U+1EEF s\\U+1ED1 l\\U+1EBB)" 'real0 (sd:cfg "CB-TRON" 1.0))
                    (list "don" "Ph\\U+1EA7n l\\U+1EC7ch do l\\U+00E0m tr\\U+00F2n d\\U+1ED3n v\\U+00E0o" 'kw (sd:cfg "CB-DON" "Tren")
                          '(("Tren" . "C\\U+00E1c b\\U+1EADc tr\\U+00EAn c\\U+00F9ng (b\\U+1EADc tr\\U+00EAn th\\U+1EA5p h\\U+01A1n ho\\U+1EB7c cao h\\U+01A1n m\\U+1ED9t ch\\U+00FAt)") ("Duoi" . "C\\U+00E1c b\\U+1EADc d\\U+01B0\\U+1EDBi c\\U+00F9ng")))
                    (list "da" "\\U+0110\\U+00E1 m\\U+1EB7t b\\U+1EADc / s\\U+00E0n d\\U+00E0y (mm)" 'real0 (sd:cfg "CB-DA" 20.0))
                    (list "vua" "L\\U+1EDBp v\\U+1EEFa / h\\U+1ED3 d\\U+1EA7u d\\U+01B0\\U+1EDBi \\U+0111\\U+00E1 (mm)" 'real0 (sd:cfg "CB-VUA" 30.0))
                    (list "st" "\\U+0110\\U+1EB7t lu\\U+00F4n chi\\U+1EC1u cao b\\U+1EADc v\\U+00E0 s\\U+1ED1 b\\U+1EADc v\\U+1EBF \\U+0111\\U+1EA7u cho SDTHANGDA" 'tog t)))
    (progn
      (setq z0 (sd:cfg-put "CB-Z0" (sd:v "z0")) z1 (sd:cfg-put "CB-Z1" (sd:v "z1")) chia (sd:cfg-put "CB-CHIA" (sd:v "chia"))
            tron (sd:cfg-put "CB-TRON" (cond ((sd:v "tron")) (0.0))) top (= (sd:cfg-put "CB-DON" (sd:v "don")) "Tren")
            da (sd:cfg-put "CB-DA" (cond ((sd:v "da")) (0.0))) vua (sd:cfg-put "CB-VUA" (cond ((sd:v "vua")) (0.0)))
            lop (+ da vua) fl (sd:cb-flights chia) n (apply '+ (cons 0 fl)) total (* 1000.0 (- z1 z0)))
      (cond
        ((null fl) (princ "\n[SD] S\\U+1ED1 b\\U+1EADc t\\U+1EEBng v\\U+1EBF kh\\U+00F4ng h\\U+1EE3p l\\U+1EC7 (VD 10,11)."))
        ((<= total 0.0) (princ "\n[SD] Cao \\U+0111\\U+1ED9 s\\U+00E0n tr\\U+00EAn ph\\U+1EA3i l\\U+1EDBn h\\U+01A1n cao \\U+0111\\U+1ED9 s\\U+00E0n d\\U+01B0\\U+1EDBi."))
        (t
         (setq hs (sd:cb-heights n total tron top)
               hmin (apply 'min hs) hmax (apply 'max hs)
               rows (sd:cb-rows (* 1000.0 z0) hs fl lop))
         (princ (strcat "\n[SD] " (itoa n) " b\\U+1EADc, chi\\U+1EC1u cao t\\U+1EA7ng " (sd:rtos total 1) " mm: b\\U+1EADc " (sd:rtos hmin 1)
                        (if (> (- hmax hmin) 0.05) (strcat " \\U+0111\\U+1EBFn " (sd:rtos hmax 1)) "") " mm (chia ch\\U+00EDnh x\\U+00E1c " (sd:rtos (/ total n) 2) ")."))
         (if (or (< hmin 150.0) (> hmax 180.0))
           (princ "\n[!] Chi\\U+1EC1u cao b\\U+1EADc ngo\\U+00E0i kho\\U+1EA3ng 150 - 180 mm: ki\\U+1EC3m tra s\\U+1ED1 b\\U+1EADc ho\\U+1EB7c cao \\U+0111\\U+1ED9."))
         (if (> (- hmax hmin) 0.05)
           (princ (strcat "\n   L\\U+00E0m tr\\U+00F2n t\\U+1EDBi " (sd:num tron) " mm n\\U+00EAn c\\U+00E1c b\\U+1EADc kh\\U+00F4ng \\U+0111\\U+1EC1u nhau, ch\\U+00EAnh t\\U+1ED1i \\U+0111a " (sd:rtos (- hmax hmin) 1) " mm; b\\U+1EADc l\\U+1EC7ch n\\U+1EB1m \\U+1EDF ph\\U+1EA7n " (if top "tr\\U+00EAn" "d\\U+01B0\\U+1EDBi") " c\\U+00F9ng c\\U+1EE7a thang.")))
         (foreach r rows
           (princ (strcat "\n  " (car r) ": ho\\U+00E0n thi\\U+1EC7n " (sd:rtos (/ (cadr r) 1000.0) 3) " | k\\U+1EBFt c\\U+1EA5u " (sd:rtos (/ (caddr r) 1000.0) 3)
                          (if (cadddr r) (strcat " | b\\U+1EADc " (sd:rtos (cadddr r) 1)) ""))))
         (setq trows (cons (list "R" (list "S\\U+00C0N D\\U+01AF\\U+1EDAI" (sd:rtos z0 3) (sd:rtos (- z0 (/ lop 1000.0)) 3) "" "") nil) trows))
         (foreach r rows
           (setq trows (cons (list "R" (list (car r) (sd:rtos (/ (cadr r) 1000.0) 3) (sd:rtos (/ (caddr r) 1000.0) 3)
                                             (if (cadddr r) (sd:rtos (cadddr r) 1) "") (if (cadddr r) "" "chi\\U+1EBFu ngh\\U+1EC9"))
                                   nil)
                             trows)))
         (setq trows (reverse trows))
         (if (setq pt (sd:getpt "\n\\U+0110i\\U+1EC3m ch\\U+00E8n b\\U+1EA3ng cao \\U+0111\\U+1ED9 (g\\U+00F3c tr\\U+00E1i tr\\U+00EAn) <b\\U+1ECF qua>: " nil))
           (sd:table2 pt "B\\U+1EA2NG CAO \\U+0110\\U+1ED8 B\\U+1EACC THANG (m, SO V\\U+1EDAI \\U+00B10.000)"
                      '(("B\\U+1EACC" 28) ("CAO \\U+0110\\U+1ED8 HO\\U+00C0N THI\\U+1EC6N" 36) ("CAO \\U+0110\\U+1ED8 K\\U+1EBET C\\U+1EA4U" 36) ("CAO B\\U+1EACC (mm)" 28) ("GHI CH\\U+00DA" 28))
                      trows -1 (sd:sc)))
         (if (sd:v "st")
           (progn
             (setq nom (if (> tron 0.0) (* tron (fix (+ 0.5 (/ (/ total n) tron)))) (/ total n)))
             (sd:cfg-put "ST-R" nom) (sd:cfg-put "ST-N" (car fl))
             (princ (strcat "\n[SD] SDTHANGDA: chi\\U+1EC1u cao b\\U+1EADc \\U+0111\\U+1EB7t " (sd:rtos nom 1) " mm, s\\U+1ED1 b\\U+1EADc " (itoa (car fl)) " (v\\U+1EBF \\U+0111\\U+1EA7u); b\\U+1EADc l\\U+1EC7ch x\\U+1EED l\\U+00FD ri\\U+00EAng n\\U+1EBFu c\\U+1EA7n.")))))))
    )
  (sd:finish))

;;; --------------------------------------------------------------------------
;;;  SDMAVIEN - Ma vien theo hinh dang: cac vien cung vat lieu va cung hinh dang (xoay duoc, tuy chon doi xung guong) co cung ma (VD G1-01).
;;;  Ma ghi vao vien (xdata SD_MAVIEN) va nho trong ban ve: chay lai thi vien cu giu ma cu, hinh moi nhan ma tiep theo.
;;; --------------------------------------------------------------------------
;; Da giac nguoc chieu kim dong ho neu can (CCW)
(defun sd:mv-orient (pts / a s)
  (setq a (last pts) s 0.0)
  (foreach b pts (setq s (+ s (- (* (car a) (cadr b)) (* (car b) (cadr a)))) a b))
  (if (< s 0.0) (reverse pts) pts))

;; Bo dinh trung / thang hang (goc re < 0.1 do)
(defun sd:mv-clean (pts / r n i p0 p1 p2 d1x d1y d2x d2y)
  (setq n (length pts) i 0)
  (repeat n
    (setq p0 (nth (rem (+ i n -1) n) pts) p1 (nth i pts) p2 (nth (rem (1+ i) n) pts)
          d1x (- (car p1) (car p0)) d1y (- (cadr p1) (cadr p0)) d2x (- (car p2) (car p1)) d2y (- (cadr p2) (cadr p1)))
    (if (> (abs (atan (- (* d1x d2y) (* d1y d2x)) (+ (* d1x d2x) (* d1y d2y)))) 0.0017) (setq r (cons p1 r)))
    (setq i (1+ i)))
  (reverse r))

;; Day token "dai/goc-re" cua da giac CCW (dai lam tron theo tol mm, goc re tron 1 do)
(defun sd:mv-seq (pts tol / n i p1 p2 p3 d1x d1y d2x d2y r)
  (setq n (length pts) i 0)
  (repeat n
    (setq p1 (nth i pts) p2 (nth (rem (1+ i) n) pts) p3 (nth (rem (+ i 2) n) pts)
          d1x (- (car p2) (car p1)) d1y (- (cadr p2) (cadr p1)) d2x (- (car p3) (car p2)) d2y (- (cadr p3) (cadr p2)))
    (setq r (cons (strcat (itoa (fix (+ 0.5 (/ (sqrt (+ (* d1x d1x) (* d1y d1y))) tol)))) "/"
                          (itoa (fix (+ 0.5 (* (/ 180.0 pi) (atan (- (* d1x d2y) (* d1y d2x)) (+ (* d1x d2x) (* d1y d2y))))))))
                  r)
          i (1+ i)))
  (reverse r))

;; Chuoi nho nhat trong cac phep quay diem bat dau cua day token (khong phu thuoc diem dau / huong xoay vien)
(defun sd:mv-canon (seq / n k best str i)
  (setq n (length seq) k 0)
  (repeat n
    (setq str "" i 0)
    (repeat n (setq str (strcat str (nth (rem (+ k i) n) seq) ";") i (1+ i)))
    (if (or (null best) (< str best)) (setq best str))
    (setq k (1+ k)))
  best)

(defun sd:mv-key (pts tol mirror / p a b)
  (setq p (sd:mv-clean (sd:mv-orient pts)) a (sd:mv-canon (sd:mv-seq p tol)))
  (if mirror
    (progn
      (setq b (sd:mv-canon (sd:mv-seq (sd:mv-orient (mapcar '(lambda (q) (list (- (car q)) (cadr q))) p)) tol)))
      (if (< b a) (setq a b))))
  a)

;; Ma viec da ghi tren viec e (nil neu chua co)
(defun sd:mv-get (e)
  (car (mapcar 'cdr (cdadr (assoc -3 (entget e '("SD_MAVIEN")))))))

;; So thu tu lon nhat da dung voi tien to pre trong bang map ((khoa . ma) ...)
(defun sd:mv-max (map pre / m n)
  (setq m 0)
  (foreach kv map
    (if (and (> (strlen (cdr kv)) (1+ (strlen pre))) (= (substr (cdr kv) 1 (1+ (strlen pre))) (strcat pre "-")))
      (progn (setq n (atoi (substr (cdr kv) (+ 2 (strlen pre))))) (if (> n m) (setq m n)))))
  m)

(defun c:SDMAVIEN (/ ss tol mir pre pfx re mk map i e xd pts key mat code np g groups fr lay sc trows lines pl pt fn f nnew nold cls)
  (sd:begin)
  (if (setq ss (sd:select-tiles "\nCh\\U+1ECDn c\\U+00E1c vi\\U+00EAn c\\U+1EA7n \\U+0111\\U+00E1nh m\\U+00E3 <Enter = t\\U+1EA5t c\\U+1EA3 trong b\\U+1EA3n v\\U+1EBD>: "))
    (if (sd:dlg "M\\U+00E3 vi\\U+00EAn theo h\\U+00ECnh d\\U+1EA1ng (SDMAVIEN)"
                (list (list "tol" "Dung sai k\\U+00EDch th\\U+01B0\\U+1EDBc coi l\\U+00E0 c\\U+00F9ng h\\U+00ECnh (mm)" 'real (sd:cfg "MV-TOL" 1.0))
                      (list "mir" "G\\U+1ED9p c\\U+1EA3 vi\\U+00EAn \\U+0111\\U+1ED1i x\\U+1EE9ng g\\U+01B0\\U+01A1ng (VD hai vi\\U+00EAn ch\\U+1EEF L \\U+0111\\U+1ED1i x\\U+1EE9ng)" 'tog (sd:cfg "MV-MIR" nil))
                      (list "pre" "Ti\\U+1EC1n t\\U+1ED1 m\\U+00E3" 'kw (sd:cfg "MV-PRE" "Mat") '(("Mat" . "M\\U+00E3 v\\U+1EADt li\\U+1EC7u (VD G1-01)") ("Co" . "Ti\\U+1EC1n t\\U+1ED1 c\\U+1ED1 \\U+0111\\U+1ECBnh b\\U+00EAn d\\U+01B0\\U+1EDBi")))
                      (list "pfx" "Ti\\U+1EC1n t\\U+1ED1 c\\U+1ED1 \\U+0111\\U+1ECBnh (VD ST)" 'str (sd:cfg "MV-PFX" "ST") nil '("pre" "Co"))
                      (list "re" "\\U+0110\\U+00E1nh l\\U+1EA1i t\\U+1EEB \\U+0111\\U+1EA7u (b\\U+1ECF b\\U+1EA3ng m\\U+00E3 \\U+0111\\U+00E3 nh\\U+1EDB)" 'tog nil)
                      (list "mk" "Ghi m\\U+00E3 l\\U+00EAn t\\U+1EEBng vi\\U+00EAn (layer SD-MAVIEN)" 'tog t)))
      (progn
        (setq tol (sd:cfg-put "MV-TOL" (sd:v "tol")) mir (sd:cfg-put "MV-MIR" (sd:v "mir")) pre (sd:cfg-put "MV-PRE" (sd:v "pre"))
              pfx (vl-string-trim " " (cond ((sd:cfg-put "MV-PFX" (cond ((sd:v "pfx")) ("ST"))))))
              re (sd:v "re") mk (sd:v "mk") sc (sd:sc) nnew 0 nold 0
              map (if re nil (vlax-ldata-get "SD" "MAVIEN-MAP")))
        (regapp "SD_MAVIEN")
        (setq lay (sd:make-layer "SD-MAVIEN" 4 "Continuous" 13))
        (sd:cd-clear lay)
        (setq i 0)
        (repeat (sslength ss)
          (setq e (ssname ss i) i (1+ i) xd (mapcar 'cdr (cdadr (assoc -3 (entget e '("SD_TILE"))))))
          (if (and (>= (length xd) 12) (/= (nth 1 xd) "X") (>= (length (setq pts (sd:curve-pts e))) 3))
            (progn
              (setq mat (nth 0 xd) key (strcat mat "|" (sd:mv-key pts tol mir)))
              (if (setq code (cdr (assoc key map)))
                (setq nold (1+ nold))
                (progn
                  (setq np (if (= pre "Mat") mat (if (= pfx "") "ST" pfx))
                        code (strcat np "-" (sd:khi-num2 (1+ (sd:mv-max map np))))
                        map (append map (list (cons key code))) nnew (1+ nnew))))
              (entmod (append (entget e) (list (list -3 (list "SD_MAVIEN" (cons 1000 code))))))
              (setq fr (sd:tile-frame pts))
              (if (setq g (assoc code groups))
                (setq groups (subst (list code (1+ (nth 1 g)) (nth 2 g) (nth 3 g) (+ (nth 4 g) (/ (sd:cd-area pts) 1e6)) (nth 5 g) (nth 6 g) (nth 7 g)) g groups))
                (setq groups (cons (list code 1 mat (nth 1 xd) (/ (sd:cd-area pts) 1e6) (cadr fr) (caddr fr) nil) groups)))
              (setq pl (cons (list code (car (cadddr fr)) (cadr (cadddr fr)) mat) pl))
              (if mk (sd:text (cadddr fr) code (sd:tile-th (cadr fr) (caddr fr) sc) "MC" lay)))))
        (vlax-ldata-put "SD" "MAVIEN-MAP" map)
        (setq groups (sd:sort groups '(lambda (a b) (< (car a) (car b)))))
        (foreach g groups
          (setq cls (cond ((= (nth 3 g) "F") "Nguy\\U+00EAn") ((= (nth 3 g) "C") "C\\U+1EAFt ch\\U+1EEF nh\\U+1EADt") (t "C\\U+1EAFt \\U+0111\\U+1EB7c bi\\U+1EC7t"))
                trows (cons (list "R" (list (car g) cls (strcat (sd:rtos (max (nth 5 g) (nth 6 g)) 0) "\\U+00D7" (sd:rtos (min (nth 5 g) (nth 6 g)) 0))
                                            (itoa (nth 1 g)) (sd:rtos (nth 4 g) 2))
                                  nil)
                            trows)
                lines (cons (sd:join (list (car g) (nth 2 g) cls (sd:rtos (max (nth 5 g) (nth 6 g)) 0) (sd:rtos (min (nth 5 g) (nth 6 g)) 0) (itoa (nth 1 g)) (sd:rtos (nth 4 g) 3)) ";") lines)))
        (setq trows (reverse trows))
        (princ (strcat "\n[SD] " (itoa (+ nnew nold)) " vi\\U+00EAn, " (itoa (length groups)) " m\\U+00E3 (" (itoa nnew) " vi\\U+00EAn thu\\U+1ED9c h\\U+00ECnh m\\U+1EDBi, " (itoa nold) " vi\\U+00EAn gi\\U+1EEF m\\U+00E3 \\U+0111\\U+00E3 nh\\U+1EDB)."))
        (if (setq pt (sd:getpt "\n\\U+0110i\\U+1EC3m ch\\U+00E8n b\\U+1EA3ng m\\U+00E3 vi\\U+00EAn (g\\U+00F3c tr\\U+00E1i tr\\U+00EAn) <b\\U+1ECF qua>: " nil))
          (sd:table2 pt "B\\U+1EA2NG M\\U+00C3 VI\\U+00CAN"
                     '(("M\\U+00C3 VI\\U+00CAN" 26) ("LO\\U+1EA0I" 32) ("K\\U+00CDCH TH\\U+01AF\\U+1EDAC (mm)" 34) ("SL" 14) ("DT (m\\U+00B2)" 24))
                     trows -1 sc))
        (setq fn (sd:csv-name "_MaVien.csv"))
        (if (setq f (sd:open fn "w"))
          (progn
            (write-line "Ma vien;Ma VL;Loai;Dai (mm);Rong (mm);SL;Tong DT (m2)" f)
            (foreach l (reverse lines) (write-line l f))
            (setq fn (sd:close f))
            (princ (strcat "\n[SD] \\U+0110\\U+00E3 xu\\U+1EA5t: " fn))))
        (setq fn (sd:csv-name "_MaVienTungVien.csv"))
        (if (setq f (sd:open fn "w"))
          (progn
            (write-line "Ma vien;X tam;Y tam;Ma VL" f)
            (foreach l (reverse pl) (write-line (sd:join (list (car l) (sd:rtos (cadr l) 0) (sd:rtos (caddr l) 0) (cadddr l)) ";") f))
            (setq fn (sd:close f))
            (princ (strcat "\n[SD] \\U+0110\\U+00E3 xu\\U+1EA5t: " fn)))))))
  (sd:finish))

;;; --------------------------------------------------------------------------
;;;  SDHOBOI - Ho boi: do doc day (dau nong -> dau sau), duong dong muc, khe co gian, mat cat doc, kiem tra theo TCVN 4260:2012 va ISPSC 2015
;;; --------------------------------------------------------------------------
;; Do sau nuoc tai tram s (mm tu thanh nong): phang d1 den a, doc den a+ls, phang d2
(defun sd:hb-depth (s a ls d1 d2)
  (cond ((<= s a) d1)
        ((>= s (+ a ls)) d2)
        (t (+ d1 (* (- s a) (/ (- d2 d1) ls))))))
;; Diem (o + u*s + v*t), v = u xoay +90 do
(defun sd:hb-pt (o u s tt)
  (list (+ (car o) (* (car u) s) (* (- (cadr u)) tt)) (+ (cadr o) (* (cadr u) s) (* (car u) tt)) 0.0))
;; Cac tham so t (da sap xep) noi duong thang tram s0 (vuong goc truc u qua o) cat da giac pts
(defun sd:hb-chord (pts o u s0 / n i p q sp sq f x y ts)
  (setq n (length pts) i 0)
  (repeat n
    (setq p (nth i pts) q (nth (rem (1+ i) n) pts)
          sp (+ (* (- (car p) (car o)) (car u)) (* (- (cadr p) (cadr o)) (cadr u)))
          sq (+ (* (- (car q) (car o)) (car u)) (* (- (cadr q) (cadr o)) (cadr u))))
    (if (and (/= sp sq) (or (and (<= sp s0) (< s0 sq)) (and (<= sq s0) (< s0 sp))))
      (setq f (/ (- s0 sp) (- sq sp))
            x (+ (car p) (* f (- (car q) (car p)))) y (+ (cadr p) (* f (- (cadr q) (cadr p))))
            ts (cons (- (* (- y (cadr o)) (car u)) (* (- x (car o)) (cadr u))) ts)))
    (setq i (1+ i)))
  (vl-sort ts '<))
;; Ve cac doan chord (cap t1-t2, t3-t4...) cua tram s0 tren layer lay
(defun sd:hb-chord-draw (pts o u s0 lay / ts)
  (setq ts (sd:hb-chord pts o u s0))
  (while (>= (length ts) 2)
    (sd:line (sd:hb-pt o u s0 (car ts)) (sd:hb-pt o u s0 (cadr ts)) lay)
    (setq ts (cddr ts)))
  (sd:hb-chord pts o u s0))
;; Kiem tra doc day: i = cao / dai (khong don vi). Tra ve danh sach dong chu
(defun sd:hb-check (d1 d2 i / r)
  (cond ((> i (/ 1.0 3.0))
         (setq r (cons "[!] D\\U+1ED1c \\U+0111\\U+00E1y l\\U+1EDBn h\\U+01A1n 1:3 (33%): v\\U+01B0\\U+1EE3t gi\\U+1EDBi h\\U+1EA1n d\\U+1ED1c v\\U+00F9ng s\\U+00E2u trong ISPSC 2015 \\U+00A7807.1.3." r)))
        ((and (> i (/ 1.0 7.0)) (< d1 838.0))
         (setq r (cons "[!] D\\U+1ED1c \\U+0111\\U+00E1y l\\U+1EDBn h\\U+01A1n 1:7 (14%) ngay t\\U+1EEB v\\U+00F9ng n\\U+01B0\\U+1EDBc n\\U+00F4ng d\\U+01B0\\U+1EDBi 838 mm: v\\U+01B0\\U+1EE3t ISPSC 2015 \\U+00A7807.1.1 (v\\U+00F9ng n\\U+00F4ng t\\U+1ED1i \\U+0111a 1:7; ch\\U+1EC9 \\U+0111\\U+01B0\\U+1EE3c d\\U+1ED1c h\\U+01A1n khi \\U+0111\\U+00E3 qua \\U+0111\\U+1ED9 s\\U+00E2u 838 mm)." r)))
        ((and (> i 0.1) (< d1 1524.0))
         (setq r (cons "[?] D\\U+1ED1c l\\U+1EDBn h\\U+01A1n 1:10 trong v\\U+00F9ng n\\U+01B0\\U+1EDBc s\\U+00E2u \\U+0111\\U+1EBFn 1,5 m: quy \\U+0111\\U+1ECBnh x\\U+00E2y d\\U+1EF1ng M\\U+1EF9 (UpCodes 454.1.2) gi\\U+1EDBi h\\U+1EA1n 1:10 \\U+1EDF v\\U+00F9ng n\\U+00E0y; x\\U+00E1c nh\\U+1EADn ti\\U+00EAu chu\\U+1EA9n \\U+00E1p d\\U+1EE5ng cho d\\U+1EF1 \\U+00E1n." r))))
  (if (or (< d1 838.0) (> d1 1219.0))
    (setq r (cons "[?] \\U+0110\\U+1ED9 s\\U+00E2u n\\U+01B0\\U+1EDBc \\U+0111\\U+1EA7u n\\U+00F4ng ngo\\U+00E0i 838 - 1219 mm (ISPSC 2015 \\U+00A7807.2, h\\U+1ED3 gia \\U+0111\\U+00ECnh): \\U+0111\\U+00FAng n\\U+1EBFu l\\U+00E0 b\\U+1EC3 tr\\U+1EBB em / b\\U+1EC3 v\\U+1EA7y ho\\U+1EB7c h\\U+1ED3 c\\U+00F4ng c\\U+1ED9ng; x\\U+00E1c nh\\U+1EADn lo\\U+1EA1i h\\U+1ED3." r)))
  (if (> d2 1200.0)
    (setq r (cons "[i] S\\U+00E2u h\\U+01A1n 1,2 m: TCVN 4260:2012 \\U+00A75.1.8 y\\U+00EAu c\\U+1EA7u b\\U+1EADc \\U+0111\\U+1EE9ng ngh\\U+1EC9 ch\\U+00E2n \\U+1EDF \\U+0111\\U+1ED9 s\\U+00E2u 1,2 m d\\U+1ECDc hai th\\U+00E0nh d\\U+1ECDc; ISPSC 2015 \\U+00A7809.3 y\\U+00EAu c\\U+1EA7u l\\U+1ED1i l\\U+00EAn xu\\U+1ED1ng \\U+1EDF v\\U+00F9ng s\\U+00E2u khi n\\U+01B0\\U+1EDBc s\\U+00E2u qu\\U+00E1 1524 mm." r)))
  (setq r (cons "[i] TCVN 4260:2012 ch\\U+1EC9 quy \\U+0111\\U+1ECBnh \\U+0111\\U+00E1y d\\U+1ED1c v\\U+1EC1 h\\U+1ED1 thu 1 - 3% (\\U+00A75.1.11), kh\\U+00F4ng quy \\U+0111\\U+1ECBnh d\\U+1ED1c t\\U+1EEB \\U+0111\\U+1EA7u n\\U+00F4ng xu\\U+1ED1ng \\U+0111\\U+1EA7u s\\U+00E2u: \\U+0111\\U+1EB7t h\\U+1ED1 thu \\U+1EDF \\U+0111i\\U+1EC3m th\\U+1EA5p nh\\U+1EA5t v\\U+00E0 \\U+0111\\U+1ED1i chi\\U+1EBFu nh\\U+00E0 thi\\U+1EBFt k\\U+1EBF b\\U+1EC3." r))
  (reverse r))

(defun c:SDHOBOI (/ r e pts sp dp u o len smin smax tmin tmax lt a b n ls d1 d2 stp rl lt0 jt dkw dki kh mc pitch i ss pt sc
                    d k nx ny nc v tt lay x ts msg pr rows rh)
  (sd:begin)
  (if (sd:dlg "H\\U+1ED3 b\\U+01A1i: \\U+0111\\U+1ED9 d\\U+1ED1c \\U+0111\\U+00E1y, \\U+0111\\U+1ED3ng m\\U+1EE9c, khe co gi\\U+00E3n, m\\U+1EB7t c\\U+1EAFt (SDHOBOI)"
              (list (list "d1" "\\U+0110\\U+1ED9 s\\U+00E2u n\\U+01B0\\U+1EDBc \\U+0111\\U+1EA7u n\\U+00F4ng (mm)" 'real (sd:cfg "HB-D1" 1000.0))
                    (list "d2" "\\U+0110\\U+1ED9 s\\U+00E2u n\\U+01B0\\U+1EDBc \\U+0111\\U+1EA7u s\\U+00E2u (mm)" 'real (sd:cfg "HB-D2" 1500.0))
                    (list "a" "\\U+0110o\\U+1EA1n \\U+0111\\U+00E1y ph\\U+1EB3ng \\U+0111\\U+1EA7u n\\U+00F4ng (mm, t\\U+00EDnh t\\U+1EEB th\\U+00E0nh n\\U+00F4ng)" 'real0 (sd:cfg "HB-A" 1000.0))
                    (list "b" "\\U+0110o\\U+1EA1n \\U+0111\\U+00E1y ph\\U+1EB3ng \\U+0111\\U+1EA7u s\\U+00E2u (mm; 0 = d\\U+1ED1c \\U+0111\\U+1EBFn h\\U+1EBFt h\\U+1ED3)" 'real0 (sd:cfg "HB-B" 0.0))
                    (list "n" "Ho\\U+1EB7c nh\\U+1EADp \\U+0111\\U+1ED9 d\\U+1ED1c 1:n (0 = suy t\\U+1EEB \\U+0111o\\U+1EA1n ph\\U+1EB3ng; nh\\U+1EADp n th\\U+00EC \\U+0111o\\U+1EA1n ph\\U+1EB3ng \\U+0111\\U+1EA7u s\\U+00E2u t\\U+1EF1 t\\U+00EDnh)" 'real0 (sd:cfg "HB-N" 0.0))
                    (list "stp" "B\\U+01B0\\U+1EDBc \\U+0111\\U+01B0\\U+1EDDng \\U+0111\\U+1ED3ng m\\U+1EE9c \\U+0111\\U+00E1y (mm \\U+0111\\U+1ED9 s\\U+00E2u)" 'real (sd:cfg "HB-STEP" 100.0))
                    (list "rl" "Cao \\U+0111\\U+1ED9 m\\U+1EB7t n\\U+01B0\\U+1EDBc (m so v\\U+1EDBi \\U+00B10.000)" 'real0 (sd:cfg "HB-RL" 0.0))
                    (list "lt" "Chi\\U+1EC1u d\\U+00E0i vi\\U+00EAn \\U+0111\\U+00E1 l\\U+00E1t theo h\\U+01B0\\U+1EDBng d\\U+1ED1c (mm; 0 = b\\U+1ECF qua)" 'real0 (sd:cfg "HB-LT" 600.0))
                    (list "jt" "Ron (mm)" 'real0 (sd:cfg "HB-JT" 3.0))
                    (list "dkw" "B\\U+1EC1 r\\U+1ED9ng s\\U+00E2n quanh h\\U+1ED3 (mm; 0 = b\\U+1ECF qua)" 'real0 (sd:cfg "HB-DKW" 3000.0))
                    (list "dki" "\\U+0110\\U+1ED9 d\\U+1ED1c s\\U+00E2n (%)" 'real (sd:cfg "HB-DKI" 1.5))
                    (list "kh" "Khe co gi\\U+00E3n: kho\\U+1EA3ng c\\U+00E1ch t\\U+1ED1i \\U+0111a (mm; 0 = kh\\U+00F4ng v\\U+1EBD)" 'real0 (sd:cfg "HB-KH" 3000.0))
                    (list "mc" "V\\U+1EBD m\\U+1EB7t c\\U+1EAFt d\\U+1ECDc v\\U+00E0 b\\U+1EA3ng cao \\U+0111\\U+1ED9 \\U+0111\\U+00E1y" 'tog t)))
    (progn
      (setq d1 (sd:cfg-put "HB-D1" (sd:v "d1")) d2 (sd:cfg-put "HB-D2" (sd:v "d2")) a (sd:cfg-put "HB-A" (cond ((sd:v "a")) (0.0)))
            b (sd:cfg-put "HB-B" (cond ((sd:v "b")) (0.0))) n (sd:cfg-put "HB-N" (cond ((sd:v "n")) (0.0)))
            stp (sd:cfg-put "HB-STEP" (sd:v "stp")) rl (sd:cfg-put "HB-RL" (cond ((sd:v "rl")) (0.0)))
            lt0 (sd:cfg-put "HB-LT" (cond ((sd:v "lt")) (0.0))) jt (sd:cfg-put "HB-JT" (cond ((sd:v "jt")) (0.0)))
            dkw (sd:cfg-put "HB-DKW" (cond ((sd:v "dkw")) (0.0))) dki (sd:cfg-put "HB-DKI" (sd:v "dki"))
            kh (sd:cfg-put "HB-KH" (cond ((sd:v "kh")) (0.0))) mc (sd:v "mc") sc (sd:sc))
      (cond
        ((<= d2 d1) (princ "\n[SD] \\U+0110\\U+1ED9 s\\U+00E2u \\U+0111\\U+1EA7u s\\U+00E2u ph\\U+1EA3i l\\U+1EDBn h\\U+01A1n \\U+0111\\U+1EA7u n\\U+00F4ng."))
        ((null (setq r (entsel "\nCh\\U+1ECDn polyline k\\U+00EDn l\\U+00E0 m\\U+00E9p trong h\\U+1ED3 (m\\U+1EB7t b\\U+1EB1ng l\\U+00F2ng h\\U+1ED3): ")))
         (princ "\n[SD] Ch\\U+01B0a ch\\U+1ECDn."))
        ((not (and (= (cdr (assoc 0 (entget (car r)))) "LWPOLYLINE") (= 1 (logand 1 (cdr (assoc 70 (entget (car r))))))))
         (princ "\n[SD] C\\U+1EA7n ch\\U+1ECDn polyline k\\U+00EDn."))
        ((null (setq sp (sd:getpt "\nB\\U+1EA5m m\\U+1ED9t \\U+0111i\\U+1EC3m \\U+1EDF \\U+0111\\U+1EA7u N\\U+00D4NG (tr\\U+00EAn tr\\U+1EE5c d\\U+1ED1c): " nil))) (princ "\n[SD] Ch\\U+01B0a ch\\U+1ECDn \\U+0111i\\U+1EC3m."))
        ((null (setq dp (sd:getpt "\nB\\U+1EA5m m\\U+1ED9t \\U+0111i\\U+1EC3m \\U+1EDF \\U+0111\\U+1EA7u S\\U+00C2U (h\\U+01B0\\U+1EDBng d\\U+1ED1c xu\\U+1ED1ng): " sp))) (princ "\n[SD] Ch\\U+01B0a ch\\U+1ECDn \\U+0111i\\U+1EC3m."))
        (t
         (setq e (car r) pts (sd:curve-pts e) o (sd:2d sp) len (distance (sd:2d sp) (sd:2d dp)))
         (if (< len 1.0)
           (princ "\n[SD] Hai \\U+0111i\\U+1EC3m tr\\U+00F9ng nhau.")
           (progn
             (setq u (list (/ (- (car dp) (car sp)) len) (/ (- (cadr dp) (cadr sp)) len))
                   ss (mapcar '(lambda (q) (+ (* (- (car q) (car o)) (car u)) (* (- (cadr q) (cadr o)) (cadr u)))) pts)
                   tt (mapcar '(lambda (q) (- (* (- (cadr q) (cadr o)) (car u)) (* (- (car q) (car o)) (cadr u)))) pts)
                   smin (apply 'min ss) smax (apply 'max ss) tmin (apply 'min tt) tmax (apply 'max tt) lt (- smax smin))
             (cond
               ((> n 0.0) (setq ls (* (- d2 d1) n) b (- lt a ls)))
               (t (setq ls (- lt a b))))
             (cond
               ((or (<= ls 1.0) (< b -1e-6))
                (princ (strcat "\n[SD] H\\U+1ED3 d\\U+00E0i " (sd:num lt) " mm theo tr\\U+1EE5c kh\\U+00F4ng \\U+0111\\U+1EE7 ch\\U+1ED7 cho \\U+0111o\\U+1EA1n ph\\U+1EB3ng + \\U+0111o\\U+1EA1n d\\U+1ED1c: gi\\U+1EA3m \\U+0111o\\U+1EA1n ph\\U+1EB3ng ho\\U+1EB7c t\\U+0103ng \\U+0111\\U+1ED9 d\\U+1ED1c.")))
               (t
                (setq i (/ (- d2 d1) ls) pitch (+ lt0 jt))
                (foreach lay (list (list "SD-HOBOI" 5) (list "SD-HOBOI-DM" 8) (list "SD-HOBOI-DOI" 1) (list "SD-HOBOI-KHE" 2) (list "SD-HOBOI-MC" 4))
                  (sd:make-layer (car lay) (cadr lay) "Continuous" 18))
                ;; truc doc + nhan
                (sd:line (sd:hb-pt o u smin (/ (+ tmin tmax) 2.0)) (sd:hb-pt o u smax (/ (+ tmin tmax) 2.0)) "SD-HOBOI")
                (sd:text (sd:p+ (sd:hb-pt o u smin (/ (+ tmin tmax) 2.0)) 0 (* 3.0 sc)) (strcat "\\U+0110\\U+1EA6U N\\U+00D4NG " (sd:num d1)) (* 2.5 sc) "L" "SD-HOBOI")
                (sd:text (sd:p+ (sd:hb-pt o u smax (/ (+ tmin tmax) 2.0)) 0 (* 3.0 sc)) (strcat "\\U+0110\\U+1EA6U S\\U+00C2U " (sd:num d2)) (* 2.5 sc) "R" "SD-HOBOI")
                ;; duong doi doc
                (if (> a 1.0) (sd:hb-chord-draw pts o u (+ smin a) "SD-HOBOI-DOI"))
                (if (> b 1.0) (sd:hb-chord-draw pts o u (+ smin a ls) "SD-HOBOI-DOI"))
                ;; duong dong muc
                (setq k 1 nc 0)
                (while (< (+ d1 (* k stp)) (- d2 1e-6))
                  (setq d (+ d1 (* k stp)) x (+ smin a (/ (- d d1) i)) ts (sd:hb-chord-draw pts o u x "SD-HOBOI-DM"))
                  (if ts
                    (sd:text (sd:hb-pt o u x (+ (car ts) (* 2.0 sc))) (strcat "-" (sd:num d) " (" (sd:rtos (- rl (/ d 1000.0)) 2) ")") (* 2.0 sc) "L" "SD-HOBOI-DM"))
                  (setq k (1+ k) nc (1+ nc)))
                ;; khe co gian
                (setq pr nil)
                (if (> kh 0.0)
                  (progn
                    (setq nx (max 1 (fix (+ 0.999 (/ lt kh)))) ny (max 1 (fix (+ 0.999 (/ (- tmax tmin) kh)))))
                    (setq k 1)
                    (repeat (1- nx) (sd:hb-chord-draw pts o u (+ smin (* k (/ lt nx))) "SD-HOBOI-KHE") (setq k (1+ k)))
                    (setq k 1 v (list (- (cadr u)) (car u)))
                    (repeat (1- ny)
                      (sd:hb-chord-draw pts o v (+ tmin (* k (/ (- tmax tmin) ny))) "SD-HOBOI-KHE")
                      (setq k (1+ k)))
                    (setq pr (list (/ lt nx) (/ (- tmax tmin) ny)))))
                ;; bao cao
                (princ (strcat "\n[SD] SDHOBOI: h\\U+1ED3 d\\U+00E0i " (sd:num lt) " mm theo tr\\U+1EE5c, r\\U+1ED9ng " (sd:num (- tmax tmin)) " mm."
                               "\n  D\\U+1ED1c \\U+0111\\U+00E1y " (sd:rtos (* 100.0 i) 2) "% = 1:" (sd:rtos (/ 1.0 i) 1) " tr\\U+00EAn \\U+0111o\\U+1EA1n d\\U+1ED1c d\\U+00E0i " (sd:num ls) " mm (ph\\U+1EB3ng " (sd:num a) " + d\\U+1ED1c + ph\\U+1EB3ng " (sd:num b) ")."
                               "\n  S\\U+1ED1 \\U+0111\\U+01B0\\U+1EDDng \\U+0111\\U+1ED3ng m\\U+1EE9c \\U+0111\\U+00E1y: " (itoa nc) " (b\\U+01B0\\U+1EDBc " (sd:num stp) " mm)."))
                (if (> lt0 0.0)
                  (princ (strcat "\n  M\\U+1ED7i vi\\U+00EAn " (sd:num lt0) " mm (ron " (sd:num jt) ") theo h\\U+01B0\\U+1EDBng d\\U+1ED1c ch\\U+00EAnh cao " (sd:rtos (* i lt0) 1) " mm gi\\U+1EEFa hai m\\U+1EA1ch."
                                 "\n  \\U+0110\\U+01B0\\U+1EDDng \\U+0111\\U+1ED5i d\\U+1ED1c 1 (s=" (sd:num a) ") r\\U+01A1i v\\U+00E0o " (sd:rtos (/ a pitch) 2) " b\\U+01B0\\U+1EDBc vi\\U+00EAn; \\U+0111\\U+1EC1 xu\\U+1EA5t \\U+0111\\U+1EB7t \\U+0111\\U+00FAng m\\U+1EA1ch: s = " (sd:num (* pitch (fix (+ 0.5 (/ a pitch))))) " mm."
                                 (if (> b 1.0) (strcat "\n  \\U+0110\\U+01B0\\U+1EDDng \\U+0111\\U+1ED5i d\\U+1ED1c 2 (s=" (sd:num (+ a ls)) ") r\\U+01A1i v\\U+00E0o " (sd:rtos (/ (+ a ls) pitch) 2) " b\\U+01B0\\U+1EDBc vi\\U+00EAn.") ""))))
                (if pr
                  (princ (strcat "\n  Khe co gi\\U+00E3n: " (itoa nx) " \\U+00F4 theo tr\\U+1EE5c (" (sd:num (car pr)) " mm), " (itoa ny) " \\U+00F4 ngang (" (sd:num (cadr pr)) " mm). B\\U+1EC1 r\\U+1ED9ng khe t\\U+1ED1i thi\\U+1EC3u "
                                 (if (<= (max (car pr) (cadr pr)) 2600.0) "9" "12") " mm, s\\U+00E2u \\U+00EDt nh\\U+1EA5t b\\U+1EB1ng n\\U+1EEDa b\\U+1EC1 r\\U+1ED9ng, tr\\U+00E1m silicone / urethane c\\U+00F3 backer rod (Laticrete / TCNA EJ171: 2,4 - 3,7 m m\\U+1ED7i ph\\U+01B0\\U+01A1ng v\\U+00E0 s\\U+00E1t m\\U+1ECDi m\\U+1EB7t ch\\U+1EB7n)."
                                 (if (> (max (car pr) (cadr pr)) 3700.0) "\n  [!] Kho\\U+1EA3ng c\\U+00E1ch khe v\\U+01B0\\U+1EE3t 3,7 m: gi\\U+1EA3m s\\U+1ED1 mm kho\\U+1EA3ng c\\U+00E1ch t\\U+1ED1i \\U+0111a." ""))))
                (if (> dkw 0.0)
                  (princ (strcat "\n  S\\U+00E2n r\\U+1ED9ng " (sd:num dkw) " mm d\\U+1ED1c " (sd:rtos dki 2) "%: ch\\U+00EAnh cao hai m\\U+00E9p s\\U+00E2n " (sd:rtos (* dkw (/ dki 100.0)) 1) " mm; v\\U+1EEFa t\\U+1EA1o d\\U+1ED1c d\\U+00E0y th\\U+00EAm \\U+0111\\U+00FAng s\\U+1ED1 n\\U+00E0y \\U+1EDF m\\U+00E9p th\\U+1EA5p."
                                 (if (or (< dki 1.0) (> dki 2.0)) "\n  [!] D\\U+1ED1c s\\U+00E2n ngo\\U+00E0i 1 - 2%: TCVN 4260:2012 \\U+00A76.2.24 l\\U+1EA5y 1 - 2% v\\U+1EC1 ph\\U+00EDa ph\\U+1EC5u thu." ""))))
                (foreach msg (sd:hb-check d1 d2 i) (princ (strcat "\n  " msg)))
                ;; mat cat doc + bang cao do
                (if (and mc (setq pt (sd:getpt "\n\\U+0110i\\U+1EC3m ch\\U+00E8n m\\U+1EB7t c\\U+1EAFt d\\U+1ECDc <b\\U+1ECF qua>: " nil)))
                  (progn
                    (setq pt (sd:2d pt))
                    (sd:line (sd:p+ pt (- 300.0) 0.0) (sd:p+ pt (+ lt 300.0) 0.0) "SD-HOBOI-MC")
                    (sd:text (sd:p+ pt (+ lt 300.0) (* 1.0 sc)) (strcat "M\\U+1EF0C N\\U+01AF\\U+1EDAC " (sd:rtos rl 2)) (* 2.5 sc) "L" "SD-HOBOI-MC")
                    (sd:line (sd:p+ pt 0 (* 8.0 sc)) (sd:p+ pt 0 (- d1)) "SD-HOBOI-MC")
                    (sd:line (sd:p+ pt lt (* 8.0 sc)) (sd:p+ pt lt (- d2)) "SD-HOBOI-MC")
                    (sd:pline (list (sd:p+ pt 0 (- d1)) (sd:p+ pt a (- d1)) (sd:p+ pt (+ a ls) (- d2)) (sd:p+ pt lt (- d2))) nil "SD-HOBOI-MC")
                    (sd:text (sd:p+ pt (/ a 2.0) (- (+ d1 (* 4.0 sc)))) (strcat "-" (sd:num d1)) (* 2.5 sc) "MC" "SD-HOBOI-MC")
                    (sd:text (sd:p+ pt (- lt (/ (max b 1.0) 2.0)) (- (+ d2 (* 4.0 sc)))) (strcat "-" (sd:num d2)) (* 2.5 sc) "MC" "SD-HOBOI-MC")
                    (sd:text (sd:p+ pt (+ a (/ ls 2.0)) (- (+ (/ (+ d1 d2) 2.0) (* 6.0 sc)))) (strcat "i = " (sd:rtos (* 100.0 i) 2) "% (1:" (sd:rtos (/ 1.0 i) 1) ")") (* 3.0 sc) "MC" "SD-HOBOI-MC")
                    (sd:text (sd:p+ pt (/ lt 2.0) (* 10.0 sc)) (strcat "M\\U+1EB6T C\\U+1EAET D\\U+1ECCC H\\U+1ED2 B\\U+01A0I (\\U+0111\\U+1EA7u n\\U+00F4ng \\U+2192 \\U+0111\\U+1EA7u s\\U+00E2u), " (sd:num lt) " mm") (* 4.0 sc) "MC" "SD-HOBOI-MC")
                    (if (> pitch 0.0)
                      (progn
                        (setq rows 0 x 0.0 rh (* 4.0 sc))
                        (sd:text (sd:p+ pt 0 (- (+ d2 (* 14.0 sc)))) "B\\U+1EA2NG CAO \\U+0110\\U+1ED8 \\U+0110\\U+00C1Y T\\U+1EA0I M\\U+1EA0CH VI\\U+00CAN (t\\U+1EEB th\\U+00E0nh n\\U+00F4ng: \\U+0111\\U+1ED9 s\\U+00E2u / cao \\U+0111\\U+1ED9 ho\\U+00E0n thi\\U+1EC7n)" (* 2.5 sc) "L" "SD-HOBOI-MC")
                        (while (and (<= x (+ lt 1e-6)) (< rows 60))
                          (sd:text (sd:p+ pt 0 (- (+ d2 (* 14.0 sc) (* (1+ rows) rh)))) (strcat "s=" (sd:num x) "   -" (sd:num (sd:hb-depth x a ls d1 d2)) "   (" (sd:rtos (- rl (/ (sd:hb-depth x a ls d1 d2) 1000.0)) 3) ")") (* 2.0 sc) "L" "SD-HOBOI-MC")
                          (setq x (+ x pitch) rows (1+ rows)))
                        (if (<= x (+ lt 1e-6)) (princ "\n[SD] B\\U+1EA3ng cao \\U+0111\\U+1ED9 ch\\U+1EC9 li\\U+1EC7t k\\U+00EA 60 m\\U+1EA1ch \\U+0111\\U+1EA7u."))))))))))))))
  (sd:finish))

;;; --------------------------------------------------------------------------
;;;  SDLIENCAODO - Chuoi cao do: san chinh -> san WC -> san ho -> muc nuoc -> day ho; pheu thu tung vung, chenh cao, doi chieu doc
;;; --------------------------------------------------------------------------
;; Chon vung (polyline kin) + cac pheu thu; tra (khoang-cach-xa-nhat-mm pheu pts) hoac nil
(defun sd:lc-zone (name / r pts drs p step far)
  (cond
    ((null (setq r (entsel (strcat "\nCh\\U+1ECDn polyline k\\U+00EDn v\\U+00F9ng " name " <b\\U+1ECF qua>: "))))
     nil)
    ((not (and (= (cdr (assoc 0 (entget (car r)))) "LWPOLYLINE") (= 1 (logand 1 (cdr (assoc 70 (entget (car r))))))))
     (princ "\n[SD] C\\U+1EA7n polyline k\\U+00EDn: b\\U+1ECF v\\U+00F9ng n\\U+00E0y.") nil)
    (t
     (setq pts (sd:curve-pts (car r)))
     (while (setq p (getpoint (strcat "\nCh\\U+1ECDn ph\\U+1EC5u thu c\\U+1EE7a v\\U+00F9ng " name " <Enter xong>: ")))
       (setq drs (cons (sd:2d p) drs)))
     (cond
       ((null drs) (princ "\n[SD] Ch\\U+01B0a ch\\U+1ECDn ph\\U+1EC5u thu: b\\U+1ECF v\\U+00F9ng n\\U+00E0y.") nil)
       (t (setq step (max 100.0 (/ (distance (car (sd:bbox pts)) (cadr (sd:bbox pts))) 40.0))
                far (sd:dr-far pts drs step))
          (list (car far) drs pts))))))
;; Dong chu cao do (m) co dau: +0.000 / -0.045
(defun sd:lc-rl (x) (strcat (if (>= x -0.0005) "+" "") (sd:rtos x 3)))
;; Cac canh bao cua chuoi cao do. m = cao do san chinh, bc = ha cot WC (mm), iw / id = doc WC / san ho (%), wl = muc nuoc, dk = cao do san ho tai mep ho (m)
(defun sd:lc-check (m bc iw id wl dk / r)
  (if (<= bc 0.0) (setq r (cons "[!] S\\U+00E0n WC kh\\U+00F4ng th\\U+1EA5p h\\U+01A1n s\\U+00E0n ch\\U+00EDnh t\\U+1EA1i ng\\U+01B0\\U+1EE1ng c\\U+1EEDa: n\\U+01B0\\U+1EDBc d\\U+1EC5 ch\\U+1EA3y ra s\\U+00E0n ch\\U+00EDnh; th\\U+00F4ng th\\U+01B0\\U+1EDDng h\\U+1EA1 c\\U+1ED1t s\\U+00E0n WC (nh\\U+1EADp theo thi\\U+1EBFt k\\U+1EBF)." r)))
  (if (and iw (or (< iw 1.0) (> iw 2.0))) (setq r (cons "[?] D\\U+1ED1c s\\U+00E0n WC ngo\\U+00E0i 1 - 2%: TCVN 4260:2012 \\U+00A76.2.24 l\\U+1EA5y 1 - 2% v\\U+1EC1 ph\\U+00EDa ph\\U+1EC5u thu (cho s\\U+00E2n quanh b\\U+1EC3 v\\U+00E0 s\\U+00E0n khu v\\U+1EC7 sinh c\\U+1EE7a b\\U+1EC3 b\\U+01A1i)." r)))
  (if (and id (or (< id 1.0) (> id 2.0))) (setq r (cons "[?] D\\U+1ED1c s\\U+00E2n h\\U+1ED3 ngo\\U+00E0i 1 - 2%: TCVN 4260:2012 \\U+00A76.2.24." r)))
  (if (and wl dk (> wl dk)) (setq r (cons "[!] M\\U+1EF1c n\\U+01B0\\U+1EDBc cao h\\U+01A1n m\\U+1EB7t s\\U+00E2n t\\U+1EA1i m\\U+00E9p h\\U+1ED3: n\\U+01B0\\U+1EDBc tr\\U+00E0n ra s\\U+00E2n." r)))
  (if (and dk (> dk (+ m 0.0005))) (setq r (cons "[?] S\\U+00E2n h\\U+1ED3 t\\U+1EA1i m\\U+00E9p h\\U+1ED3 cao h\\U+01A1n s\\U+00E0n ch\\U+00EDnh: ki\\U+1EC3m tra n\\U+01B0\\U+1EDBc m\\U+01B0a / n\\U+01B0\\U+1EDBc r\\U+1EEDa s\\U+00E2n c\\U+00F3 ch\\U+1EA3y v\\U+00E0o nh\\U+00E0 kh\\U+00F4ng." r)))
  (reverse r))

(defun c:SDLIENCAODO (/ m bc iw id dk wl d1 d2 wc dkz levels n pt sc rowh y x0 x1 i lv prev dr bh ds)
  (sd:begin)
  (if (sd:dlg "Chu\\U+1ED7i cao \\U+0111\\U+1ED9: s\\U+00E0n ch\\U+00EDnh, WC, s\\U+00E2n h\\U+1ED3, \\U+0111\\U+00E1y h\\U+1ED3 (SDLIENCAODO)"
              (list (list "m" "Cao \\U+0111\\U+1ED9 s\\U+00E0n ch\\U+00EDnh ho\\U+00E0n thi\\U+1EC7n (m so v\\U+1EDBi \\U+00B10.000)" 'real0 (sd:cfg "LC-M" 0.0))
                    (list "bc" "S\\U+00E0n WC h\\U+1EA1 so v\\U+1EDBi s\\U+00E0n ch\\U+00EDnh t\\U+1EA1i ng\\U+01B0\\U+1EE1ng c\\U+1EEDa (mm)" 'real0 (sd:cfg "LC-BC" 20.0))
                    (list "iw" "D\\U+1ED1c s\\U+00E0n WC v\\U+1EC1 ph\\U+1EC5u thu (%)" 'real (sd:cfg "LC-IW" 1.0))
                    (list "dk" "Cao \\U+0111\\U+1ED9 s\\U+00E2n h\\U+1ED3 t\\U+1EA1i m\\U+00E9p h\\U+1ED3 (m)" 'real0 (sd:cfg "LC-DK" (sd:cfg "LC-M" 0.0)))
                    (list "id" "D\\U+1ED1c s\\U+00E2n h\\U+1ED3 v\\U+1EC1 ph\\U+1EC5u / r\\U+00E3nh thu (%)" 'real (sd:cfg "LC-ID" 1.5))
                    (list "wl" "Cao \\U+0111\\U+1ED9 m\\U+1EF1c n\\U+01B0\\U+1EDBc h\\U+1ED3 (m; h\\U+1ED3 \\U+0111\\U+00E3 nh\\U+1EADp b\\U+1EB1ng SDHOBOI th\\U+00EC l\\U+1EA5y theo \\U+0111\\U+00F3)" 'real0 (sd:cfg "HB-RL" -0.05))
                    (list "d1" "\\U+0110\\U+1ED9 s\\U+00E2u n\\U+01B0\\U+1EDBc \\U+0111\\U+1EA7u n\\U+00F4ng (mm)" 'real (sd:cfg "HB-D1" 1000.0))
                    (list "d2" "\\U+0110\\U+1ED9 s\\U+00E2u n\\U+01B0\\U+1EDBc \\U+0111\\U+1EA7u s\\U+00E2u (mm)" 'real (sd:cfg "HB-D2" 1500.0))
                    (list "bh" "B\\U+1EC1 r\\U+1ED9ng h\\U+1ED3 \\U+1EDF m\\U+1EB7t c\\U+1EAFt ngang (mm; ch\\U+1EC9 \\U+0111\\U+1EC3 v\\U+1EBD m\\U+1EB7t c\\U+1EAFt)" 'real0 (sd:cfg "LC-BH" 3000.0))
                    (list "ds" "\\U+0110\\U+1ED9 s\\U+00E2u n\\U+01B0\\U+1EDBc t\\U+1EA1i m\\U+1EB7t c\\U+1EAFt ngang (mm; 0 = \\U+0111\\U+1EA7u n\\U+00F4ng)" 'real0 (sd:cfg "LC-DS" 0.0))))
    (progn
      (setq m (sd:cfg-put "LC-M" (cond ((sd:v "m")) (0.0))) bc (sd:cfg-put "LC-BC" (cond ((sd:v "bc")) (0.0)))
            iw (sd:cfg-put "LC-IW" (sd:v "iw")) dk (sd:cfg-put "LC-DK" (cond ((sd:v "dk")) (0.0)))
            id (sd:cfg-put "LC-ID" (sd:v "id")) wl (sd:cfg-put "HB-RL" (cond ((sd:v "wl")) (0.0)))
            d1 (sd:cfg-put "HB-D1" (sd:v "d1")) d2 (sd:cfg-put "HB-D2" (sd:v "d2")) sc (sd:sc)
            bh (sd:cfg-put "LC-BH" (cond ((sd:v "bh")) (3000.0))) ds (sd:cfg-put "LC-DS" (cond ((sd:v "ds")) (0.0))))
      (if (<= ds 0.0) (setq ds d1))
      (sd:ho-warn '("LC-M" "LC-BC" "LC-IW" "LC-ID" "LC-DK" "HB-RL" "HB-D1" "HB-D2"))
      (princ "\nV\\U+00F9ng s\\U+00E0n WC (m\\U+1ED7i l\\U+1EA7n m\\U+1ED9t v\\U+00F9ng; Enter \\U+0111\\U+1EC3 b\\U+1ECF qua):")
      (setq wc (sd:lc-zone "WC"))
      (princ "\nV\\U+00F9ng s\\U+00E2n h\\U+1ED3:")
      (setq dkz (sd:lc-zone "s\\U+00E2n h\\U+1ED3"))
      ;; danh sach cao do (nhan rl), cao truoc
      (setq levels (list (list "S\\U+00E0n ch\\U+00EDnh ho\\U+00E0n thi\\U+1EC7n" m)
                         (list "S\\U+00E2n h\\U+1ED3 t\\U+1EA1i m\\U+00E9p h\\U+1ED3" dk)
                         (list "M\\U+1EF1c n\\U+01B0\\U+1EDBc h\\U+1ED3" wl)
                         (list "\\U+0110\\U+00E1y h\\U+1ED3 \\U+0111\\U+1EA7u n\\U+00F4ng" (- wl (/ d1 1000.0)))
                         (list "\\U+0110\\U+00E1y h\\U+1ED3 \\U+0111\\U+1EA7u s\\U+00E2u (h\\U+1ED1 thu \\U+0111\\U+00E1y h\\U+1ED3)" (- wl (/ d2 1000.0))))
            n (- m (/ bc 1000.0)))
      (setq levels (cons (list "S\\U+00E0n WC t\\U+1EA1i ng\\U+01B0\\U+1EE1ng c\\U+1EEDa (\\U+0111i\\U+1EC3m cao nh\\U+1EA5t)" n) levels))
      (if wc
        (setq levels (cons (list (strcat "S\\U+00E0n WC t\\U+1EA1i ph\\U+1EC5u thu (xa ph\\U+1EC5u nh\\U+1EA5t " (sd:rtos (/ (car wc) 1000.0) 2) " m)") (- n (* (/ iw 100.0) (/ (car wc) 1000.0)))) levels)))
      (if dkz
        (setq levels (cons (list (strcat "S\\U+00E2n h\\U+1ED3 t\\U+1EA1i ph\\U+1EC5u / r\\U+00E3nh thu (xa nh\\U+1EA5t " (sd:rtos (/ (car dkz) 1000.0) 2) " m)") (- dk (* (/ id 100.0) (/ (car dkz) 1000.0)))) levels)))
      (setq levels (sd:sort levels '(lambda (a b) (> (cadr a) (cadr b)))))
      (princ "\n[SD] SDLIENCAODO: chu\\U+1ED7i cao \\U+0111\\U+1ED9 t\\U+1EEB cao xu\\U+1ED1ng th\\U+1EA5p")
      (setq prev nil)
      (foreach lv levels
        (princ (strcat "\n  " (sd:lc-rl (cadr lv)) "  " (car lv) (if prev (strcat "   (th\\U+1EA5p h\\U+01A1n m\\U+1EE9c tr\\U+00EAn " (sd:rtos (* 1000.0 (- prev (cadr lv))) 0) " mm)") "")))
        (setq prev (cadr lv)))
      (princ (strcat "\n  S\\U+00E0n WC t\\U+1EA1i ng\\U+01B0\\U+1EE1ng th\\U+1EA5p h\\U+01A1n s\\U+00E0n ch\\U+00EDnh " (sd:rtos bc 0) " mm"
                     (if wc (strcat "; t\\U+1EA1i ph\\U+1EC5u th\\U+1EA5p h\\U+01A1n s\\U+00E0n ch\\U+00EDnh " (sd:rtos (* 1000.0 (- m (- n (* (/ iw 100.0) (/ (car wc) 1000.0))))) 0) " mm") "")
                     "; s\\U+00E2n h\\U+1ED3 c\\U+00E1ch m\\U+1EF1c n\\U+01B0\\U+1EDBc " (sd:rtos (* 1000.0 (- dk wl)) 0) " mm."))
      (foreach msg (sd:lc-check m bc (if wc iw) (if dkz id) wl dk) (princ (strcat "\n  " msg)))
      (vlax-ldata-put "SD" "LC-LEVELS" (mapcar '(lambda (lv) (list (car lv) (cadr lv))) levels))
      (if (setq pt (sd:getpt "\n\\U+0110i\\U+1EC3m ch\\U+00E8n s\\U+01A1 \\U+0111\\U+1ED3 cao \\U+0111\\U+1ED9 <b\\U+1ECF qua>: " nil))
        (progn
          (sd:make-layer "SD-CAODO-LIEN" 5 "Continuous" 18)
          (setq pt (sd:2d pt) rowh (* 14.0 sc) x0 0.0 x1 (* 60.0 sc) i 0 prev nil)
          (sd:text (sd:p+ pt 0 (* 8.0 sc)) "S\\U+01A0 \\U+0110\\U+1ED2 LI\\U+00CAN H\\U+1EC6 CAO \\U+0110\\U+1ED8 (kh\\U+00F4ng theo t\\U+1EC9 l\\U+1EC7 \\U+0111\\U+1EE9ng)" (* 4.0 sc) "L" "SD-CAODO-LIEN")
          (foreach lv levels
            (setq y (- (* i rowh)))
            (sd:line (sd:p+ pt x0 y) (sd:p+ pt x1 y) "SD-CAODO-LIEN")
            (sd:text (sd:p+ pt (- x0 (* 2.0 sc)) y) (sd:lc-rl (cadr lv)) (* 2.5 sc) "MR" "SD-CAODO-LIEN")
            (sd:text (sd:p+ pt (+ x1 (* 2.0 sc)) y) (car lv) (* 2.5 sc) "ML" "SD-CAODO-LIEN")
            (if prev
              (sd:text (sd:p+ pt (/ x1 2.0) (+ y (/ rowh 2.0))) (strcat "\\U+0394 " (sd:rtos (* 1000.0 (- prev (cadr lv))) 0) " mm") (* 2.0 sc) "MC" "SD-CAODO-LIEN"))
            (setq prev (cadr lv) i (1+ i)))))
      (if (setq pt (sd:getpt "\n\\U+0110i\\U+1EC3m ch\\U+00E8n m\\U+1EB7t c\\U+1EAFt ngang \\U+0111\\U+00FAng t\\U+1EC9 l\\U+1EC7 (g\\U+1ED1c = cao \\U+0111\\U+1ED9 \\U+00B10.000) <b\\U+1ECF qua>: " nil))
        (sd:lc-section (sd:2d pt) m n (if wc (- n (* (/ iw 100.0) (/ (car wc) 1000.0)))) (if wc (car wc))
                       dk (if dkz (- dk (* (/ id 100.0) (/ (car dkz) 1000.0)))) (if dkz (car dkz)) wl ds bh sc))))
  (sd:finish))

;; Mat cat ngang dung ti le (1 don vi = 1 mm ca ngang lan dung): san chinh -> nguong -> san WC doc ve pheu; mep ho: thanh ho, day ho, san ho doc ra xa ho
;; m, n, nw = cao do san chinh / WC tai nguong / WC tai pheu (m); lw, ld = khoang xa nhat (mm); dk, dd = san ho tai mep / tai pheu (m)
(defun sd:lc-section (pt m n nw lw dk dd ld wl ds bh sc / lay x1 x2 xb fl wl2 lwd ldd)
  (setq lay (sd:make-layer "SD-CAODO-MC" 3 "Continuous" 25) lwd (cond (lw) (1500.0)) ldd (cond (ld) (1500.0))
        x1 1000.0 x2 (+ x1 lwd) xb (+ x2 1500.0 bh 300.0) fl (- wl (/ ds 1000.0)))
  (sd:text (sd:p+ pt 0 (+ (* 1000.0 m) (* 14.0 sc))) "M\\U+1EB6T C\\U+1EAET NGANG CAO \\U+0110\\U+1ED8 (\\U+0111\\U+00FAng t\\U+1EC9 l\\U+1EC7 1:1 theo mm, g\\U+1ED1c \\U+00B10.000)" (* 4.0 sc) "L" lay)
  ;; san chinh + nguong + san WC
  (sd:pline (list (sd:p+ pt 0 (* 1000.0 m)) (sd:p+ pt x1 (* 1000.0 m)) (sd:p+ pt x1 (* 1000.0 n)) (sd:p+ pt x2 (* 1000.0 (cond (nw) (n))))) nil lay)
  (sd:text (sd:p+ pt (/ x1 2.0) (+ (* 1000.0 m) (* 3.0 sc))) (strcat "S\\U+00C0N CH\\U+00CDNH " (sd:lc-rl m)) (* 2.5 sc) "MC" lay)
  (sd:text (sd:p+ pt (+ x1 (* 2.0 sc)) (- (* 1000.0 n) (* 5.0 sc))) (strcat "NG\\U+01AF\\U+1EE0NG WC " (sd:lc-rl n)) (* 2.5 sc) "L" lay)
  (if nw (sd:text (sd:p+ pt x2 (- (* 1000.0 nw) (* 6.0 sc))) (strcat "PH\\U+1EC4U THU WC " (sd:lc-rl nw)) (* 2.5 sc) "MR" lay))
  (sd:text (sd:p+ pt (+ x1 (* 2.0 sc)) (+ (* 1000.0 n) (* 4.0 sc))) (strcat "h\\U+1EA1 " (sd:rtos (* 1000.0 (- m n)) 0) " mm") (* 2.0 sc) "L" lay)
  ;; ho: san ho trai, thanh ho, day ho, thanh ho, san ho doc ra xa phia phai
  (setq wl2 (+ x2 1500.0))
  (sd:pline (list (sd:p+ pt wl2 (* 1000.0 dk)) (sd:p+ pt (+ wl2 300.0) (* 1000.0 dk)) (sd:p+ pt (+ wl2 300.0) (* 1000.0 fl))
                  (sd:p+ pt (+ wl2 300.0 bh) (* 1000.0 fl)) (sd:p+ pt (+ wl2 300.0 bh) (* 1000.0 dk))
                  (sd:p+ pt (+ wl2 300.0 bh ldd) (* 1000.0 (cond (dd) (dk))))) nil lay)
  (sd:line (sd:p+ pt (+ wl2 300.0) (* 1000.0 wl)) (sd:p+ pt (+ wl2 300.0 bh) (* 1000.0 wl)) lay)
  (sd:text (sd:p+ pt (+ wl2 300.0 (/ bh 2.0)) (+ (* 1000.0 wl) (* 2.0 sc))) (strcat "M\\U+1EF0C N\\U+01AF\\U+1EDAC " (sd:lc-rl wl)) (* 2.5 sc) "MC" lay)
  (sd:text (sd:p+ pt (+ wl2 300.0 (/ bh 2.0)) (- (* 1000.0 fl) (* 6.0 sc))) (strcat "\\U+0110\\U+00C1Y H\\U+1ED2 " (sd:lc-rl (- wl (/ ds 1000.0))) "  (s\\U+00E2u " (sd:num ds) ")") (* 2.5 sc) "MC" lay)
  (sd:text (sd:p+ pt wl2 (+ (* 1000.0 dk) (* 3.0 sc))) (strcat "S\\U+00C2N H\\U+1ED2 " (sd:lc-rl dk)) (* 2.5 sc) "L" lay)
  (if dd (sd:text (sd:p+ pt (+ wl2 300.0 bh ldd) (- (* 1000.0 dd) (* 6.0 sc))) (strcat "PH\\U+1EC4U / R\\U+00C3NH THU S\\U+00C2N " (sd:lc-rl dd)) (* 2.5 sc) "MR" lay))
  (princ "\n[SD] \\U+0110\\U+00E3 v\\U+1EBD m\\U+1EB7t c\\U+1EAFt ngang \\U+0111\\U+00FAng t\\U+1EC9 l\\U+1EC7 tr\\U+00EAn layer SD-CAODO-MC."))

;;; --------------------------------------------------------------------------
;;;  SDBACCAODO - Gan "du" cho cac cho doi cao do (nguong WC, mep ho, chan thanh): copy net sang layer SD-CAODO-BAC-<mm>, SDCATDU tu nhan
;;; --------------------------------------------------------------------------
(defun c:SDBACCAODO (/ ss i e dz kieu td kl mm lay ob ob2 n)
  (sd:begin)
  (princ "\nCh\\U+1ECDn c\\U+00E1c n\\U+00E9t (LINE / polyline) n\\U+1EB1m \\U+0111\\U+00FAng ch\\U+1ED7 \\U+0111\\U+1ED5i cao \\U+0111\\U+1ED9, vd m\\U+00E9p ng\\U+01B0\\U+1EE1ng WC, m\\U+00E9p h\\U+1ED3, ch\\U+00E2n th\\U+00E0nh: ")
  (if (setq ss (ssget '((0 . "LINE,LWPOLYLINE,POLYLINE,ARC"))))
    (if (sd:dlg "Ch\\U+1EEBa d\\U+01B0 t\\U+1EA1i ch\\U+1ED7 \\U+0111\\U+1ED5i cao \\U+0111\\U+1ED9 (SDBACCAODO)"
                (list (list "kieu" "Ki\\U+1EC3u x\\U+1EED l\\U+00FD ch\\U+1ED7 \\U+0111\\U+1ED5i cao \\U+0111\\U+1ED9" 'kw (sd:cfg "BC-KIEU" "Dung")
                            '(("Dung" . "\\U+0110\\U+00E1 d\\U+01B0\\U+1EDBi chui d\\U+01B0\\U+1EDBi \\U+0111\\U+00E1 \\U+0111\\U+1EE9ng (\\U+0111\\U+00E1 \\U+0111\\U+1EE9ng d\\U+1EF1ng sau): d\\U+01B0 = d\\U+00E0y \\U+0111\\U+00E1 \\U+0111\\U+1EE9ng + keo") ("Op" . "\\U+0110\\U+00E1 s\\U+00E0n \\U+1ED1p l\\U+00EAn m\\U+1EB7t \\U+0111\\U+1EE9ng: d\\U+01B0 = ch\\U+00EAnh cao + keo")))
                      (list "dz" "Ch\\U+00EAnh cao t\\U+1EA1i ch\\U+1ED7 n\\U+00E0y (mm; m\\U+1EB7c \\U+0111\\U+1ECBnh = h\\U+1EA1 c\\U+1ED1t WC c\\U+1EE7a SDLIENCAODO)" 'real0 (sd:cfg "BC-DZ" (sd:cfg "LC-BC" 20.0)))
                      (list "td" "D\\U+00E0y \\U+0111\\U+00E1 \\U+0111\\U+1EE9ng (mm; d\\U+00F9ng cho ki\\U+1EC3u \\U+0111\\U+00E1 \\U+0111\\U+1EE9ng)" 'real0 (sd:cfg "BC-TD" 20.0))
                      (list "kl" "Keo ch\\U+1EEBa th\\U+00EAm (mm)" 'real0 (sd:cfg "BC-KL" 10.0))))
      (progn
        (setq kieu (sd:cfg-put "BC-KIEU" (cond ((sd:v "kieu")) ("Dung"))) dz (sd:cfg-put "BC-DZ" (cond ((sd:v "dz")) (0.0)))
              td (sd:cfg-put "BC-TD" (cond ((sd:v "td")) (0.0))) kl (sd:cfg-put "BC-KL" (cond ((sd:v "kl")) (0.0)))
              mm (+ kl (if (= kieu "Op") dz td)))
        (sd:ho-warn '("BC-TD" "BC-KL" "LC-BC"))
        (if (<= mm 0.0)
          (princ "\n[SD] S\\U+1ED1 mm d\\U+01B0 b\\U+1EB1ng 0: kh\\U+00F4ng l\\U+00E0m g\\U+00EC.")
          (progn
            (setq lay (sd:make-layer (strcat "SD-CAODO-BAC-" (sd:num mm)) 6 "Continuous" 25) i 0 n 0)
            (repeat (sslength ss)
              (setq e (ssname ss i) i (1+ i)
                    ob (vlax-ename->vla-object e)
                    ob2 (vl-catch-all-apply 'vla-copy (list ob)))
              (if (not (vl-catch-all-error-p ob2))
                (progn (vla-put-layer ob2 lay) (setq n (1+ n)))))
            (princ (strcat "\n[SD] \\U+0110\\U+00E3 copy " (itoa n) " n\\U+00E9t sang layer " lay " (d\\U+01B0 " (sd:num mm) " mm). SDCATDU s\\U+1EBD t\\U+1EF1 ch\\U+1EEBa d\\U+01B0 c\\U+00E1c c\\U+1EA1nh vi\\U+00EAn s\\U+00E1t nh\\U+1EEFng n\\U+00E9t n\\U+00E0y.")))))))
  (sd:finish))

;;; --------------------------------------------------------------------------
;;;  SDMAP - Thu vien map (anh) da granite co san: chen anh tam da dung kich thuoc that de SDANHDA cat vao vien
;;;  Thu muc Maps canh ShopDrawing.lsp (17 map); tha them .jpg / .png vao do la co trong danh sach.
;;; --------------------------------------------------------------------------
;; Ten map -> khoa chon (khong dau cach: initget tach theo dau cach)
(defun sd:map-key (base) (vl-string-translate " " "_" base))
;; Thu muc map: SDMAPDIR (nho trong may) -> Maps canh ShopDrawing.lsp -> Maps canh ban ve; nil neu khong thay
(defun sd:map-dir (/ r d)
  (foreach p (append (list (getenv "SDMAPDIR"))
                     (mapcar '(lambda (x) (strcat (vl-string-right-trim "\\" x) "\\Maps"))
                             (append (list (cond ((findfile "ShopDrawing.lsp") (vl-filename-directory (findfile "ShopDrawing.lsp"))) ("")))
                                     (sd:split (cond ((getenv "ACAD")) ("")) ";")
                                     (list (cond ((getvar "DWGPREFIX")) (""))))))
    (if (and (null r) p (/= p "") (setq d (vl-string-right-trim "\\" p)) (vl-file-directory-p d)
             (or (vl-directory-files d "*.jpg" 1) (vl-directory-files d "*.png" 1)))
      (setq r d)))
  r)
;; Danh sach map trong thu muc: (khoa ten-hien-thi duong-dan-day-du), sap theo ten
(defun sd:map-list (dir / fs r b sz nm)
  (setq fs (append (vl-directory-files dir "*.jpg" 1) (vl-directory-files dir "*.jpeg" 1) (vl-directory-files dir "*.png" 1)))
  (foreach f (vl-sort fs '(lambda (a b) (< (strcase a) (strcase b))))
    (setq b (vl-filename-base f) sz (sd:map-size b)
          nm (vl-string-translate "-_" "  " (if sz (substr b 1 (vl-string-position (ascii "_") b 0 t)) b)))
    (setq r (cons (list (sd:map-key b) (if sz (strcat nm " (" (itoa (car sz)) " x " (itoa (cadr sz)) ")") nm) (strcat dir "\\" f) sz) r)))
  (reverse r))
;; Kho that ghi o cuoi ten file: Ten_3180x1920 -> (3180 1920); khong co -> nil
(defun sd:map-size (b / i p)
  (if (and (setq i (vl-string-position (ascii "_") b 0 t))
           (= (length (setq p (sd:split (strcase (substr b (+ i 2)) t) "x"))) 2)
           (> (atoi (car p)) 0) (> (atoi (cadr p)) 0))
    (list (atoi (car p)) (atoi (cadr p)))))
;; Chen mot anh file vao vi tri p, rong sw mm; tra ve doi tuong VLA hoac nil
(defun sd:map-put (file p sw / o)
  (if (not (vl-catch-all-error-p
             (setq o (vl-catch-all-apply 'vla-AddRaster (list (sd:ms) file (vlax-3d-point (car p) (cadr p) 0.0) 1.0 0.0)))))
    (progn
      (vla-ScaleEntity o (vlax-3d-point (car p) (cadr p) 0.0) (/ sw (vla-get-Width o)))
      (vla-put-Layer o "SD-MAP")
      o)))

(defun c:SDMAP (/ dir ls ch pick sw n gap p x o k nok fn w r)
  (sd:begin)
  (setq dir (sd:map-dir))
  (if (null dir)
    (progn
      (princ "\n[SD] Ch\\U+01B0a th\\U+1EA5y th\\U+01B0 m\\U+1EE5c Maps. Ch\\U+1ECDn m\\U+1ED9t \\U+1EA3nh b\\U+1EA5t k\\U+1EF3 trong th\\U+01B0 m\\U+1EE5c map (VD th\\U+01B0 m\\U+1EE5c ShopDrawing\\Maps).")
      (if (setq fn (getfiled "Ch\\U+1ECDn m\\U+1ED9t \\U+1EA3nh trong th\\U+01B0 m\\U+1EE5c map" "" "jpg;png" 4))
        (progn (setq dir (vl-filename-directory fn)) (setenv "SDMAPDIR" dir)))))
  (setq ls (if dir (sd:map-list dir)))
  (cond
    ((null ls) (princ "\n[SD] Th\\U+01B0 m\\U+1EE5c map tr\\U+1ED1ng: ch\\U+00E9p c\\U+00E1c file .jpg / .png v\\U+00E0o \\U+0111\\U+00F3 (\\U+0111\\U+1EB7t t\\U+00EAn kh\\U+00F4ng d\\U+1EA5u) r\\U+1ED3i ch\\U+1EA1y l\\U+1EA1i SDMAP."))
    (t
     (setq ch (cons (cons "Tatca" "T\\U+1EA5t c\\U+1EA3 map, m\\U+1ED7i map m\\U+1ED9t t\\U+1EA5m (nhi\\U+1EC1u v\\U+00E2n kh\\U+00E1c nhau cho SDANHDA)")
                    (mapcar '(lambda (r) (cons (car r) (cadr r))) ls)))
     (if (sd:dlg (strcat "Ch\\U+00E8n map \\U+0111\\U+00E1 c\\U+00F3 s\\U+1EB5n (SDMAP) - " (itoa (length ls)) " map")
                 (list (list "map" "Ch\\U+1ECDn map" 'kw (cond ((vl-position (sd:cfg "MAP-LAST" "") (mapcar 'car ch)) (sd:cfg "MAP-LAST" "")) ("Tatca")) ch)
                       (list "sw" "Chi\\U+1EC1u d\\U+00E0i th\\U+1EADt c\\U+1EE7a t\\U+1EA5m \\U+0111\\U+00E1 (mm); 0 = theo kh\\U+1ED5 ghi trong t\\U+00EAn file (VD _3180x1920), kh\\U+00F4ng c\\U+00F3 th\\U+00EC 3000; chi\\U+1EC1u r\\U+1ED9ng theo t\\U+1EC9 l\\U+1EC7 \\U+1EA3nh" 'real0 (sd:cfg "MAP-SW" 0.0))
                       (list "so" "S\\U+1ED1 t\\U+1EA5m ch\\U+00E8n (ch\\U+1ECDn 1 map; m\\U+1ED7i t\\U+1EA5m c\\U+00F9ng v\\U+00E2n)" 'int (sd:cfg "MAP-SO" 1) nil '("map" "Tatca"))
                       (list "gap" "Kho\\U+1EA3ng c\\U+00E1ch gi\\U+1EEFa c\\U+00E1c t\\U+1EA5m (mm)" 'real0 (sd:cfg "MAP-GAP" 200.0))))
       (progn
         (setq pick (sd:cfg-put "MAP-LAST" (sd:v "map")) sw (sd:cfg-put "MAP-SW" (sd:v "sw"))
               n (sd:cfg-put "MAP-SO" (cond ((sd:v "so")) (1))) gap (sd:cfg-put "MAP-GAP" (cond ((sd:v "gap")) (0.0))))
         (if (setq p (sd:getpt "\n\\U+0110i\\U+1EC3m ch\\U+00E8n g\\U+00F3c tr\\U+00E1i d\\U+01B0\\U+1EDBi c\\U+1EE7a t\\U+1EA5m \\U+0111\\U+1EA7u: " nil))
           (progn
             (sd:make-layer "SD-MAP" 8 "Continuous" 13)
             (setq x (car p) nok 0 k nil)
             (if (= pick "Tatca")
               (setq k ls)
               (repeat n (setq k (cons (assoc pick ls) k))))
             (foreach r k
               (setq w (cond ((> sw 0.0) sw) ((car (cadddr r))) (3000.0)))
               (if (setq o (sd:map-put (caddr r) (list x (cadr p)) w))
                 (progn (setq nok (1+ nok) x (+ x w gap)))
                 (princ (strcat "\n[SD] Kh\\U+00F4ng ch\\U+00E8n \\U+0111\\U+01B0\\U+1EE3c \\U+1EA3nh " (caddr r) " (\\U+0111\\U+1ECBnh d\\U+1EA1ng \\U+1EA3nh kh\\U+00F4ng h\\U+1EE3p l\\U+1EC7?)."))))
             (princ (strcat "\n[SD] \\U+0110\\U+00E3 ch\\U+00E8n " (itoa nok) " t\\U+1EA5m map (layer SD-MAP)."
                            "\n[SD] Ti\\U+1EBFp: SDANHDA > ch\\U+1ECDn c\\U+00E1c \\U+1EA3nh v\\U+1EEBa ch\\U+00E8n (b\\U+1EADt 'L\\U+1EA5y k\\U+00EDch th\\U+01B0\\U+1EDBc t\\U+1EA5m t\\U+1EEB \\U+1EA3nh') > qu\\U+00E9t c\\U+00E1c vi\\U+00EAn."
                            "\n[SD] Th\\U+00EAm map c\\U+1EE7a b\\U+1EA1n: ch\\U+00E9p file .jpg / .png v\\U+00E0o " dir "."))))))))
  (sd:finish))

;;; --------------------------------------------------------------------------
;;;  SDDICHVAN - Dich van da tung buoc: nhich anh tam da duoi bien vien (trai / phai / len / xuong, buoc mm), bien vien dung yen, cat lai anh sau moi buoc
;;; --------------------------------------------------------------------------
;; Cat lai anh im theo da giac pts (xoa clip cu, tao clip da giac moi)

(defun sd:dv-clip (im pts / os)
  ;; tat OSNAP khi nhap toa do bang (command): net bat diem dang chay co the keo dinh polygon cat sang vien ke
  (setq os (getvar "OSMODE")) (setvar "OSMODE" 0)
  (command "_.IMAGECLIP" im "_D")
  (command "_.IMAGECLIP" im "_N" "_P")
  (foreach q pts (command (trans (list (car q) (cadr q) 0.0) 0 1)))
  (command "")
  (setq *SD:IMCLIPS* nil)
  (setvar "OSMODE" os))

;; Dich anh im them d = (dx dy) neu da giac pts van nam tron trong anh (chua le m); tra ve T neu da dich va cat lai
(defun sd:dv-try (im pts d m / g g2 f)
  (setq g (sd:im-geom im)
        g2 (list (list (+ (car (car g)) (car d)) (+ (cadr (car g)) (cadr d))) (cadr g) (caddr g) (cadddr g))
        f (sd:im-fit g2 pts m))
  (if (and f (< (distance '(0.0 0.0) f) 1e-6))
    (progn
      (vla-Move (vlax-ename->vla-object im) (vlax-3d-point 0.0 0.0 0.0) (vlax-3d-point (car d) (cadr d) 0.0))
      (sd:dv-clip im pts)
      t)))


(defun sd:dv-clip-new (im pts / os)
  (setq os (getvar "OSMODE")) (setvar "OSMODE" 0)
  (command "_.IMAGECLIP" im "_N" "_P")
  (foreach q pts (command (trans (list (car q) (cadr q) 0.0) 0 1)))
  (command "")
  (setq *SD:IMCLIPS* nil)
  (setvar "OSMODE" os))

;; Tong dich chuyen d = (dx dy) so voi anh goc g0 sau khi ep cho da giac pts nam tron trong anh (chua le m); nil neu da giac lon hon anh
(defun sd:dv-clamp (g0 pts d m / g2 f)
  (setq g2 (list (list (+ (car (car g0)) (car d)) (+ (cadr (car g0)) (cadr d))) (cadr g0) (caddr g0) (cadddr g0))
        f (sd:im-fit g2 pts m))
  (if f (list (+ (car d) (car f)) (+ (cadr d) (cadr f)))))

;; Ve vien da giac pts bang net sang tam thoi (grdraw) de thay vien dung yen khi keo anh
(defun sd:dv-outline (pts / a)
  (setq a (last pts))
  (foreach b pts (grdraw (list (car a) (cadr a)) (list (car b) (cadr b)) 1 1) (setq a b)))

;; Vong keo: anh bo clip, hien ca tam da mo di, vien dung yen; chuot / phim mui ten dich anh (ep cho vien luon nam trong anh)
;; Click trai / Enter / Space = chap nhan, Esc / chuot phai = huy. *SD:DVAP* luon ghi tong dich dang ap dung (de khoi phuc khi loi)
(defun sd:dv-drag-run (ob pts m step g0 base / done gr kind pt key d tgt lastpt)
  (setq lastpt base)
  (while (not done)
    (setq gr (grread T 15 0) kind (car gr) d nil)
    (cond
      ((= kind 5) (setq pt (trans (cadr gr) 1 0) lastpt pt d (list (- (car pt) (car base)) (- (cadr pt) (cadr base)))))
      ((= kind 3) (setq done 'ok))
      ((member kind '(25 11)) (setq done 'cancel))
      ((= kind 2)
       (setq key (cadr gr))
       (cond ((member key '(13 32)) (setq done 'ok))
             ((= key 27) (setq done 'cancel))
             ((= key 331) (setq d (list (- (car *SD:DVAP*) step) (cadr *SD:DVAP*))))
             ((= key 333) (setq d (list (+ (car *SD:DVAP*) step) (cadr *SD:DVAP*))))
             ((= key 328) (setq d (list (car *SD:DVAP*) (+ (cadr *SD:DVAP*) step))))
             ((= key 336) (setq d (list (car *SD:DVAP*) (- (cadr *SD:DVAP*) step))))
             (t nil))
       ;; sau phim mui ten, dich chuot tiep tuc tu vi tri hien tai
       (if d (setq base (list (- (car lastpt) (car d)) (- (cadr lastpt) (cadr d)))))))
    (if (and d (null done) (setq tgt (sd:dv-clamp g0 pts d m)))
      (progn
        (vla-Move ob (vlax-3d-point 0.0 0.0 0.0)
                  (vlax-3d-point (- (car tgt) (car *SD:DVAP*)) (- (cadr tgt) (cadr *SD:DVAP*)) 0.0))
        (setq *SD:DVAP* tgt)
        (sd:dv-outline pts))))
  done)

;; Keo van tu do: tra ve tong dich (dx dy) neu chap nhan va co dich, nil neu huy / khong dich
(defun sd:dv-drag (im pts m step / ob g0 base fade st r ap)
  (setq ob (vlax-ename->vla-object im) g0 (sd:im-geom im) *SD:DVAP* (list 0.0 0.0))
  (if (setq base (getpoint "\nCh\\U+1ECDn \\U+0111i\\U+1EC3m g\\U+1ED1c \\U+0111\\U+1EC3 k\\U+00E9o v\\U+00E2n (r\\U+1ED3i k\\U+00E9o chu\\U+1ED9t / ph\\U+00EDm m\\U+0169i t\\U+00EAn, Enter ho\\U+1EB7c click = ch\\U+1EA5p nh\\U+1EADn, Esc = h\\U+1EE7y): "))
    (progn
      (setq base (list (car base) (cadr base)) fade (vl-catch-all-apply 'vla-get-Fade (list ob)))
      (if (vl-catch-all-error-p fade) (setq fade nil))
      (command "_.IMAGECLIP" im "_D")
      (if fade (vl-catch-all-apply 'vla-put-Fade (list ob 50)))
      (setq r (vl-catch-all-apply 'sd:dv-drag-run (list ob pts m step g0 base)))
      (if (vl-catch-all-error-p r) (setq st 'cancel) (setq st r))
      (redraw)
      (if (= st 'cancel)
        (progn (vla-Move ob (vlax-3d-point 0.0 0.0 0.0) (vlax-3d-point (- (car *SD:DVAP*)) (- (cadr *SD:DVAP*)) 0.0))
               (setq *SD:DVAP* (list 0.0 0.0))))
      (if fade (vl-catch-all-apply 'vla-put-Fade (list ob fade)))
      (sd:dv-clip-new im pts)
      (setq ap *SD:DVAP*)
      (if (and (= st 'ok) (> (distance '(0.0 0.0) ap) 1e-6)) ap))
    (progn (command "_.IMAGECLIP" im "_D") (sd:dv-clip-new im pts) nil)))

;; Tam xoay vien = tam khung bao cua da giac pts
(defun sd:dv-ctr (pts / xs ys)
  (setq xs (mapcar 'car pts) ys (mapcar 'cadr pts))
  (list (/ (+ (apply 'min xs) (apply 'max xs)) 2.0) (/ (+ (apply 'min ys) (apply 'max ys)) 2.0) 0.0))

;; Xoay anh im goc t (rad, +: nguoc chieu kim dong ho) quanh tam vien, roi dich nhe de vien van nam tron trong anh (chua le m); cat lai clip
;; Tra ve (fx fy t) de hoan; nil neu vien se vuot ra ngoai anh (khong xoay)

;; Cong goc xoay anh vao SD_ANH (goc anh so voi canh dai vien): neu khong, SDTUDONG / SDMOANH / SDRON se xoay anh tro lai huong cu
(defun sd:dv-adddelta (im d / xd)
  (setq xd (mapcar 'cdr (cdadr (assoc -3 (entget im '("SD_ANH"))))))
  (if (and (>= (length xd) 3) (< (abs (nth 2 xd)) 50.0))
    (vl-catch-all-apply 'sd:put-xd
      (list im (list -3 (list "SD_ANH" (cons 1040 (car xd)) (cons 1040 (cadr xd))
                              (cons 1040 (rem (+ (nth 2 xd) d (* 4.0 pi)) (* 2.0 pi)))))))))

(defun sd:dv-rot (im pts t0 m / g c o2 g2 f ob lp)
  (setq g (sd:im-geom im) c (sd:dv-ctr pts) ob (vlax-ename->vla-object im)
        o2 (mapcar '+ c (sd:rot (list (- (car (car g)) (car c)) (- (cadr (car g)) (cadr c))) t0))
        g2 (list o2 (+ (cadr g) t0) (caddr g) (cadddr g))
        f (sd:im-fit g2 pts m))
  (if f
    (progn
      (vla-Rotate ob (vlax-3d-point (car c) (cadr c) 0.0) t0)
      (vla-Move ob (vlax-3d-point 0.0 0.0 0.0) (vlax-3d-point (car f) (cadr f) 0.0))
      (sd:dv-clip im pts)
      (sd:dv-adddelta im t0)
      (list (car f) (cadr f) t0))
    (progn
      (setq lp (mapcar '(lambda (q) (sd:w2l o2 (cadr g2) q)) pts))
      (princ (strcat "\n[SD] Khong xoay duoc " (sd:rtos (* 180.0 (/ t0 pi)) 1) " do: vien can khung "
                     (sd:rtos (- (apply 'max (mapcar 'car lp)) (apply 'min (mapcar 'car lp))) 0) " x "
                     (sd:rtos (- (apply 'max (mapcar 'cadr lp)) (apply 'min (mapcar 'cadr lp))) 0)
                     " mm trong anh, nhung tam anh chi " (sd:rtos (caddr g) 0) " x " (sd:rtos (cadddr g) 0) " mm."))
      nil)))

;; Hoan 1 buoc xoay (fx fy t)

(defun sd:dv-unrot (im pts h / ob c)
  (setq ob (vlax-ename->vla-object im) c (sd:dv-ctr pts))
  (vla-Move ob (vlax-3d-point 0.0 0.0 0.0) (vlax-3d-point (- (car h)) (- (cadr h)) 0.0))
  (vla-Rotate ob (vlax-3d-point (car c) (cadr c) 0.0) (- (caddr h)))
  (sd:dv-clip im pts)
  (sd:dv-adddelta im (- (caddr h)))
  t)

(defun c:SDDICHVAN (/ buoc goc m r e pts ims im kw hist d n)
  (sd:begin)
  (if (sd:dlg "D\\U+1ECBch v\\U+00E2n \\U+0111\\U+00E1 t\\U+1EEBng b\\U+01B0\\U+1EDBc (SDDICHVAN)"
              (list (list "buoc" "B\\U+01B0\\U+1EDBc d\\U+1ECBch m\\U+1ED7i l\\U+1EA7n (mm)" 'real (sd:cfg "DV-BUOC" 10.0))
                    (list "goc" "G\\U+00F3c xoay v\\U+00E2n m\\U+1ED7i l\\U+1EA7n (\\U+0111\\U+1ED9), d\\U+00F9ng cho QT / QP" 'real (sd:cfg "DV-GOC" 5.0))
                    (list "m" "Ch\\U+1EEBa l\\U+1EC1 an to\\U+00E0n m\\U+1ED7i c\\U+1EA1nh (mm)" 'real0 (sd:cfg "MOANH-M" 10.0))))
    (progn
      (setq buoc (sd:cfg-put "DV-BUOC" (sd:v "buoc")) goc (sd:cfg-put "DV-GOC" (sd:v "goc")) m (cond ((sd:v "m")) (0.0))
            ims (ssget "_X" '((0 . "IMAGE") (-3 ("SD_ANH")))))
      (while (setq r (entsel "\nCh\\U+1ECDn vi\\U+00EAn c\\U+1EA7n d\\U+1ECBch v\\U+00E2n <Enter = xong>: "))
        (setq e (car r))
        (if (not (member (cdr (assoc 0 (entget e))) '("LWPOLYLINE" "IMAGE")))
          (princ "\n[SD] C\\U+1EA7n ch\\U+1ECDn polyline vi\\U+00EAn.")
          (progn
            (if (= (cdr (assoc 0 (entget e))) "IMAGE")
              (setq pts (sd:im-clip-pts e) im (if pts e))
              (setq pts (sd:curve-pts e) im (sd:im-find pts ims)))
            (setq hist nil n 0)
            (if (and (null im) (setq r (entsel "\nKh\\U+00F4ng t\\U+1EF1 gh\\U+00E9p \\U+0111\\U+01B0\\U+1EE3c \\U+1EA3nh. Ch\\U+1ECDn \\U+1EA3nh c\\U+1EE7a vi\\U+00EAn n\\U+00E0y <b\\U+1ECF qua>: ")))
              (if (= (cdr (assoc 0 (entget (car r)))) "IMAGE") (setq im (sd:im-adopt (car r) pts))))
            (if (null im)
              (princ "\n[SD] Kh\\U+00F4ng c\\U+00F3 \\U+1EA3nh \\U+0111\\U+1EC3 d\\U+1ECBch.")
              (progn
                (setq kw "")
                (while kw
                  (initget "Trai Phai Len Xuong Keo QT QP Xoay Hoan Buoc Goc Xong")
                  (setq kw (getkword (strcat "\nD\\U+1ECBch v\\U+00E2n " (sd:num buoc) " mm / " (sd:num goc) "\\U+00B0 [Trai/Phai/Len/Xuong/Keo/QT=quay tr\\U+00E1i/QP=quay ph\\U+1EA3i/Xoay=nhap goc/Hoan/Buoc/Goc/Xong] <Xong>: ")))
                  (cond
                    ((or (null kw) (= kw "Xong")) (setq kw nil))
                    ((= kw "Buoc")
                     (setq buoc (cond ((getdist (strcat "\nB\\U+01B0\\U+1EDBc d\\U+1ECBch (mm) <" (sd:num buoc) ">: "))) (buoc)))
                     (sd:cfg-put "DV-BUOC" buoc))
                    ((= kw "Goc")
                     (setq goc (cond ((getreal (strcat "\nG\\U+00F3c xoay m\\U+1ED7i l\\U+1EA7n (\\U+0111\\U+1ED9) <" (sd:num goc) ">: "))) (goc)))
                     (sd:cfg-put "DV-GOC" goc))
                    ((= kw "Xoay")
                     (if (setq d (getreal "\nGoc xoay van (do; duong = nguoc chieu kim dong ho, am = cung chieu): "))
                       (if (setq d (sd:dv-rot im pts (/ (* d pi) 180.0) m))
                         (setq hist (cons d hist)))))
                    ((member kw '("QT" "QP"))
                     (if (setq d (sd:dv-rot im pts (* (if (= kw "QT") 1.0 -1.0) (/ (* goc pi) 180.0)) m))
                       (setq hist (cons d hist))
                       (princ "\n[SD] Xoay th\\U+00EAm th\\U+00EC vi\\U+00EAn v\\U+01B0\\U+1EE3t ra ngo\\U+00E0i t\\U+1EA5m \\U+1EA3nh: kh\\U+00F4ng xoay. Th\\U+1EED g\\U+00F3c nh\\U+1ECF h\\U+01A1n ho\\U+1EB7c xoay chi\\U+1EC1u ng\\U+01B0\\U+1EE3c l\\U+1EA1i.")))
                    ((= kw "Keo")
                     (if (setq d (sd:dv-drag im pts m buoc))
                       (setq hist (cons d hist))
                       (princ "\n[SD] Kh\\U+00F4ng d\\U+1ECBch (\\U+0111\\U+00E3 h\\U+1EE7y ho\\U+1EB7c ch\\U+01B0a k\\U+00E9o).")))
                    ((= kw "Hoan")
                     (cond ((null hist) (princ "\n[SD] Kh\\U+00F4ng c\\U+00F2n b\\U+01B0\\U+1EDBc \\U+0111\\U+1EC3 ho\\U+00E0n."))
                           ((= (length (car hist)) 3) (sd:dv-unrot im pts (car hist)) (setq hist (cdr hist)))
                           ((sd:dv-try im pts (list (- (car (car hist))) (- (cadr (car hist)))) m) (setq hist (cdr hist)))
                           (t (princ "\n[SD] Kh\\U+00F4ng ho\\U+00E0n \\U+0111\\U+01B0\\U+1EE3c b\\U+01B0\\U+1EDBc n\\U+00E0y."))))
                    (t
                     (setq d (cond ((= kw "Trai") (list (- buoc) 0.0)) ((= kw "Phai") (list buoc 0.0)) ((= kw "Len") (list 0.0 buoc)) (t (list 0.0 (- buoc)))))
                     (if (sd:dv-try im pts d m)
                       (setq hist (cons d hist))
                       (princ "\n[SD] H\\U+1EBFt kh\\U+1ED5 v\\U+1EC1 ph\\U+00EDa \\U+0111\\U+00F3 (c\\U+00F2n l\\U+1EC1 an to\\U+00E0n): kh\\U+00F4ng d\\U+1ECBch th\\U+00EAm \\U+0111\\U+01B0\\U+1EE3c. Th\\U+1EED h\\U+01B0\\U+1EDBng kh\\U+00E1c ho\\U+1EB7c b\\U+01B0\\U+1EDBc nh\\U+1ECF h\\U+01A1n.")))))
                (princ (strcat "\n[SD] T\\U+1ED5ng \\U+0111\\U+00E3 d\\U+1ECBch v\\U+00E2n: X " (sd:rtos (apply '+ (cons 0.0 (mapcar 'car (vl-remove-if-not '(lambda (h) (= (length h) 2)) hist)))) 1) " mm, Y "
                               (sd:rtos (apply '+ (cons 0.0 (mapcar 'cadr (vl-remove-if-not '(lambda (h) (= (length h) 2)) hist)))) 1) " mm (Ph\\U+1EA3i / L\\U+00EAn l\\U+00E0 d\\U+01B0\\U+01A1ng), xoay "
                               (sd:rtos (/ (* 180.0 (apply '+ (cons 0.0 (mapcar 'caddr (vl-remove-if-not '(lambda (h) (= (length h) 3)) hist))))) pi) 1) "\\U+00B0 (tr\\U+00E1i l\\U+00E0 d\\U+01B0\\U+01A1ng).")))))))))
  (sd:finish))

;;; --------------------------------------------------------------------------
;;;  SDLOP - Chi tiet cau tao lop op / lat (san hoac tuong)
;;; --------------------------------------------------------------------------
(defun sd:parse-layers (s / r tok p)
  (foreach tok (sd:split s ";")
    (setq tok (vl-string-trim " " tok))
    (if (and (/= tok "") (setq p (vl-string-position (ascii " ") tok nil t))
             (> (atof (substr tok (+ p 2))) 0))
      (setq r (cons (list tok (atof (substr tok (+ p 2)))) r))))
  (reverse r))

(defun c:SDLOP (/ ts ori lays L o n x y mids bnd i tl yl xl r)
  (sd:begin)
  (setq ts (float *SD:DETSCALE*))
  (if (not (sd:dlg "Cau tao lop op / lat (SDLOP)"
                   (list (list "ori" "Cau tao" 'kw "San" '(("San" . "San") ("Tuong" . "Tuong")))
                         (list "note" "Cac lop tu mat hoan thien vao, cach nhau ; - so cuoi moi lop la chieu day (mm)" 'note nil)
                         (list "lop" "Cac lop" 'str (cond (*SD:LOP*) ("Da granite day 20;Vua xi mang M75 day 30;San BTCT 150")))
                         (list "L" "Chieu dai doan the hien (mm)" 'real 600.0))))
    (exit))
  (setq ori (sd:v "ori") *SD:LOP* (sd:v "lop") lays (sd:parse-layers *SD:LOP*) L (sd:v "L"))
  (if (and lays (setq o (sd:getpt (if (= ori "San") "\nDiem chen (goc trai mat hoan thien): "
                                      "\nDiem chen (chan mat hoan thien): ") nil)))
    (progn
      (setq n (length lays) i 0 tl (* ts (max 40.0 (apply 'max (mapcar '(lambda (x) (* 1.6 (strlen (car x)))) lays)))))
      (sd:use-dimstyle ts)
      (if (= ori "San")
        (progn
          ;; cac lop xep tu tren xuong
          (setq y 0.0 bnd (list (sd:p+ o 0 0)))
          (foreach ly lays
            (sd:rect (sd:p+ o 0 (- y (cadr ly))) L (cadr ly) "SD-OP-LOP")
            (setq mids (cons (- y (/ (cadr ly) 2.0)) mids)
                  y (- y (cadr ly))
                  bnd (cons (sd:p+ o 0 y) bnd)))
          (setq mids (reverse mids) xl (* 0.7 L))
          (sd:dimchain (reverse bnd) "V" (sd:p+ o (* -8 ts) 0))
          ;; duong dan dung + danh sach ghi chu (lop tren cung ghi tren cung)
          (sd:line (sd:p+ o xl (last mids)) (sd:p+ o xl (+ (* 6 ts) (* 5 ts (1- n)))) "SD-KYHIEU")
          (foreach ly lays
            (setq yl (+ (* 6 ts) (* 5 ts (- n 1 i))))
            (sd:dot (sd:p+ o xl (nth i mids)) ts "SD-KYHIEU")
            (sd:line (sd:p+ o xl yl) (sd:p+ o (+ xl tl) yl) "SD-KYHIEU")
            (sd:text (sd:p+ o (+ xl ts) (+ yl (* 0.8 ts))) (car ly) (* 2.5 ts) "L" "SD-CHU")
            (setq i (1+ i))))
        (progn
          ;; tuong: mat hoan thien ben trai, cac lop xep sang phai
          (setq x 0.0 bnd (list (sd:p+ o 0 0)))
          (foreach ly lays
            (sd:rect (sd:p+ o x 0) (cadr ly) L "SD-OP-LOP")
            (setq mids (cons (+ x (/ (cadr ly) 2.0)) mids)
                  x (+ x (cadr ly))
                  bnd (cons (sd:p+ o x 0) bnd)))
          (setq mids (reverse mids) yl (* 0.7 L) xl (* -10 ts))
          (sd:dimchain (reverse bnd) "H" (sd:p+ o 0 (* -8 ts)))
          (sd:line (sd:p+ o (last mids) yl) (sd:p+ o xl yl) "SD-KYHIEU")
          (sd:line (sd:p+ o xl yl) (sd:p+ o xl (+ yl (* 5 ts n))) "SD-KYHIEU")
          (foreach ly lays
            (setq r (+ yl (* 5 ts (- n i))))
            (sd:dot (sd:p+ o (nth i mids) yl) ts "SD-KYHIEU")
            (sd:line (sd:p+ o xl r) (sd:p+ o (- xl tl) r) "SD-KYHIEU")
            (sd:text (sd:p+ o (- xl ts) (+ r (* 0.8 ts))) (car ly) (* 2.5 ts) "R" "SD-CHU")
            (setq i (1+ i)))))
      (sd:use-dimstyle *SD:SCALE*)))
  (if (null lays) (princ "\n[SD] Khong doc duoc lop nao. Vi du: Da granite 20;Vua XM 30;San BTCT 150"))
  (sd:finish))

;;; --------------------------------------------------------------------------
;;;  SDCHANTUONG - Len chan tuong: chia vien doc theo tuong, tru lo cua
;;; --------------------------------------------------------------------------
(defun sd:subtract (a b doors / res cur)
  (setq cur a)
  (foreach d doors
    (if (and (< (car d) b) (> (cadr d) cur))
      (progn
        (if (> (car d) cur) (setq res (cons (list cur (car d)) res)))
        (setq cur (max cur (cadr d))))))
  (if (< cur b) (setq res (cons (list cur b) res)))
  (reverse res))

(defun c:SDCHANTUONG (/ sc es e mat name lc hc tk jt doors p1 p2 d1 d2 pts segs closed side
                        dacc p q len fa nv a b pcs poly n tot rc elev bnds vinfo ep i r yt)
  (sd:begin)
  (setq sc (sd:sc))
  (setq es (entsel "\nChon duong mat tuong (polyline, kin hoac ho): "))
  (if (not (and es (= (cdr (assoc 0 (entget (car es)))) "LWPOLYLINE")))
    (princ "\n[SD] Can chon 1 polyline the hien mat tuong.")
    (progn
      (setq e (car es) closed (vlax-curve-isClosed e) pts (sd:curve-pts e))
      (if (not (sd:dlg "Len chan tuong (SDCHANTUONG)"
                       (list (list "mat" "Ma len chan tuong" 'str (cond (*SD:LCODE*) ("L1")))
                             (list "name" "Ten vat lieu" 'str (cond (*SD:LNAME*) ("Len granite")))
                             (list "lc" "Chieu dai 1 vien len (mm)" 'real (cond (*SD:LLC*) (600.0)))
                             (list "hc" "Chieu cao len (mm)" 'real (cond (*SD:LHC*) (120.0)))
                             (list "tk" "Chieu day len (mm)" 'real (cond (*SD:LTK*) (18.0)))
                             (list "jt" "Mach giua cac vien (mm)" 'real0 1.0)
                             (list "elev" "Ve trien khai mat dung" 'tog t))))
        (exit))
      (setq mat (sd:v "mat") name (sd:v "name") lc (sd:v "lc") hc (sd:v "hc") tk (sd:v "tk") jt (sd:v "jt"))
      (setq *SD:LCODE* mat *SD:LNAME* name *SD:LLC* lc *SD:LHC* hc *SD:LTK* tk)
      ;; phia trong phong
      (if closed
        (setq side (if (> (sd:area pts) 0) 1.0 -1.0))
        (if (setq p (sd:getpt "\nChon 1 diem phia trong phong: " nil))
          (setq side (if (> (- (* (- (car (cadr pts)) (car (car pts))) (- (cadr p) (cadr (car pts))))
                               (* (- (cadr (cadr pts)) (cadr (car pts))) (- (car p) (car (car pts)))))
                            0) 1.0 -1.0))
          (setq side 1.0)))
      ;; lo cua
      (while (and (setq p1 (sd:getpt "\nDiem dau lo cua tren duong tuong <Enter = het>: " nil))
                  (setq p2 (sd:getpt "\nDiem cuoi lo cua: " p1)))
        (setq d1 (vlax-curve-getDistAtPoint e (vlax-curve-getClosestPointTo e p1))
              d2 (vlax-curve-getDistAtPoint e (vlax-curve-getClosestPointTo e p2))
              doors (cons (list (min d1 d2) (max d1 d2)) doors)))
      (setq doors (sd:sort doors '(lambda (x y) (< (car x) (car y))))
            segs  (mapcar 'list pts (if closed (append (cdr pts) (list (car pts))) (cdr pts))))
      (setq dacc 0.0 tot 0.0)
      (foreach s segs
        (setq p (car s) q (cadr s) len (distance p q) fa (angle p q)
              nv (+ fa (* side (/ pi 2)))
              bnds (cons dacc bnds)
              vinfo (cons (list p fa nv) vinfo))
        (foreach iv (sd:subtract dacc (+ dacc len) doors)
          (setq a (- (car iv) dacc))
          (while (< a (- (cadr iv) dacc 1.0))
            (setq b (min (+ a lc) (- (cadr iv) dacc))
                  poly (list (polar p fa a) (polar p fa b) (polar (polar p fa b) nv tk) (polar (polar p fa a) nv tk))
                  poly (mapcar 'sd:2d poly))
            (sd:pline poly t "SD-LEN-CHAN")
            (setq pcs (cons (list (list (entlast)) (- b a) hc (* (- b a) hc)
                                  (if (equal (- b a) lc 0.5) "F" "C")
                                  (sd:centroid poly) (list a 0.0) (sd:2d p) fa)
                            pcs)
                  tot (+ tot (- b a))
                  elev (cons (list (+ dacc a) (+ dacc b) (entlast)) elev)
                  a (+ b jt))))
        (setq dacc (+ dacc len)))
      (setq rc (sd:code-pieces pcs mat name lc hc tk nil sc))
      ;; ---- trien khai mat dung (tuong duoc trai phang theo thu tu canh)
      (setq bnds (reverse (cons dacc bnds)) vinfo (reverse vinfo) r (* 2.5 sc) yt (+ hc (* 12 sc)))
      (if (and (sd:v "elev")
               (setq ep (sd:getpt "\nDiem chen mat dung (dau tuong, cao do san): " nil)))
        (progn
          (sd:line ep (sd:p+ ep dacc 0) "SD-BANG")
          (foreach v elev
            (sd:rect (sd:p+ ep (car v) 0) (- (cadr v) (car v)) hc "SD-LEN-CHAN")
            (sd:text (sd:p+ ep (/ (+ (car v) (cadr v)) 2) (/ hc 2))
                     (nth 2 (mapcar 'cdr (cdadr (assoc -3 (entget (caddr v) '("SD_TILE"))))))
                     (min (* 2.0 sc) (* 0.35 hc) (* 0.3 (- (cadr v) (car v)))) "MC" "SD-CHU"))
          ;; lo cua
          (foreach d doors
            (sd:line (sd:p+ ep (car d) 0) (sd:p+ ep (car d) (* 3 hc)) "SD-KHUAT")
            (sd:line (sd:p+ ep (cadr d) 0) (sd:p+ ep (cadr d) (* 3 hc)) "SD-KHUAT")
            (sd:text (sd:p+ ep (/ (+ (car d) (cadr d)) 2) (* 1.5 hc)) "C\\U+1EECA" (* 2.5 sc) "MC" "SD-CHU"))
          ;; goc tuong: duong truc tren mat dung + so goc, danh so tuong ung tren mat bang
          (setq i 0)
          (foreach x bnds
            (sd:line (sd:p+ ep x 0) (sd:p+ ep x (- yt r)) "SD-TRUC")
            (sd:bubble (sd:p+ ep x yt) r (itoa (1+ (rem i (length pts)))))
            (if (nth i vinfo)
              (sd:bubble (polar (polar (car (nth i vinfo)) (caddr (nth i vinfo)) (* 6 sc))
                                (cadr (nth i vinfo)) (* 6 sc))
                         r (itoa (1+ i))))
            (setq i (1+ i)))
          (if (and (not closed) (last pts) (> (length bnds) (length vinfo)))
            (sd:bubble (polar (last pts) (caddr (last vinfo)) (* 6 sc)) r (itoa (length bnds))))
          (sd:use-dimstyle sc)
          (sd:dimchain (mapcar '(lambda (x) (sd:p+ ep x 0)) bnds) "H" (sd:p+ ep 0 (* -8 sc)))
          (sd:dim ep (sd:p+ ep 0 hc) "V" (sd:p+ ep (* -8 sc) 0))
          (sd:text (sd:p+ ep 0 (* -20 sc))
                   (strcat "TRI\\U+1EC2N KHAI M\\U+1EB6T \\U+0110\\U+1EE8NG LEN CH\\U+00C2N T\\U+01AF\\U+1EDCNG " mat " - cao " (sd:num hc)
                           ", d\\U+00E0y " (sd:num tk) ", d\\U+00E0i " (sd:rtos (/ tot 1000.0) 2) " m")
                   (* 3.0 sc) "L" "SD-CHU")))
      (princ (strcat "\n[SD] " mat ": tong chieu dai " (sd:rtos (/ tot 1000.0) 2) " m; "
                     (itoa (length (vl-remove-if-not '(lambda (x) (= (nth 4 x) "F")) pcs))) " vien nguyen, "
                     (itoa (length (vl-remove-if '(lambda (x) (= (nth 4 x) "F")) pcs))) " vien cat ("
                     (itoa (car rc)) " ma); dien tich " (sd:rtos (/ (* tot hc) 1e6) 2) " m2."))))
  (sd:finish))

;;; --------------------------------------------------------------------------
;;;  Doc vien op lat (XDATA SD_TILE) -> ((maVL . ((maVien SL ename xd) ...)) ...)
;;; --------------------------------------------------------------------------
(defun sd:tile-groups (ss / i e xd key g grp)
  (setq i 0)
  (repeat (sslength ss)
    (setq e (ssname ss i) i (1+ i)
          xd (mapcar 'cdr (cdadr (assoc -3 (entget e '("SD_TILE"))))))
    (if (/= (nth 1 xd) "X")
      (progn
        (setq key (strcat (nth 0 xd) "|" (nth 2 xd)))
        (if (setq g (assoc key grp))
          (setq grp (subst (list key (1+ (nth 1 g)) (nth 2 g) (nth 3 g)) g grp))
          (setq grp (cons (list key 1 e xd) grp))))))
  (sd:sort grp
    '(lambda (a b)
       (cond ((/= (car (nth 3 a)) (car (nth 3 b))) (< (car (nth 3 a)) (car (nth 3 b))))
             ((/= (= (nth 1 (nth 3 a)) "F") (= (nth 1 (nth 3 b)) "F")) (= (nth 1 (nth 3 a)) "F"))
             (t (< (sd:pc-idx (nth 2 (nth 3 a))) (sd:pc-idx (nth 2 (nth 3 b)))))))))

(defun sd:select-tiles (msg / flt)
  (setq flt '((-3 ("SD_TILE"))))
  (princ msg)
  (cond ((ssget flt)) ((ssget "_X" flt))))

;;; --------------------------------------------------------------------------
;;;  SDGIACONG - Ban ve gia cong tung ma vien cat (gui xuong)
;;; --------------------------------------------------------------------------
(defun sd:dimal (p1 p2 pd / os cl df dx dm)
  (setq os (getvar "OSMODE") cl (getvar "CLAYER") df (getvar "DIMATFIT") dx (getvar "DIMTIX") dm (getvar "DIMTMOVE"))
  (setvar "OSMODE" 0)
  (setvar "CLAYER" "SD-KICHTHUOC")
  (sd:dimchu-apply)   ;; quy tac dim ron: chu canh duong dim (tuy chon chu dim, goc/DGD)
  (command "_.DIMALIGNED" (trans p1 0 1) (trans p2 0 1) (trans pd 0 1))
  (setvar "DIMATFIT" df) (setvar "DIMTIX" dx) (setvar "DIMTMOVE" dm)
  (setvar "CLAYER" cl)
  (setvar "OSMODE" os))

;; Vong lo khoet (loai X) cung ma vien, nam trong bao cua vien dai dien
(defun sd:piece-holes (e pc / bb ss i x xd r)
  (setq bb (sd:bbox (sd:curve-pts e)))
  (if (setq ss (ssget "_X" '((0 . "LWPOLYLINE") (-3 ("SD_TILE")))))
    (progn
      (setq i 0)
      (repeat (sslength ss)
        (setq x (ssname ss i) i (1+ i)
              xd (mapcar 'cdr (cdadr (assoc -3 (entget x '("SD_TILE"))))))
        (if (and (= (nth 1 xd) "X") (= (nth 2 xd) pc)
                 (vl-every '(lambda (p) (and (<= (car (car bb)) (car p) (car (cadr bb)))
                                             (<= (cadr (car bb)) (cadr p) (cadr (cadr bb)))))
                           (sd:curve-pts x)))
          (setq r (cons (sd:curve-pts x) r))))))
  r)

(defun c:SDGIACONG (/ ss inclF ts grp pt cx cy col rowh xd n e typ w h fa thk loops mn po cw ch
                      rg mnp mxp sg p1 p2 ncol dx dy l)
  (sd:begin)
  (if (not (setq ss (sd:select-tiles "\nChon cac vien can ve gia cong <Enter = tat ca>: ")))
    (princ "\n[SD] Khong tim thay vien nao (SDGACH / SDCHANTUONG).")
    (progn
      (if (not (sd:dlg "Ban ve gia cong vien (SDGIACONG)"
                       (list (list "inclF" "Ve ca vien nguyen" 'tog nil)
                             (list "ts" "Ty le ban ve gia cong 1/" 'int (cond (*SD:GCSC*) (10)))
                             (list "ncol" "So the vien tren 1 hang" 'int 4))))
        (exit))
      (setq inclF (sd:v "inclF")
            ts    (float (sd:v "ts"))
            ncol  (sd:v "ncol")
            *SD:GCSC* (fix ts)
            grp   (sd:tile-groups ss))
      (if (setq pt (sd:getpt "\nDiem chen (goc trai tren): " nil))
        (progn
          (sd:use-dimstyle ts)
          (setq cx (car pt) cy (cadr pt) col 0 rowh 0.0)
          (foreach g grp
            (setq xd (nth 3 g) n (nth 1 g) e (nth 2 g) typ (nth 1 xd)
                  w (nth 3 xd) h (nth 4 xd)
                  fa (cond ((nth 10 xd)) (0.0)) thk (cond ((nth 11 xd)) (0.0))
                  loops nil rg nil)
            (if (or inclF (/= typ "F"))
              (progn
                ;; hinh dang vien trong he toa do cua vien, goc trai duoi = (0,0)
                (cond
                  ((and (member typ '("F" "C")) (/= (nth 12 xd) "G"))
                   (setq loops (list (list '(0.0 0.0) (list w 0.0) (list w h) (list 0.0 h)))))
                  ((= (cdr (assoc 0 (entget e))) "LWPOLYLINE")
                   (setq loops (mapcar '(lambda (lp) (mapcar '(lambda (p) (sd:w2l '(0.0 0.0) fa p)) lp))
                                       (cons (sd:curve-pts e) (sd:piece-holes e (nth 2 xd))))
                         mn (car (sd:bbox (car loops)))
                         loops (mapcar '(lambda (lp) (mapcar '(lambda (p) (list (- (car p) (car mn)) (- (cadr p) (cadr mn)))) lp))
                                       loops)
                         w (car (cadr (sd:bbox (car loops)))) h (cadr (cadr (sd:bbox (car loops))))))
                  (t (setq rg (vla-Copy (vlax-ename->vla-object e)))))
                (setq cw (max (+ w (* 24 ts)) (* 75 ts))
                      ch (+ h (* 30 ts))
                      po (list (+ cx (* 14 ts)) (- cy (* 14 ts) h) 0.0))
                ;; vien cong (region): xoay ve phuong vien va dat vao the
                (if rg
                  (progn
                    (vla-Rotate rg (vlax-3d-point '(0.0 0.0 0.0)) (- fa))
                    (vla-GetBoundingBox rg 'mnp 'mxp)
                    (setq mnp (vlax-safearray->list mnp) mxp (vlax-safearray->list mxp))
                    (vla-Move rg (vlax-3d-point mnp) (vlax-3d-point po))
                    (vla-put-Layer rg "SD-GIACONG")
                    (setq w (- (car mxp) (car mnp)) h (- (cadr mxp) (cadr mnp)))))
                (foreach lp loops
                  (sd:pline (mapcar '(lambda (p) (sd:p+ po (car p) (cadr p))) lp) t "SD-GIACONG"))
                ;; kich thuoc bao
                (sd:dim po (sd:p+ po w 0) "H" (sd:p+ po 0 (* -8 ts)))
                (sd:dim po (sd:p+ po 0 h) "V" (sd:p+ po (* -8 ts) 0))
                ;; vien dac biet: ghi tung canh (tru canh bang kich thuoc bao) va canh lo
                (if (and (or (= typ "D") (= (nth 12 xd) "G")) loops)
                  (foreach lp loops
                    (setq sg (if (> (sd:area lp) 0) 1.0 -1.0))
                    (mapcar
                      '(lambda (a b / dx dy l)
                         (setq dx (- (car b) (car a)) dy (- (cadr b) (cadr a)) l (distance a b))
                         (if (and (> l 1.0)
                                  (not (and (equal dy 0.0 0.01) (equal l w 0.5)))
                                  (not (and (equal dx 0.0 0.01) (equal l h 0.5))))
                           (sd:dimal (sd:p+ po (car a) (cadr a)) (sd:p+ po (car b) (cadr b))
                                     (sd:p+ po (+ (/ (+ (car a) (car b)) 2) (* sg (/ dy l) 4 ts))
                                               (- (/ (+ (cadr a) (cadr b)) 2) (* sg (/ dx l) 4 ts))))))
                      lp (append (cdr lp) (list (car lp))))))
                ;; tieu de the
                (sd:text (list (+ cx (* 2 ts)) (- cy (* 5 ts))) (nth 2 xd) (* 3.5 ts) "L" "SD-CHU")
                (sd:text (list (+ cx (* 2 ts)) (- cy (* 9.5 ts)))
                         (strcat "SL: " (itoa n) " vi\\U+00EAn | " (sd:rtos w 0) "\\U+00D7" (sd:rtos h 0)
                                 (if (> thk 0) (strcat "\\U+00D7" (sd:num thk)) "") " | " (nth 7 xd))
                         (* 2.2 ts) "L" "SD-CHU")
                (sd:rect (list cx (- cy ch) 0.0) cw ch "SD-BANG")
                (setq rowh (max rowh ch) col (1+ col) cx (+ cx cw))
                (if (>= col ncol) (setq col 0 cx (car pt) cy (- cy rowh) rowh 0.0)))))
          (sd:use-dimstyle *SD:SCALE*)
          (princ (strcat "\n[SD] Da ve the gia cong cho "
                         (itoa (length (if inclF grp (vl-remove-if '(lambda (g) (= (nth 1 (nth 3 g)) "F")) grp))))
                         " ma vien."))))))
  (sd:finish))

;;; --------------------------------------------------------------------------
;;;  SDDATHO - Cat vien tu tam da tho (slab): toi uu 2D, so do cat, hieu suat
;;; --------------------------------------------------------------------------
;; Tim cho dat tot nhat trong cac o trong. fm: 0 it thua canh ngan nhat (BSSF), 1 it thua canh dai nhat, 2 it thua dien tich;
;; vua khit mot canh thi uu tien (cat duoc ca dai, it vun)
(defun sd:gfit (frs w h rot fm / best i sc lw lh)
  (setq i 0)
  (foreach fr frs
    (foreach o (if rot (list (list w h 0) (list h w 1)) (list (list w h 0)))
      (if (and (<= (car o) (+ (nth 2 fr) 1e-6)) (<= (cadr o) (+ (nth 3 fr) 1e-6)))
        (progn
          (setq lw (- (nth 2 fr) (car o)) lh (- (nth 3 fr) (cadr o))
                sc (cond ((= fm 1) (max lw lh))
                         ((= fm 2) (- (* (nth 2 fr) (nth 3 fr)) (* (car o) (cadr o))))
                         (t (min lw lh))))
          (if (or (< lw 1.0) (< lh 1.0)) (setq sc (- sc 1e8)))
          (if (or (null best) (< sc (car best))) (setq best (list sc i (car o) (cadr o) (caddr o)))))))
    (setq i (1+ i)))
  best)

;; Dat vien vao o, chia o con lai kieu guillotine (cat thang suot tam)
;; tam = (o-trong dat-vien ma-loai-tam); dat-vien = (ma x y rong cao xoay)
;; sm: 0 tach theo canh thua ngan (nhu cu), 1 theo canh thua dai, 2 giu o lon nhat, 3 luon ngang truoc, 4 luon dung truoc
(defun sd:gplace (slab f code k sm / frs fr fx fy fw fh ww hh rw rh hfirst)
  (setq frs (car slab) fr (nth (nth 1 f) frs) ww (nth 2 f) hh (nth 3 f)
        fx (nth 0 fr) fy (nth 1 fr) fw (nth 2 fr) fh (nth 3 fr)
        rw (- fw ww) rh (- fh hh)
        frs (sd:remove-nth (nth 1 f) frs)
        hfirst (cond ((= sm 1) (> rw rh))
                     ((= sm 2) (>= (max (* fw rh) (* rw hh)) (max (* rw fh) (* ww rh))))
                     ((= sm 3) t)
                     ((= sm 4) nil)
                     (t (< rw rh))))
  (foreach nr (if hfirst
                (list (list (+ fx ww) fy rw hh) (list fx (+ fy hh) fw rh))
                (list (list (+ fx ww) fy rw fh) (list fx (+ fy hh) ww rh)))
    (if (and (> (nth 2 nr) 1e-6) (> (nth 3 nr) 1e-6)) (setq frs (cons nr frs))))
  (append (list frs (cons (list code fx fy (- ww k) (- hh k) (nth 4 f)) (cadr slab))) (cddr slab)))

;; Loai tam: (ma rong-dung dai-dung so-luong dai-that rong-that [R = tam du]); so-luong -1 = khong gioi han
(defun sd:fits (tp w h rot)
  (or (and (<= w (nth 1 tp)) (<= h (nth 2 tp)))
      (and rot (<= h (nth 1 tp)) (<= w (nth 2 tp)))))

;; Chon loai tam mo moi: tam du (R) vua nho nhat truoc (uu = T), roi tam kho nguyen (tm 0 lon nhat / tm 1 nho nhat vua), het moi dung tam "MOI" (mua)
(defun sd:pick-type (types w h rot tm uu / best rbest)
  (foreach tp types
    (if (and (/= (car tp) "MOI") (/= (nth 3 tp) 0) (sd:fits tp w h rot))
      (if (and uu (nth 6 tp))
        (if (or (null rbest) (< (* (nth 1 tp) (nth 2 tp)) (* (nth 1 rbest) (nth 2 rbest)))) (setq rbest tp))
        (if (or (null best)
                (if (= tm 1)
                  (< (* (nth 1 tp) (nth 2 tp)) (* (nth 1 best) (nth 2 best)))
                  (> (* (nth 1 tp) (nth 2 tp)) (* (nth 1 best) (nth 2 best)))))
          (setq best tp)))))
  (cond (rbest)
        (best)
        ((and (setq best (assoc "MOI" types)) (sd:fits best w h rot)) best)))

(defun sd:add-type (types id n)
  (mapcar '(lambda (tp)
             (if (and (= (car tp) id) (>= (nth 3 tp) 0))
               (list (nth 0 tp) (nth 1 tp) (nth 2 tp) (+ (nth 3 tp) n) (nth 4 tp) (nth 5 tp) (nth 6 tp))
               tp))
          types))

;; Xep vien len cac tam. Tra ve (danh-sach-tam loai-tam-con-lai vien-khong-xep-duoc)
;; fm / sm: cach cham diem o trong / cach tach o; tm: chon tam kho (0 lon nhat, 1 nho nhat vua); uu: uu tien tam du
(defun sd:slab-pack (pcs types rot k fm sm tm uu / slabs f i done s tp nofit)
  (foreach p pcs
    (setq done nil i 0)
    (while (and (not done) (< i (length slabs)))
      (if (setq f (sd:gfit (car (nth i slabs)) (cadr p) (caddr p) rot fm))
        (setq slabs (sd:replace-nth i (sd:gplace (nth i slabs) f (car p) k sm) slabs) done t))
      (setq i (1+ i)))
    (if (not done)
      (if (setq tp (sd:pick-type types (cadr p) (caddr p) rot tm uu))
        (setq types (sd:add-type types (car tp) -1)
              s     (list (list (list 0.0 0.0 (nth 1 tp) (nth 2 tp))) nil (car tp))
              f     (sd:gfit (car s) (cadr p) (caddr p) rot fm)
              slabs (append slabs (list (sd:gplace s f (car p) k sm))))
        (setq nofit (cons (car p) nofit)))))
  (list slabs types nofit))

;; Doi tam dung it sang loai tam nho hon con trong kho (hoac tam du) neu chua du het vien cua tam do
(defun sd:downsize (slabs types rot k / out cur pcs cands res done)
  (foreach s slabs
    (setq cur  (assoc (caddr s) types)
          pcs  (mapcar '(lambda (p) (list (car p) (+ (nth 3 p) k) (+ (nth 4 p) k))) (cadr s))
          cands (sd:sort (vl-remove-if-not
                           '(lambda (tp) (and (/= (car tp) (car cur)) (/= (car tp) "MOI") (/= (nth 3 tp) 0)
                                              (< (* (nth 1 tp) (nth 2 tp)) (* (nth 1 cur) (nth 2 cur)))))
                           types)
                         '(lambda (a b) (< (* (nth 1 a) (nth 2 a)) (* (nth 1 b) (nth 2 b)))))
          done nil)
    (foreach tp cands
      (if (not done)
        (progn
          (setq res (sd:slab-pack pcs (list (list (car tp) (nth 1 tp) (nth 2 tp) 1 (nth 4 tp) (nth 5 tp) (nth 6 tp))) rot k 0 0 0 nil))
          (if (and (= (length (car res)) 1) (null (caddr res)))
            (setq out   (cons (car (car res)) out)
                  types (sd:add-type (sd:add-type types (car tp) -1) (car cur) 1)
                  done  t)))))
    (if (not done) (setq out (cons s out))))
  (list (reverse out) types))

;; ---- Toi uu kieu ABF cho SDDATHO: nhieu cach xep, uu tien tam du, leo doi ----
;; Cac o trong du lon (ca 2 canh >= dumin) cua 1 tam: ((x y rong cao) ...) kich thuoc that (tru be rong luoi cat)
(defun sd:sp-free (s k dumin / r)
  (foreach f (car s)
    (if (and (>= (- (nth 2 f) k) dumin) (>= (- (nth 3 f) k) dumin))
      (setq r (cons (list (nth 0 f) (nth 1 f) (- (nth 2 f) k) (- (nth 3 f) k)) r))))
  (reverse r))

;; Khoa so sanh: (vien-khong-xep so-tam-mua-moi dien-tich-tam-kho-dung -dien-tich-phe-lieu-giu-lai); nho hon la tot hon
(defun sd:sp-key (slabs types nof k dumin / nnew raw remv tp)
  (setq nnew 0 raw 0.0 remv 0.0)
  (foreach s slabs
    (setq tp (assoc (caddr s) types))
    (cond ((= (car tp) "MOI") (setq nnew (1+ nnew)))
          ((nth 6 tp))
          (t (setq raw (+ raw (* (nth 4 tp) (nth 5 tp))))))
    (foreach f (sd:sp-free s k dumin) (setq remv (+ remv (* (nth 2 f) (nth 3 f))))))
  (list (length nof) nnew raw (- remv)))
(defun sd:sp-less (a b)
  (cond ((/= (car a) (car b)) (< (car a) (car b)))
        ((/= (cadr a) (cadr b)) (< (cadr a) (cadr b)))
        ((> (abs (- (caddr a) (caddr b))) 1.0) (< (caddr a) (caddr b)))
        (t (< (cadddr a) (- (cadddr b) 20000.0)))))

;; Xep + doi tam; q: 0 nhanh (1 cach), 1 can bang (18 to hop: 3 thu tu x 3 cach tach x 2 cach chon tam; thu 48 to hop cho ket qua nhu nhau), 2 ky (them leo doi). Tra ve (slabs types nof)
(defun sd:slab-opt (pcs types rot k q uu dumin / sorts fms sms tms best bk ord s fm sm tm r1 r2 key cur curk n i j a b nb iter t0 bfm bsm btm bord seed)
  (setq q (cond (q) (0))
        sorts (if (= q 0) '(0) '(1 3 0))
        fms (if (= q 0) '(0) '(0))
        sms (if (= q 0) '(0) '(1 2 0))
        tms (if (= q 0) '(0) '(0 1)))
  (foreach s sorts
    (setq ord (sd:ng-sort pcs s))
    (foreach fm fms
      (foreach sm sms
        (foreach tm tms
          (setq r1 (sd:slab-pack ord types rot k fm sm tm uu)
                r2 (sd:downsize (car r1) (cadr r1) rot k)
                key (sd:sp-key (car r2) (cadr r2) (caddr r1) k dumin))
          (if (or (null bk) (sd:sp-less key bk))
            (setq best (list (car r2) (cadr r2) (caddr r1)) bk key bord ord bfm fm bsm sm btm tm))))))
  (if (and (>= q 2) (> (length pcs) 3))
    (progn
      (setq n (length bord) cur bord curk bk iter 0 seed 12345.0 t0 (getvar "MILLISECS"))
      (while (and (< iter 600) (< (- (getvar "MILLISECS") t0) 6000.0))
        (setq seed (rem (+ (* seed 1664525.0) 1013904223.0) 4294967296.0) i (fix (* n (/ seed 4294967296.0)))
              seed (rem (+ (* seed 1664525.0) 1013904223.0) 4294967296.0) j (fix (* n (/ seed 4294967296.0)))
              iter (1+ iter))
        (if (/= i j)
          (progn
            (setq a (nth i cur) b (nth j cur) nb (sd:lset (sd:lset cur i b) j a)
                  r1 (sd:slab-pack nb types rot k bfm bsm btm uu)
                  r2 (sd:downsize (car r1) (cadr r1) rot k)
                  key (sd:sp-key (car r2) (cadr r2) (caddr r1) k dumin))
            (if (not (sd:sp-less curk key))
              (progn (setq cur nb curk key)
                     (if (sd:sp-less key bk) (setq best (list (car r2) (cadr r2) (caddr r1)) bk key)))))))))
  best)

;; Them 1 tam du vao kho: cung vat lieu + kich thuoc (+-1 mm) + day thi cong so luong; ma moi = ma-goc-D<n> (khong lap ma da co)
(defun sd:sp-add-rem (inv parent mat w h thk / root e hit n id)
  (setq root (if (setq n (vl-string-search "-D" parent)) (substr parent 1 n) parent)
        e (assoc parent inv)
        thk (cond ((and e (> (nth 5 e) 0)) (nth 5 e)) (thk) (0.0)))
  (foreach x inv
    (if (and (nth 6 x) (= (nth 1 x) mat) (equal (nth 2 x) w 1.0) (equal (nth 3 x) h 1.0) (equal (nth 5 x) thk 0.5)) (setq hit x)))
  (if hit
    (subst (list (nth 0 hit) (nth 1 hit) (nth 2 hit) (nth 3 hit) (1+ (nth 4 hit)) (nth 5 hit) "R") hit inv)
    (progn
      (setq n 1 id (strcat root "-D1"))
      (while (assoc id inv) (setq n (1+ n) id (strcat root "-D" (itoa n))))
      (append inv (list (list id mat (float (fix (+ 0.5 w))) (float (fix (+ 0.5 h))) 1 thk "R"))))))

;; Tam du moi tu cac o trong: ((id-goc rong cao) ...) theo thu tu tam; id-goc = ma loai tam
(defun sd:sp-remnants (slabs k dumin / r)
  (foreach s slabs
    (foreach f (sd:sp-free s k dumin)
      (setq r (cons (list (caddr s) (nth 2 f) (nth 3 f)) r))))
  (reverse r))

;;; --------------------------------------------------------------------------
;;;  SDKHODA - Quan ly kho da tho: nhieu loai tam, kich thuoc, so luong
;;;  ban ghi kho: (ma-tam ma-VL dai rong so-luong day); ma-VL "*" = dung cho moi VL
;;; --------------------------------------------------------------------------
(defun sd:kho () (vlax-ldata-get "SD" "KHO"))

(defun sd:kho-print (inv)
  (princ "\n  Ma tam | Ma VL | Dai x Rong (mm) | SL | Day")
  (foreach e inv
    (princ (strcat "\n  " (nth 0 e) (if (nth 6 e) " (du)" "") " | " (nth 1 e) " | " (sd:num (nth 2 e)) " x " (sd:num (nth 3 e))
                   " | " (itoa (nth 4 e)) " | " (if (> (nth 5 e) 0) (sd:num (nth 5 e)) "-"))))
  (princ (strcat "\n  Tong: " (itoa (length inv)) " loai, "
                 (itoa (apply '+ (cons 0 (mapcar '(lambda (e) (nth 4 e)) inv)))) " tam, "
                 (sd:rtos (/ (apply '+ (cons 0.0 (mapcar '(lambda (e) (* (nth 2 e) (nth 3 e) (nth 4 e))) inv))) 1e6) 2)
                 " m2")))

(defun c:SDKHODA (/ inv op id e more fn f ln fl sep mode new)
  (sd:begin)
  (setq inv (sd:kho))
  (if (not (sd:dlg "Kho da tho (SDKHODA)"
                   (list (list "op" "Thao tac" 'kw "Lietke"
                               '(("Lietke" . "Liet ke kho") ("Them" . "Them loai tam") ("Sua" . "Sua so luong")
                                 ("Xoa" . "Xoa loai tam") ("Xoadu" . "Xoa tat ca tam du (phe lieu giu lai tu SDDATHO)")
                                 ("Nhap" . "Nhap tu CSV") ("Xuat" . "Xuat ra CSV"))))))
    (exit))
  (setq op (sd:v "op"))
  (cond
    ((= op "Them")
     (setq more t)
     (while more
       (if (not (sd:dlg "Them tam da tho vao kho (SDKHODA)"
                        (list (list "id" "Ma tam (vd T01)" 'str (strcat "T" (itoa (1+ (length inv)))))
                              (list "mat" "Dung cho ma vat lieu (* = moi vat lieu)" 'str "*")
                              (list "L" "Dai (mm)" 'real 2700.0)
                              (list "B" "Rong (mm)" 'real 1800.0)
                              (list "n" "So luong tam" 'int 1)
                              (list "t" "Chieu day (mm, 0 = khong kiem tra)" 'real0 0.0)
                              (list "more" "Them loai tam khac sau khi OK" 'tog nil))))
         (setq more nil)
         (progn
           (setq id (sd:v "id") more (sd:v "more"))
           (if (assoc id inv)
             (princ "\n[SD] Ma tam da co, dung lenh Sua de doi so luong.")
             (setq inv (append inv (list (list id (sd:v "mat") (sd:v "L") (sd:v "B") (sd:v "n") (sd:v "t"))))))))))
    ((= op "Sua")
     (sd:kho-print inv)
     (if (and inv
              (sd:dlg "Sua so luong tam (SDKHODA)"
                      (list (list "id" "Ma tam" 'kw (car (car inv))
                                  (mapcar '(lambda (x) (cons (car x) (strcat (car x) "  " (sd:num (nth 2 x)) "x"
                                                                             (sd:num (nth 3 x)) "  SL " (itoa (nth 4 x)))))
                                          inv))
                            (list "n" "So luong moi" 'int0 (nth 4 (car inv)))))
              (setq e (assoc (sd:v "id") inv)))
       (setq inv (subst (list (nth 0 e) (nth 1 e) (nth 2 e) (nth 3 e) (sd:v "n") (nth 5 e) (nth 6 e)) e inv))
       (princ "\n[SD] Kho trong hoac da huy.")))
    ((= op "Xoa")
     (sd:kho-print inv)
     (if (and inv
              (sd:dlg "Xoa tam khoi kho (SDKHODA)"
                      (list (list "id" "Ma tam can xoa" 'kw (car (car inv))
                                  (append (mapcar 'car inv) '(("*" . "* - xoa het kho")))))))
       (setq id (sd:v "id") inv (if (= id "*") nil (vl-remove (assoc id inv) inv)))))
    ((= op "Xoadu")
     (setq inv (vl-remove-if '(lambda (x) (nth 6 x)) inv))
     (princ "\n[SD] Da xoa cac tam du khoi kho."))
    ((= op "Nhap")
     (if (and (setq fn (getfiled "Chon file kho da tho (CSV: Ma tam;Ma VL;Dai;Rong;SL;Day;Loai = R neu la tam du)" (getvar "DWGPREFIX") "csv" 0))
              (setq f (sd:open fn "r")))
       (progn
         (setq mode (if (sd:dlg "Nhap kho tu CSV (SDKHODA)"
                                (list (list "mode" "Du lieu cu trong kho" 'kw "Themvao"
                                            '(("Themvao" . "Giu, them vao") ("Thaythe" . "Thay the toan bo")))))
                      (sd:v "mode") "Themvao"))
         (while (setq ln (read-line f))
           (setq sep (if (vl-string-search ";" ln) ";" ",")
                 fl  (mapcar '(lambda (x) (vl-string-trim " \t\"" x)) (sd:split ln sep)))
           (if (and (>= (length fl) 5) (> (atof (nth 2 fl)) 0) (> (atof (nth 3 fl)) 0))
             (setq new (cons (list (nth 0 fl) (if (= (nth 1 fl) "") "*" (nth 1 fl))
                                   (atof (nth 2 fl)) (atof (nth 3 fl)) (atoi (nth 4 fl))
                                   (if (nth 5 fl) (atof (nth 5 fl)) 0.0)
                                   (if (and (nth 6 fl) (= (strcase (nth 6 fl)) "R")) "R"))
                             new))))
         (setq fn (sd:close f))
         (setq inv (if (= mode "Thaythe") (reverse new)
                     (append (vl-remove-if '(lambda (x) (assoc (car x) new)) inv) (reverse new))))
         (princ (strcat "\n[SD] Da nhap " (itoa (length new)) " loai tam.")))))
    ((= op "Xuat")
     (setq fn (sd:csv-name "_KhoDaTho.csv"))
     (if (setq f (sd:open fn "w"))
       (progn
         (write-line "Ma tam;Ma VL;Dai (mm);Rong (mm);SL;Day (mm);Loai (R = tam du)" f)
         (foreach e inv
           (write-line (sd:join (list (nth 0 e) (nth 1 e) (sd:num (nth 2 e)) (sd:num (nth 3 e))
                                      (itoa (nth 4 e)) (sd:num (nth 5 e)) (if (nth 6 e) "R" "")) ";") f))
         (setq fn (sd:close f))
         (princ (strcat "\n[SD] Da xuat: " fn))))))
  (if (member op '("Them" "Sua" "Xoa" "Xoadu" "Nhap")) (vlax-ldata-put "SD" "KHO" inv))
  (sd:kho-print inv)
  (sd:finish))

;;; --------------------------------------------------------------------------
;;;  SDDATHO - Cat vien tu da tho: kho nhieu kich thuoc hoac 1 co tam; so do cat
;;; --------------------------------------------------------------------------
(defun c:SDDATHO (/ ss grp inv src buy SL SB trim kerf rot ds mats pcs uniq slabs types res nof
                    lays key g pt x0 y0 col idx used fin tfin traw lines bx base rowh maxw th fn f tp thkM
                    usage moi moid uu giu dumin oq rems nrem remarea ntrem)
  (sd:begin)
  (if (not (setq ss (sd:select-tiles "\nChon cac vien can cat tu da tho <Enter = tat ca>: ")))
    (princ "\n[SD] Khong tim thay vien nao (SDGACH / SDCHANTUONG).")
    (progn
      (setq inv (sd:kho))
      (if inv (sd:kho-print inv))
      (if (not (sd:dlg "Cat vien tu da tho (SDDATHO)"
                       (list (list "src" "Nguon da tho" 'kw (if inv "Kho" "Motco")
                                   (if inv '(("Kho" . "Kho (nhieu co tam)") ("Motco" . "Mot co tam")) '(("Motco" . "Mot co tam"))))
                             (list "buy" "Khi kho khong du" 'kw "Muamoi" '(("Muamoi" . "Them tam mua moi") ("Dung" . "Bao thieu"))
                                   '("src" "Kho"))
                             (list "SL" "Tam da tho / tam mua moi - dai (mm)" 'real (sd:cfg "SLABL" 2700.0))
                             (list "SB" "Tam da tho / tam mua moi - rong (mm)" 'real (sd:cfg "SLABB" 1800.0))
                             (list "trim" "Xen bien moi canh (mm)" 'real0 (sd:cfg "SLABTRIM" 20.0))
                             (list "kerf" "Be rong luoi cat (mm)" 'real0 (sd:cfg "SLABKERF" 3.0))
                             (list "rot" "Cho xoay vien 90 do (khong giu chieu van)" 'tog t)
                             (list "ds" "Ty le ve so do cat 1/" 'int (cond (*SD:DTSC*) (50)))
                             (list "uu" "Uu tien dung tam du trong kho truoc" 'tog t nil '("src" "Kho"))
                             (list "giu" "Giu phe lieu (o trong du lon) thanh tam du trong kho" 'tog t nil '("src" "Kho"))
                             (list "dumin" "Tam du: chi giu khi ca 2 canh >= (mm)" 'real0 (sd:cfg "DUMIN" 300.0) nil '("src" "Kho"))
                             (list "oq" "Do ky khi xep (thu nhieu cach, chon it tam / it mua moi nhat)" 'kw (cond (*SD:DTQ*) ("Canbang"))
                                   '(("Nhanh" . "Nhanh: 1 cach xep") ("Canbang" . "Can bang: thu nhieu to hop sap xep / cham diem / tach o / chon tam")
                                     ("Ky" . "Ky: them leo doi hoan doi thu tu (toi da ~6 giay moi vat lieu)")))
                             (list "ded" "Tru so tam da dung khoi kho (va ghi tam du moi)" 'tog nil nil '("src" "Kho")))))
        (exit))
      (setq src (sd:v "src") buy (or (/= src "Kho") (= (sd:v "buy") "Muamoi"))
            SL (sd:cfg-put "SLABL" (sd:v "SL")) SB (sd:cfg-put "SLABB" (sd:v "SB"))
            trim (sd:cfg-put "SLABTRIM" (sd:v "trim")) kerf (sd:cfg-put "SLABKERF" (sd:v "kerf"))
            rot (sd:v "rot") ds (float (sd:v "ds")) *SD:DTSC* (fix ds)
            uu (sd:v "uu") giu (and (= src "Kho") (sd:v "giu")) dumin (sd:cfg-put "DUMIN" (sd:v "dumin"))
            oq (cond ((sd:v "oq")) ("Canbang")) *SD:DTQ* oq
            moi (if (= src "Kho") "MUA MOI" "TAM") moid (if (= src "Kho") "MUA M\\U+1EDAI" "T\\U+1EA4M")
            grp (sd:tile-groups ss))
      (foreach g grp (if (not (member (car (nth 3 g)) mats)) (setq mats (cons (car (nth 3 g)) mats))))
      (setq pt (sd:getpt "\nDiem chen so do cat (goc trai tren): " nil)
            y0 (if pt (cadr pt) 0.0) tfin 0.0 traw 0.0)
      (foreach mat (reverse mats)
        ;; vien rieng (ma w h SL), canh lon giam dan, roi trai ra tung vien
        (setq uniq nil pcs nil thkM nil)
        (foreach g grp
          (if (= (car (nth 3 g)) mat)
            (setq uniq (cons (list (nth 2 (nth 3 g)) (+ (nth 3 (nth 3 g)) kerf) (+ (nth 4 (nth 3 g)) kerf) (nth 1 g)) uniq)
                  thkM (cond (thkM) ((nth 11 (nth 3 g)))))))
        (setq uniq (sd:sort uniq '(lambda (a b) (if (equal (max (cadr a) (caddr a)) (max (cadr b) (caddr b)) 0.01)
                                                  (> (* (cadr a) (caddr a)) (* (cadr b) (caddr b)))
                                                  (> (max (cadr a) (caddr a)) (max (cadr b) (caddr b)))))))
        (foreach u uniq (repeat (cadddr u) (setq pcs (cons (list (car u) (cadr u) (caddr u)) pcs))))
        ;; loai tam dung duoc cho vat lieu nay (kho dung ma VL hoac "*", dung chieu day)
        (setq types nil)
        (if (= src "Kho")
          (foreach e inv
            (if (and (> (nth 4 e) 0) (or (= (nth 1 e) "*") (= (nth 1 e) mat))
                     (or (<= (nth 5 e) 0) (null thkM) (<= thkM 0) (equal (nth 5 e) thkM 0.5)))
              ;; tam du (R) da la canh cat sach: khong xen bien nua
              (setq types (cons (list (nth 0 e) (if (nth 6 e) (+ (nth 2 e) kerf) (+ (- (nth 2 e) trim trim) kerf))
                                      (if (nth 6 e) (+ (nth 3 e) kerf) (+ (- (nth 3 e) trim trim) kerf))
                                      (nth 4 e) (nth 2 e) (nth 3 e) (nth 6 e))
                                types)))))
        (if buy (setq types (cons (list "MOI" (+ (- SL trim trim) kerf) (+ (- SB trim trim) kerf) -1 SL SB nil) types)))
        (setq res   (sd:slab-opt (reverse pcs) types rot kerf (cond ((= oq "Nhanh") 0) ((= oq "Ky") 2) (t 1)) uu dumin)
              nof   (caddr res)
              slabs (car res)
              types (cadr res)
              fin   (apply '+ (mapcar '(lambda (s) (apply '+ (mapcar '(lambda (p) (* (nth 3 p) (nth 4 p))) (cadr s)))) slabs)))
        ;; cap nhat ton kho tam thoi (cho vat lieu sau) va thong ke su dung theo loai tam
        (setq usage nil)
        (foreach s slabs
          (setq usage (sd:addcnt (caddr s) 1 usage)))
        (if (= src "Kho")
          (setq inv (mapcar '(lambda (e) (if (assoc (car e) usage)
                                           (list (nth 0 e) (nth 1 e) (nth 2 e) (nth 3 e)
                                                 (- (nth 4 e) (cdr (assoc (car e) usage))) (nth 5 e))
                                           e))
                            inv)))
        (setq tfin (+ tfin fin)
              traw (+ traw (apply '+ (mapcar '(lambda (s) (setq tp (assoc (caddr s) types)) (* (nth 4 tp) (nth 5 tp))) slabs))))
        ;; phe lieu du lon -> tam du trong kho (cho lan chay sau); tam du da dung o lan nay khong tinh la phe lieu moi
        (if giu
          (progn
            (setq rems (sd:sp-remnants slabs kerf dumin) nrem 0 remarea 0.0)
            (foreach r rems
              (setq inv (sd:sp-add-rem inv (car r) mat (nth 1 r) (nth 2 r) thkM)
                    nrem (1+ nrem) remarea (+ remarea (* (nth 1 r) (nth 2 r)))))
            (setq ntrem (+ (cond (ntrem) (0)) nrem))
            (if (> nrem 0)
              (princ (strcat "\n   Giu lai " (itoa nrem) " tam du (" (sd:rtos (/ remarea 1e6) 2) " m2), moi canh >= " (sd:num dumin) " mm"
                             (if (sd:v "ded") " - ghi vao kho" " - CHUA ghi kho (bat 'Tru so tam da dung khoi kho')"))))))
        ;; gom so do giong nhau (cung loai tam + cung cach xep)
        (setq lays nil)
        (foreach s slabs
          (setq key (vl-princ-to-string (cons (caddr s) (cadr s))))
          (if (setq g (assoc key lays))
            (setq lays (subst (list key (1+ (cadr g)) (caddr g)) g lays))
            (setq lays (cons (list key 1 s) lays))))
        (setq lays (reverse lays))
        (princ (strcat "\n " mat ": " (itoa (length slabs)) " tam (" (itoa (length lays)) " mau so do)"))
        (foreach u usage
          (setq tp (assoc (car u) types))
          (princ (strcat "\n   " (if (= (car u) "MOI") moi (car u)) (if (nth 6 tp) " (tam du)" "") " " (sd:num (nth 4 tp)) "x" (sd:num (nth 5 tp))
                         ": " (itoa (cdr u)) " tam")))
        (if nof
          (princ (strcat "\n [!] Khong du da / vien qua lon, chua xep: " (itoa (length nof)) " vien ("
                         (sd:join (sd:uniq nof) ", ") ")")))
        ;; ve so do
        (if pt
          (progn
            (sd:text (list (car pt) y0)
                     (strcat "S\\U+01A0 \\U+0110\\U+1ED2 C\\U+1EAET \\U+0110\\U+00C1 TH\\U+00D4 " mat ": " (itoa (length slabs)) " t\\U+1EA5m; th\\U+00E0nh ph\\U+1EA9m "
                             (sd:rtos (/ fin 1e6) 2) " m\\U+00B2"
                             (if nof (strcat "; THI\\U+1EBEU \\U+0110\\U+00C1 CHO " (itoa (length nof)) " VI\\U+00CAN") ""))
                     (* 3.5 ds) "L" "SD-CHU")
            (setq y0 (- y0 (* 12 ds)) x0 (car pt) col 0 idx 0 rowh 0.0
                  maxw (* 3.5 (apply 'max (mapcar '(lambda (x) (nth 4 x)) types))))
            (foreach l lays
              (setq tp   (assoc (caddr (caddr l)) types)
                    idx  (1+ idx)
                    used (apply '+ (mapcar '(lambda (p) (* (nth 3 p) (nth 4 p))) (cadr (caddr l)))))
              (if (and (> col 0) (> (+ (- x0 (car pt)) (nth 4 tp)) maxw))
                (setq col 0 x0 (car pt) y0 (- y0 rowh (* 12 ds)) rowh 0.0))
              (setq bx x0 base (- y0 (nth 5 tp)) rowh (max rowh (nth 5 tp)))
              (sd:rect (list bx base 0.0) (nth 4 tp) (nth 5 tp) "SD-GIACONG")
              (sd:rect (list (+ bx trim) (+ base trim) 0.0)
                       (- (nth 4 tp) trim trim) (- (nth 5 tp) trim trim) "SD-KHUAT")
              (foreach p (cadr (caddr l))
                (setq th (max (* 0.6 ds) (min (* 2.0 ds) (* 0.25 (min (nth 3 p) (nth 4 p))))))
                (sd:rect (list (+ bx trim (nth 1 p)) (+ base trim (nth 2 p)) 0.0) (nth 3 p) (nth 4 p) "SD-GACH-CAT")
                (sd:text (list (+ bx trim (nth 1 p) (/ (nth 3 p) 2)) (+ base trim (nth 2 p) (/ (nth 4 p) 2) (* 0.6 th)))
                         (car p) th "MC" "SD-CHU")
                (sd:text (list (+ bx trim (nth 1 p) (/ (nth 3 p) 2)) (- (+ base trim (nth 2 p) (/ (nth 4 p) 2)) (* 0.6 th)))
                         (strcat (sd:rtos (nth 3 p) 0) "\\U+00D7" (sd:rtos (nth 4 p) 0)) (* 0.8 th) "MC" "SD-CHU")
                (setq lines (cons (sd:join (list mat (itoa idx) (if (= (car tp) "MOI") moi (car tp))
                                                 (sd:num (nth 4 tp)) (sd:num (nth 5 tp)) (itoa (cadr l)) (car p)
                                                 (sd:rtos (nth 1 p) 0) (sd:rtos (nth 2 p) 0)
                                                 (sd:rtos (nth 3 p) 0) (sd:rtos (nth 4 p) 0)
                                                 (if (= (nth 5 p) 1) "Co" "Khong")) ";")
                                  lines)))
              (sd:text (list bx (+ y0 (* 2 ds)))
                       (strcat "T\\U+1EA4M " (itoa idx) " (\\U+00D7" (itoa (cadr l)) ") "
                               (if (= (car tp) "MOI") moid (car tp)) " " (sd:num (nth 4 tp)) "\\U+00D7" (sd:num (nth 5 tp))
                               " - s\\U+1EED d\\U+1EE5ng " (sd:rtos (/ (* 100.0 used) (* (nth 4 tp) (nth 5 tp))) 1) "%")
                       (* 2.5 ds) "L" "SD-CHU")
              (setq col (1+ col) x0 (+ x0 (nth 4 tp) (* 0.15 (nth 4 tp)))))
            (setq y0 (- y0 rowh (* 20 ds))))))
      (princ (strcat "\n TONG: da tho " (sd:rtos (/ traw 1e6) 2) " m2, thanh pham " (sd:rtos (/ tfin 1e6) 2)
                     " m2, hieu suat " (sd:rtos (if (> traw 0) (/ (* 100.0 tfin) traw) 0.0) 1) "%"))
      ;; tru kho
      (if (= src "Kho")
        (progn
          (if (sd:v "ded")
            (progn
              (vlax-ldata-put "SD" "KHO" (vl-remove-if '(lambda (e) (<= (nth 4 e) 0)) inv))
              (princ "\n[SD] Da cap nhat kho (loai tam het hang duoc xoa).")
              (sd:kho-print (sd:kho))))))
      (setq fn (sd:csv-name "_SoDoCatDaTho.csv"))
      (if (and lines (setq f (sd:open fn "w")))
        (progn
          (write-line "Ma VL;Mau so do;Loai tam;Dai tam;Rong tam;So tam;Ma vien;x (mm);y (mm);Rong (mm);Cao (mm);Xoay" f)
          (foreach l (reverse lines) (write-line l f))
          (setq fn (sd:close f))
          (princ (strcat "\n[SD] Da xuat: " fn))))))
  (sd:finish))

(defun sd:uniq (lst / r) (foreach x lst (if (not (member x r)) (setq r (cons x r)))) (reverse r))

;;; ==========================================================================
;;;  SDTHANGDA - Cau thang da: mat bac, co bac, mui bac, khe LED, len chan tuong, ra da kieu ABF
;;;  Mui bac: Thang (mat chong len co, mui nho ra) / V45 (mat va co ghep vat 45 do) /
;;;           Roi (dai mui cat rieng) / CNC (mat lien, mui bo hay vat bang CNC)
;;;  Khe LED: Cobac (tru vao chieu cao co bac) / Matbac (tru vao chieu sau mat bac) / Ranh (cat ranh duoi mat bac)
;;; ==========================================================================
;; So phan chia chieu dai L thanh cac vien dai nhat Lmax (co mach gap giua cac vien)
(defun sd:st-split (L Lmax gap)
  (max 1 (fix (+ (/ (+ L gap) (+ Lmax gap)) 0.999999))))

;; Danh sach vien cua 1 cau thang. Moi vien: (ma ten dai rong so-luong day goc ghichu vat-mm cnc-mm)
;; dai x rong la kich thuoc phoi (mat lon nhat cua vien vat 45), goc la goc cat dac biet (90 = vuong)
(defun sd:st-pieces (kieu n W gd R tm tc nho rm led ledv Lmax gap nside hl
                     / k part dm hc pcs ls al blank m seg cnc)
  (setq nho (if (= kieu "V45") 0.0 nho)
        dm  (cond ((= kieu "V45") gd) ((= kieu "Roi") (- (+ gd nho) rm)) (t (+ gd nho)))
        hc  (if (= kieu "V45") R (- R tm)))
  (if (> led 0.0)
    (cond ((= ledv "Cobac") (setq hc (- hc led)))
          ((= ledv "Matbac") (setq dm (- dm led)))))
  (setq k (sd:st-split W Lmax gap)
        part (/ (- W (* (1- k) gap)) k)
        cnc (cond ((= kieu "CNC") part) (t 0.0)))
  (if (or (and (> led 0.0) (= ledv "Ranh")) (= ledv "Hoc")) (setq cnc (+ cnc part)))
  (setq pcs
        (list (list "MB" "Mat bac" part dm (* n k) tm (if (= kieu "V45") 45.0 90.0)
                    (cond ((= kieu "V45") "vat 45 do canh truoc")
                          ((= kieu "CNC") "mui bo / vat CNC")
                          ((= kieu "Roi") "mat bac, mui rieng")
                          (t "mui nho ra"))
                    (if (= kieu "V45") part 0.0) cnc)
              (list "CB" "Co bac" part hc (* n k) tc (if (= kieu "V45") 45.0 90.0)
                    (if (= kieu "V45") "vat 45 do canh tren" "cat vuong")
                    (if (= kieu "V45") part 0.0) 0.0)))
  (if (= ledv "Hoc")
    (setq pcs (cons (sd:lset (car pcs) 7 (strcat (nth 7 (car pcs)) ", hoc LED duoi mep truoc")) (cdr pcs))))
  (if (= kieu "Roi")
    (setq pcs (append pcs (list (list "MR" "Dai mui roi" part rm (* n k) tm 90.0 "bo / vat CNC canh truoc" 0.0 part)))))
  (if (and (> nside 0) (> hl 0.0))
    (progn
      (setq ls (* n (sqrt (+ (* gd gd) (* R R))))
            al (atan R gd)
            blank (+ ls (* hl (/ (sin al) (cos al))))
            m (sd:st-split blank Lmax gap)
            seg (/ (- blank (* (1- m) gap)) m))
      (setq pcs (append pcs (list (list "LN" "Len chan tuong" seg hl (* m nside) tc (* al (/ 180.0 pi))
                                        "2 vien dau cuoi cat xien theo do doc" 0.0 0.0))))))
  pcs)

;; ---- Phoi bac quat theo hinh that: bao loi, phoi chu nhat nho nhat (xoay), ghep 2 vien nguoc nhau ----
(defun sd:cr (o a b) (- (* (- (car a) (car o)) (- (cadr b) (cadr o))) (* (- (cadr a) (cadr o)) (- (car b) (car o)))))

;; Bao loi (monotone chain) cua cac diem 2D, tra ve cac dinh nguoc kim dong ho
(defun sd:hull (pts / s lo up)
  (setq s (sd:sort pts '(lambda (a b) (if (= (car a) (car b)) (< (cadr a) (cadr b)) (< (car a) (car b))))))
  (foreach p s
    (while (and (cdr lo) (<= (sd:cr (cadr lo) (car lo) p) 0.0)) (setq lo (cdr lo)))
    (setq lo (cons p lo)))
  (foreach p (reverse s)
    (while (and (cdr up) (<= (sd:cr (cadr up) (car up) p) 0.0)) (setq up (cdr up)))
    (setq up (cons p up)))
  (append (reverse (cdr lo)) (reverse (cdr up))))

;; Rong x cao cua khung bao khi xoay he truc di phi
(defun sd:wf-bbox (pts phi / c sn xs ys)
  (setq c (cos phi) sn (sin phi)
        xs (mapcar '(lambda (p) (+ (* (car p) c) (* (cadr p) sn))) pts)
        ys (mapcar '(lambda (p) (- (* (cadr p) c) (* (car p) sn))) pts))
  (list (- (apply 'max xs) (apply 'min xs)) (- (apply 'max ys) (apply 'min ys))))

;; Phoi chu nhat dien tich nho nhat khi xoay mot da giac: (dien-tich rong cao goc-xoay)
(defun sd:wf-single (pts / k phi bb best a)
  (setq k 0)
  (while (< k 90)
    (setq phi (* k (/ pi 90.0)) bb (sd:wf-bbox pts phi) a (* (car bb) (cadr bb)))
    (if (or (null best) (< a (car best))) (setq best (list a (car bb) (cadr bb) phi)))
    (setq k (1+ k)))
  best)

;; Ghep 2 vien loi giong nhau, vien thu 2 xoay 180 do: B = t - A khong chong A khi t nam tren bien cua 2A.
;; Tra ve phoi chu nhat nho nhat cua cap, chua khe m giua 2 vien: (dien-tich rong cao goc-xoay tx ty)
(defun sd:wf-pair (hull m / best i p q s tt pts2 phi bb a dx dy ln)
  (setq i 0)
  (foreach p hull
    (setq q (nth (rem (1+ i) (length hull)) hull) s 0
          dx (- (car q) (car p)) dy (- (cadr q) (cadr p)) ln (max 1e-9 (sqrt (+ (* dx dx) (* dy dy)))))
    (while (<= s 10)
      (setq tt (list (+ (* 2.0 (+ (car p) (* (/ s 10.0) dx))) (* m (/ dy ln)))
                     (- (* 2.0 (+ (cadr p) (* (/ s 10.0) dy))) (* m (/ dx ln))))
            pts2 (append hull (mapcar '(lambda (a) (list (- (car tt) (car a)) (- (cadr tt) (cadr a)))) hull)) phi 0.0)
      (while (< phi pi)
        (setq bb (sd:wf-bbox pts2 phi) a (* (car bb) (cadr bb)))
        (if (or (null best) (< a (car best))) (setq best (list a (car bb) (cadr bb) phi (car tt) (cadr tt))))
        (setq phi (+ phi (/ pi 60.0))))
      (setq s (1+ s)))
    (setq i (1+ i)))
  best)

;; Bo vien cua ca cau thang: nve ve thang (moi ve n bac), chieu nghi cnl x cnw, nq bac quat tong goc gq (do), ban kinh trong ri / ngoai ro
(defun sd:st-all (kieu n W gd R tm tc nho rm led ledv Lmax gap nside hl nve cnl cnw nq gq ri ro dq rc dk / pcs out kl kw th hc ar hl1 b1 b2 np nr ky cc cl sg m ph)
  (setq pcs (sd:st-pieces kieu n W gd R tm tc nho rm led ledv Lmax gap nside hl)
        out (mapcar '(lambda (p) (if (> nve 1) (append (list (car p) (cadr p) (caddr p) (cadddr p) (* (nth 4 p) nve)) (nthcdr 5 p)) p)) pcs))
  (if (and (> nve 1) (> cnl 0.0) (> cnw 0.0))
    (progn
      (setq kl (sd:st-split cnl Lmax gap) kw (sd:st-split cnw Lmax gap))
      (setq out (append out (list (list "CN" "Chieu nghi" (/ (- cnl (* (1- kl) gap)) kl) (/ (- cnw (* (1- kw) gap)) kw)
                                        (* (1- nve) kl kw) tm 90.0 "tam lat chieu nghi" 0.0 0.0))))))
  (if (and (> nq 0) (> gq 0.0) (> ro ri))
    (progn
      (setq th (/ (* gq (/ pi 180.0)) nq)
            hc (- R (if (= kieu "V45") 0.0 tm))
            ar (* 0.5 th (- (* ro ro) (* ri ri)))
            ky (list th ri ro))
      (if (setq cc (assoc ky *SD:WFC*))
        (setq b1 (cadr cc) b2 (caddr cc))
        (progn
          (setq hl1 (sd:hull (sd:st-sector (list 0.0 0.0) ri ro (/ th -2.0) (/ th 2.0)))
                b1 (sd:wf-single hl1) b2 (sd:wf-pair hl1 (+ gap 2.0))
                *SD:WFC* (cons (list ky b1 b2) *SD:WFC*))))
      (setq
            np (if (< (car b2) (* 0.97 2.0 (car b1))) (fix (/ nq 2)) 0)
            nr (- nq (* 2 np)))
      (if (> nr 0)
        (setq out (append out (list (list "MQ" "Mat bac quat" (cadr b1) (caddr b1) nr tm (/ (* th 180.0) pi)
                                          "hinh quat: phoi chu nhat nho nhat khi xoay" 0.0 0.0 ar)))))
      (if (> np 0)
        (setq out (append out (list (list "MQG" "Mat bac quat ghep doi" (cadr b2) (caddr b2) np tm (/ (* th 180.0) pi)
                                          "2 quat xoay nguoc nhau trong 1 phoi" 0.0 0.0 (* 2.0 ar))))))
      (cond
        ;; co bac cong: tam cong cat tu phoi day bang CNC; phoi = day cung x rong day, day phoi = mui ten cung + day tam
        ((and (= dq "Cong") (> rc 1.0))
         (setq cl (* 2.0 rc (sin (/ th 2.0))) sg (* rc (- 1.0 (cos (/ th 2.0)))))
         (setq out (append out (list (list "CQC" "Co bac quat cong" cl hc nq (+ sg tc) (/ (* th 90.0) pi)
                                           (strcat "cong ban kinh " (sd:num rc) ", phoi day " (sd:rtos (+ sg tc) 0) " (CNC cat cong 2 mat)")
                                           0.0 (* 2.0 rc th) (* rc th hc))))))
        ;; co bac ghep doan: cac tam thang, hai dau vat nua goc chuyen huong
        ((and (= dq "Doan") (> rc 1.0) (> dk 1.0))
         (setq m (max 1 (fix (+ 0.999999 (/ (* rc th) dk)))) ph (/ th m))
         (setq out (append out (list (list "CQD" "Co bac quat ghep doan" (* 2.0 rc (sin (/ ph 2.0))) hc (* nq m) tc (/ (* ph 90.0) pi)
                                           (strcat "ghep " (itoa m) " doan / bac, 2 dau vat " (sd:rtos (/ (* ph 90.0) pi) 1) " do")
                                           (* 2.0 hc) 0.0 (* rc th hc (/ 1.0 m)))))))
        (t (setq out (append out (list (list "CQ" "Co bac quat" (- ro ri) hc nq tc 90.0 "canh truoc theo ban kinh" 0.0 0.0))))))))
  out)

;; Xep cac vien len tam da tho (kieu ABF) theo tung do day. Tra ve ((day slabs types nof) ...)
(defun sd:st-nest (pcs SL SB trim kerf rot q / out thks items types r)
  (foreach p pcs (if (not (member (nth 5 p) thks)) (setq thks (cons (nth 5 p) thks))))
  (foreach th (reverse thks)
    (setq items nil)
    (foreach p pcs
      (if (equal (nth 5 p) th 0.01)
        (repeat (fix (+ 0.5 (nth 4 p)))
          (setq items (cons (list (car p) (+ (nth 2 p) kerf) (+ (nth 3 p) kerf)) items)))))
    (setq types (list (list "MOI" (+ (- SL trim trim) kerf) (+ (- SB trim trim) kerf) -1 SL SB nil))
          r (sd:slab-opt (reverse items) types rot kerf q nil 0.0)
          out (cons (list th (car r) (cadr r) (caddr r)) out)))
  (reverse out))

;; Tom tat ket qua xep: (so-tam dien-tich-tho dien-tich-thanh-pham so-vien-chua-xep)
(defun sd:st-sum (nest / ns raw fin nof)
  (setq ns 0 raw 0.0 fin 0.0 nof 0)
  (foreach g nest
    (foreach s (cadr g)
      (setq ns (1+ ns)
            raw (+ raw (* (nth 4 (assoc (caddr s) (caddr g))) (nth 5 (assoc (caddr s) (caddr g)))))
            fin (+ fin (apply '+ (mapcar '(lambda (p) (* (nth 3 p) (nth 4 p))) (cadr s))))))
    (setq nof (+ nof (length (cadddr g)))))
  (list ns raw fin nof))

;; Tong dien tich phoi / chieu dai vat 45 / chieu dai CNC cua 1 bo vien (m2, m, m)
(defun sd:st-tot (pcs / a v c f)
  (setq a 0.0 v 0.0 c 0.0 f 0.0)
  (foreach p pcs
    (setq a (+ a (/ (* (nth 4 p) (nth 2 p) (nth 3 p)) 1e6))
          f (+ f (/ (* (nth 4 p) (cond ((nth 10 p)) (t (* (nth 2 p) (nth 3 p))))) 1e6))
          v (+ v (/ (* (nth 4 p) (nth 8 p)) 1000.0))
          c (+ c (/ (* (nth 4 p) (nth 9 p)) 1000.0))))
  (list a v c f))

;; Mat cat doc 3 bac de xem mui bac va khe LED. o = goc duoi trai, huong len cao di sang phai
(defun sd:st-profile (o kieu gd R tm tc nho rm led ledv ledr leds ledc / k x0 y0 hc dm tl tr hx hy)
  (setq nho (if (= kieu "V45") 0.0 nho)
        hc  (if (= kieu "V45") R (- R tm)))
  (if (and (> led 0.0) (= ledv "Cobac")) (setq hc (- hc led)))
  (setq k 0)
  (repeat 3
    (setq x0 (* k gd) y0 (* k R)
          tl (if (= kieu "Roi") (+ (- x0 nho) rm) (- x0 nho))
          tr (if (and (> led 0.0) (= ledv "Matbac")) (- (+ x0 gd) led) (+ x0 gd)))
    ;; co bac
    (if (= kieu "V45")
      (sd:pline (list (sd:p+ o x0 y0) (sd:p+ o (+ x0 tc) y0) (sd:p+ o (+ x0 tc) (+ y0 (- hc tc))) (sd:p+ o x0 (+ y0 hc))) t "SD-GACH")
      (sd:pline (list (sd:p+ o x0 y0) (sd:p+ o (+ x0 tc) y0) (sd:p+ o (+ x0 tc) (+ y0 hc)) (sd:p+ o x0 (+ y0 hc))) t "SD-GACH"))
    ;; mat bac (dinh tai y0 + R)
    (if (= kieu "V45")
      (sd:pline (list (sd:p+ o x0 (+ y0 R)) (sd:p+ o tr (+ y0 R)) (sd:p+ o tr (+ y0 (- R tm))) (sd:p+ o (+ x0 tm) (+ y0 (- R tm)))) t "SD-GACH-CAT")
      (sd:pline (list (sd:p+ o tl (+ y0 (- R tm))) (sd:p+ o tr (+ y0 (- R tm))) (sd:p+ o tr (+ y0 R)) (sd:p+ o tl (+ y0 R))) t "SD-GACH-CAT"))
    ;; hoc LED duoi mep truoc mat bac: hinh chu nhat cat vao mat bac + ky hieu den (layer SD-LED)
    (if (= ledv "Hoc")
      (progn
        (sd:make-layer "SD-LED" 1 "Continuous" 25)
        (setq hx (+ tl ledc) hy (+ y0 (- R tm)))
        (sd:pline (list (sd:p+ o hx hy) (sd:p+ o (+ hx ledr) hy) (sd:p+ o (+ hx ledr) (+ hy leds)) (sd:p+ o hx (+ hy leds))) t "SD-KHUAT")
        (if (= k 0)
          (progn
            (entmake (list '(0 . "CIRCLE") '(8 . "SD-LED") (cons 10 (sd:p+ o (+ hx (/ ledr 2.0)) (+ hy (/ leds 2.0)))) (cons 40 (* 0.3 (min ledr leds)))))
            (sd:line (sd:p+ o (+ hx (/ ledr 2.0)) (- hy 8.0)) (sd:p+ o (+ hx (/ ledr 2.0)) (+ hy leds 8.0)) "SD-LED")
            (sd:line (sd:p+ o (- hx 8.0) (+ hy (/ leds 2.0))) (sd:p+ o (+ hx ledr 8.0) (+ hy (/ leds 2.0))) "SD-LED")
            (sd:text (sd:p+ o (+ hx ledr 14.0) (- hy 10.0)) (strcat "HOC LED " (sd:num ledr) "x" (sd:num leds) ", cach mep " (sd:num ledc)) 6.0 "L" "SD-LED")))))
    ;; dai mui roi
    (if (= kieu "Roi")
      (sd:pline (list (sd:p+ o (- x0 nho) (+ y0 (- R tm))) (sd:p+ o tl (+ y0 (- R tm))) (sd:p+ o tl (+ y0 R)) (sd:p+ o (- x0 nho) (+ y0 R))) t "SD-KHUAT"))
    (setq k (1+ k))))

;; Mo ta ngan 1 phuong an
(defun sd:st-name (kieu)
  (cond ((= kieu "Thang") "Thang (mui nho ra)")
        ((= kieu "V45") "Ghep vat 45 do")
        ((= kieu "Roi") "Dai mui roi")
        (t "Mui bo / vat CNC")))

;; ---- Mat bang cau thang (hinh thang nhanh de doi chieu): ve, chieu nghi, bac quat ----
(defun sd:pp (p u d) (list (+ (car p) (* d (car u))) (+ (cadr p) (* d (cadr u)))))

;; Quat tu tam c, ban kinh trong r0 / ngoai r1, tu goc a0 den a1 (rad): da giac
(defun sd:st-sector (c r0 r1 a0 a1 / pts k m)
  (setq m 6 k 0)
  (while (<= k m)
    (setq pts (cons (sd:pp c (list (cos (+ a0 (* k (/ (- a1 a0) m)))) (sin (+ a0 (* k (/ (- a1 a0) m))))) r1) pts) k (1+ k)))
  (setq k m)
  (if (> r0 1.0)
    (while (>= k 0)
      (setq pts (cons (sd:pp c (list (cos (+ a0 (* k (/ (- a1 a0) m)))) (sin (+ a0 (* k (/ (- a1 a0) m))))) r0) pts) k (1- k)))
    (setq pts (cons c pts)))
  (reverse pts))

;; Hinh mat bang: danh sach ('P pts lay) polyline kin, ('L p1 p2 lay) doan, ('T p chu); toa do cuc bo, bac dau tai goc 0,0, huong +X.
;; dang "L" re trai moi lan re / "U" quay dau; chieu nghi cnl x cnw (0 = o vuong W x W, U: W x (2W + 50)); bac quat chi o lan re dau
(defun sd:st-plan (n gd W nve dang cnl cnw nq gq ri ro / out p u v k len a b c d i s th a0 j u2 p2 cl cw)
  (setq p (list 0.0 0.0) u (list 1.0 0.0) k 0 len (* n gd))
  (while (< k nve)
    (setq v (list (- (cadr u)) (car u)) a p b (sd:pp a u len) c (sd:pp b v W) d (sd:pp a v W))
    (setq out (cons (list 'P (list a b c d) "SD-GACH") out) i 1)
    (while (< i n)
      (setq out (cons (list 'L (sd:pp a u (* i gd)) (sd:pp (sd:pp a u (* i gd)) v W) "SD-GACH-VIEN") out) i (1+ i)))
    (setq out (cons (list 'T (sd:pp (sd:pp a u (/ len 2.0)) v (/ W 2.0)) (strcat "VE " (itoa (1+ k)) ": " (itoa n) " BAC")) out))
    (if (or (< (1+ k) nve) (and (= nve 1) (> nq 0) (= k 0)))
      (progn
        (cond
          ;; bac quat o lan re trai dau tien
          ((and (> nq 0) (= k 0) (/= dang "U"))
           (setq s ro th (/ (* gq (/ pi 180.0)) nq) a0 (- (atan (cadr u) (car u)) (/ pi 2.0)) j 0)
           (while (< j nq)
             (setq out (cons (list 'P (sd:st-sector (sd:pp b v s) ri s (+ a0 (* j th)) (+ a0 (* (1+ j) th))) "SD-GACH-CAT") out) j (1+ j)))
           (setq out (cons (list 'T (sd:pp (sd:pp b v (/ s 2.0)) u (/ s 2.0)) (strcat (itoa nq) " BAC QUAT")) out)
                 p2 (sd:pp (sd:pp b u s) v s) u2 v))
          ((= dang "U")
           (setq cl (if (> cnl 0.0) cnl W) cw (if (> cnw 0.0) cnw (+ (* 2.0 W) 50.0)))
           (setq out (cons (list 'P (list b (sd:pp b u cl) (sd:pp (sd:pp b u cl) v cw) (sd:pp b v cw)) "SD-GACH-CAT") out)
                 out (cons (list 'T (sd:pp (sd:pp b u (/ cl 2.0)) v (/ cw 2.0)) "CHIEU NGHI") out)
                 p2 (sd:pp b v cw) u2 (list (- (car u)) (- (cadr u)))))
          (t
           (setq cl (if (> cnl 0.0) cnl W) cw (if (> cnw 0.0) cnw W))
           (setq out (cons (list 'P (list b (sd:pp b u cl) (sd:pp (sd:pp b u cl) v cw) (sd:pp b v cw)) "SD-GACH-CAT") out)
                 out (cons (list 'T (sd:pp (sd:pp b u (/ cl 2.0)) v (/ cw 2.0)) "CHIEU NGHI") out)
                 p2 (sd:pp (sd:pp b u cl) v cw) u2 v)))
        (setq p p2 u u2)))
    (setq k (1+ k)))
  (reverse out))

;; Khung bao cac phan tu mat bang: ((xmin ymin) (xmax ymax))
(defun sd:st-pbb (items / pts)
  (foreach it items
    (cond ((= (car it) 'P) (setq pts (append pts (cadr it))))
          ((= (car it) 'L) (setq pts (append pts (list (cadr it) (caddr it)))))
          (t (setq pts (append pts (list (cadr it)))))))
  (sd:bbox pts))

(defun sd:st-pdraw (items dx dy ds)
  (foreach it items
    (cond ((= (car it) 'P) (sd:pline (mapcar '(lambda (q) (list (+ dx (car q)) (+ dy (cadr q)) 0.0)) (cadr it)) t (caddr it)))
          ((= (car it) 'L) (sd:line (list (+ dx (car (cadr it))) (+ dy (cadr (cadr it))) 0.0) (list (+ dx (car (caddr it))) (+ dy (cadr (caddr it))) 0.0) (cadddr it)))
          (t (sd:text (list (+ dx (car (cadr it))) (+ dy (cadr (cadr it))) 0.0) (caddr it) (* 2.5 ds) "MC" "SD-CHU")))))

(defun c:SDTHANGDA (/ mat n W gd R tm tc kieu nho rm led ledv Lmax gap nside hl SL SB trim kerf rot q pcs nest sm tot
                      cmp k pc pn sm2 tt pt ds y0 x0 i l key lays g tp bx base rowh col maxw idx used th lines fn f
                      thks e vb Htot nve cnl cnw nq gq ri ro nst cmf dang plan bb dq rc dk ledr leds ledc)
  (sd:begin)
  (if (not (sd:dlg "Cau thang da (SDTHANGDA)"
                   (list (list "mat" "Ma vat lieu" 'str (sd:cfg "ST-MAT" "DA"))
                         (list "n" "So bac (moi ve thang)" 'int (sd:cfg "ST-N" 16))
                         (list "W" "Be rong bac (mm)" 'real (sd:cfg "ST-W" 1200.0))
                         (list "gd" "Buoc dap - mat ngoai co bac nay den co bac ke (mm)" 'real (sd:cfg "ST-T" 280.0))
                         (list "R" "Chieu cao bac (mm)" 'real (sd:cfg "ST-R" 165.0))
                         (list "tm" "Day mat bac (mm)" 'real (sd:cfg "ST-TM" 30.0))
                         (list "tc" "Day co bac / len (mm)" 'real (sd:cfg "ST-TC" 20.0))
                         (list "kieu" "Kieu mui bac" 'kw (sd:cfg "ST-KIEU" "Thang")
                               '(("Thang" . "Thang: mat chong len co, mui nho ra")
                                 ("V45" . "V45: mat va co ghep vat 45 do")
                                 ("Roi" . "Roi: dai mui cat rieng")
                                 ("CNC" . "CNC: mat lien, mui bo / vat bang CNC")))
                         (list "nho" "Mui nho ra khoi mat co bac (mm)" 'real0 (sd:cfg "ST-NHO" 30.0)
                               nil '("kieu" "Thang" "Roi" "CNC"))
                         (list "rm" "Dai mui roi - be rong (mm)" 'real (sd:cfg "ST-RM" 50.0) nil '("kieu" "Roi"))
                         (list "led" "Khe hat LED (mm, 0 = khong)" 'real0 (sd:cfg "ST-LED" 0.0))
                         (list "ledv" "Khe LED tru vao" 'kw (sd:cfg "ST-LEDV" "Cobac")
                               '(("Cobac" . "Chieu cao co bac")
                                 ("Matbac" . "Chieu sau mat bac")
                                 ("Ranh" . "Khong tru, cat ranh duoi mat bac (CNC)")
                                 ("Hoc" . "Hoc LED duoi mep truoc mat bac (CNC, khong tru kich thuoc)")))
                         (list "ledr" "Hoc LED - rong (mm)" 'real (sd:cfg "ST-LEDR" 17.0) nil '("ledv" "Hoc"))
                         (list "leds" "Hoc LED - sau vao mat bac (mm)" 'real (sd:cfg "ST-LEDS" 20.0) nil '("ledv" "Hoc"))
                         (list "ledc" "Hoc LED - cach mep truoc mat bac (mm)" 'real0 (sd:cfg "ST-LEDC" 20.0) nil '("ledv" "Hoc"))
                         (list "nside" "Len chan tuong - so ben (0 = khong)" 'int0 (sd:cfg "ST-NSIDE" 2))
                         (list "hl" "Len chan tuong - be rong dai (mm)" 'real0 (sd:cfg "ST-HL" 100.0))
                         (list "Lmax" "Vien dai toi da (mm, dai hon se chia)" 'real (sd:cfg "ST-LMAX" 2400.0))
                         (list "gap" "Mach giua cac vien chia (mm)" 'real0 (sd:cfg "ST-GAP" 2.0))
                         (list "Htot" "Tong chieu cao thang (mm, 0 = nhap chieu cao bac)" 'real0 (sd:cfg "ST-H" 0.0))
                         (list "nve" "So ve thang (2 = chu L / chu U, moi ve 'So bac' bac)" 'int (sd:cfg "ST-NVE" 1))
                         (list "dang" "Hinh thang khi nhieu ve" 'kw (sd:cfg "ST-DANG" "L")
                               '(("L" . "Chu L: re trai moi lan re") ("U" . "Chu U: quay dau o chieu nghi")))
                         (list "cnl" "Chieu nghi - dai (mm, 0 = khong)" 'real0 (sd:cfg "ST-CNL" 0.0))
                         (list "cnw" "Chieu nghi - rong (mm)" 'real0 (sd:cfg "ST-CNW" 0.0))
                         (list "nq" "So bac quat (0 = khong)" 'int0 (sd:cfg "ST-NQ" 0))
                         (list "gq" "Bac quat - tong goc quay (do)" 'real0 (sd:cfg "ST-GQ" 90.0))
                         (list "ri" "Bac quat - ban kinh trong (mm)" 'real0 (sd:cfg "ST-RI" 50.0))
                         (list "ro" "Bac quat - ban kinh ngoai (mm)" 'real (sd:cfg "ST-RO" 1200.0))
                         (list "dq" "Co bac quat" 'kw (sd:cfg "ST-DQ" "Thang")
                               '(("Thang" . "Thang: tam thang theo canh truoc (ban kinh)")
                                 ("Cong" . "Cong: tam cong cat tu phoi day bang CNC")
                                 ("Doan" . "Doan: ghep cac tam thang theo cung")))
                         (list "rc" "Co bac quat cong - ban kinh cung (mm)" 'real (sd:cfg "ST-RC" 1200.0) nil '("dq" "Cong" "Doan"))
                         (list "dk" "Co bac quat ghep doan - rong toi da 1 doan (mm)" 'real (sd:cfg "ST-DK" 250.0) nil '("dq" "Doan"))
                         (list "SL" "Tam da tho - dai (mm)" 'real (sd:cfg "SLABL" 2700.0))
                         (list "SB" "Tam da tho - rong (mm)" 'real (sd:cfg "SLABB" 1800.0))
                         (list "trim" "Xen bien moi canh (mm)" 'real0 (sd:cfg "SLABTRIM" 20.0))
                         (list "kerf" "Be rong luoi cat (mm)" 'real0 (sd:cfg "SLABKERF" 3.0))
                         (list "rot" "Cho xoay vien 90 do (khong giu chieu van)" 'tog (sd:cfg "ST-ROT" t))
                         (list "q" "Do ky khi xep" 'kw (cond (*SD:DTQ*) ("Canbang"))
                               '(("Nhanh" . "Nhanh: 1 cach xep") ("Canbang" . "Can bang: thu nhieu to hop")
                                 ("Ky" . "Ky: them leo doi hoan doi thu tu")))
                         (list "cmp" "So sanh ca 4 kieu mui bac (so tam da can)" 'tog t)
                         (list "ve" "Ve mat cat, so do cat va cac vien (co du lieu SD_TILE cho SDDATHO)" 'tog t)
                         (list "ds" "Ty le ve so do 1/" 'int (cond (*SD:DTSC*) (50))))))
    (exit))
  (setq mat (sd:cfg-put "ST-MAT" (sd:v "mat")) n (sd:cfg-put "ST-N" (sd:v "n"))
        W (sd:cfg-put "ST-W" (sd:v "W")) gd (sd:cfg-put "ST-T" (sd:v "gd")) R (sd:cfg-put "ST-R" (sd:v "R"))
        tm (sd:cfg-put "ST-TM" (sd:v "tm")) tc (sd:cfg-put "ST-TC" (sd:v "tc"))
        kieu (sd:cfg-put "ST-KIEU" (sd:v "kieu")) nho (sd:cfg-put "ST-NHO" (cond ((sd:v "nho")) (0.0)))
        rm (sd:cfg-put "ST-RM" (cond ((sd:v "rm")) (50.0)))
        led (sd:cfg-put "ST-LED" (sd:v "led")) ledv (sd:cfg-put "ST-LEDV" (sd:v "ledv"))
        ledr (sd:cfg-put "ST-LEDR" (cond ((sd:v "ledr")) (17.0))) leds (sd:cfg-put "ST-LEDS" (cond ((sd:v "leds")) (20.0)))
        ledc (sd:cfg-put "ST-LEDC" (cond ((sd:v "ledc")) (20.0)))
        nside (sd:cfg-put "ST-NSIDE" (sd:v "nside")) hl (sd:cfg-put "ST-HL" (sd:v "hl"))
        Lmax (sd:cfg-put "ST-LMAX" (sd:v "Lmax")) gap (sd:cfg-put "ST-GAP" (sd:v "gap"))
        SL (sd:cfg-put "SLABL" (sd:v "SL")) SB (sd:cfg-put "SLABB" (sd:v "SB"))
        trim (sd:cfg-put "SLABTRIM" (sd:v "trim")) kerf (sd:cfg-put "SLABKERF" (sd:v "kerf"))
        Htot (sd:cfg-put "ST-H" (sd:v "Htot")) nve (sd:cfg-put "ST-NVE" (sd:v "nve"))
        dang (sd:cfg-put "ST-DANG" (cond ((sd:v "dang")) ("L")))
        cnl (sd:cfg-put "ST-CNL" (sd:v "cnl")) cnw (sd:cfg-put "ST-CNW" (sd:v "cnw"))
        nq (sd:cfg-put "ST-NQ" (sd:v "nq")) gq (sd:cfg-put "ST-GQ" (sd:v "gq"))
        ri (sd:cfg-put "ST-RI" (sd:v "ri")) ro (sd:cfg-put "ST-RO" (sd:v "ro"))
        dq (sd:cfg-put "ST-DQ" (cond ((sd:v "dq")) ("Thang")))
        rc (sd:cfg-put "ST-RC" (cond ((sd:v "rc")) (1200.0))) dk (sd:cfg-put "ST-DK" (cond ((sd:v "dk")) (250.0)))
        rot (sd:cfg-put "ST-ROT" (sd:v "rot")) q (sd:v "q") *SD:DTQ* q
        ds (float (sd:v "ds")) *SD:DTSC* (fix ds)
        q (cond ((= q "Nhanh") 0) ((= q "Ky") 2) (t 1)))
  ;; tong chieu cao -> chia bac: so bac thang + bac quat, chieu cao bac deu
  (if (> Htot 0.0)
    (progn
      (setq nst (max 1 (fix (+ 0.5 (/ Htot R)))) R (/ Htot nst)
            n (max 1 (fix (+ 0.999999 (/ (float (max 1 (- nst nq))) nve)))))
      (princ (strcat "\n[SD] Tong cao " (sd:num Htot) " mm chia " (itoa nst) " bac (gom " (itoa nq) " bac quat): cao bac "
                     (sd:rtos R 1) " mm, " (itoa nve) " ve x " (itoa n) " bac thang"))))
  ;; cong thuc buoc do: 2R + T trong khoang 600 - 640 mm
  (setq cmf (+ (* 2.0 R) gd))
  (if (or (< cmf 600.0) (> cmf 640.0))
    (princ (strcat "\n [!] 2R + T = " (sd:rtos cmf 0) " mm ngoai khoang 600 - 640 mm di thoai mai; buoc dap goi y " (sd:rtos (- 630.0 (* 2.0 R)) 0) " mm."))
    (princ (strcat "\n 2R + T = " (sd:rtos cmf 0) " mm: dat (600 - 640 mm).")))
  (if (> R 190.0) (princ (strcat "\n [!] Chieu cao bac " (sd:rtos R 1) " mm lon hon 190 mm, kiem tra quy chuan.")))
  (cond
    ((>= led (- R tm)) (princ "\n[SD] Khe LED lon hon chieu cao co bac, kiem tra lai so lieu."))
    ((and (= ledv "Hoc") (>= leds tm)) (princ (strcat "\n[SD] Hoc LED sau " (sd:num leds) " mm >= day mat bac " (sd:num tm) " mm: se xuyen thung mat bac, giam do sau hoac tang day mat bac.")))
    ((and (= ledv "Hoc") (> (+ ledc ledr) (+ gd nho))) (princ "\n[SD] Hoc LED vuot ra ngoai chieu sau mat bac, giam khoang cach tu mep hoac be rong hoc."))
    ((<= (- (+ gd nho) (if (= kieu "Roi") rm 0.0) (if (and (> led 0.0) (= ledv "Matbac")) led 0.0)) 0.0)
     (princ "\n[SD] Mat bac co chieu sau <= 0, kiem tra mui nho / dai mui roi / khe LED."))
    (t
     (setq pcs (sd:st-all kieu n W gd R tm tc nho rm led ledv Lmax gap nside hl nve cnl cnw nq gq ri ro dq rc dk)
           nest (sd:st-nest pcs SL SB trim kerf rot q)
           sm (sd:st-sum nest) tot (sd:st-tot pcs))
     (princ (strcat "\n=== CAU THANG DA " mat ": " (itoa n) " bac, be rong " (sd:num W) ", buoc dap " (sd:num gd)
                    ", cao " (sd:num R) ", mui " (sd:st-name kieu)
                    (if (> led 0.0) (strcat ", khe LED " (sd:num led) " (" ledv ")") "") " ==="))
     (princ "\n Ma  Ten               Dai x Rong (mm)     So luong  Day  Goc cat  Ghi chu")
     (foreach p pcs
       (princ (strcat "\n " (car p) "  " (cadr p) "   " (sd:rtos (nth 2 p) 1) " x " (sd:rtos (nth 3 p) 1)
                      "   x " (itoa (fix (+ 0.5 (nth 4 p)))) "   " (sd:num (nth 5 p)) "   " (sd:rtos (nth 6 p) 1) "   " (nth 7 p))))
     (if (and (= kieu "V45") (not (equal tm tc 0.01)))
       (princ "\n [!] Mat bac va co bac khac do day: ghep vat 45 do se bi lech nac, nen dung cung do day."))
     (princ (strcat "\n Phoi tong " (sd:rtos (car tot) 2) " m2 (thanh pham " (sd:rtos (cadddr tot) 2) " m2); vat 45 do " (sd:rtos (cadr tot) 1) " m; CNC / ranh "
                    (sd:rtos (caddr tot) 1) " m"))
     (princ (strcat "\n Ra da: " (itoa (car sm)) " tam " (sd:num SL) "x" (sd:num SB) " (" (sd:rtos (/ (cadr sm) 1e6) 2) " m2 tho), "
                    "hieu suat " (sd:rtos (if (> (cadr sm) 0) (/ (* 100.0 (caddr sm)) (cadr sm)) 0.0) 1) "%"
                    (if (> (cadddr sm) 0) (strcat ", CHUA XEP " (itoa (cadddr sm)) " vien (qua kho tam)") "")))
     ;; so sanh cac kieu mui bac
     (if (sd:v "cmp")
       (progn
         (princ "\n So sanh phuong an (cung so lieu):")
         (foreach kk '("Thang" "V45" "Roi" "CNC")
           (setq pc (sd:st-all kk n W gd R tm tc nho rm led ledv Lmax gap nside hl nve cnl cnw nq gq ri ro dq rc dk)
                 pn (sd:st-nest pc SL SB trim kerf rot q)
                 sm2 (sd:st-sum pn) tt (sd:st-tot pc))
           (princ (strcat "\n  " (if (= kk kieu) "> " "  ") (sd:st-name kk) ": " (itoa (car sm2)) " tam, hieu suat "
                          (sd:rtos (if (> (cadr sm2) 0) (/ (* 100.0 (caddr sm2)) (cadr sm2)) 0.0) 1) "%, vat 45 "
                          (sd:rtos (cadr tt) 1) " m, CNC " (sd:rtos (caddr tt) 1) " m"
                          (if (> (cadddr sm2) 0) " - CHUA XEP DU" ""))))))
     ;; ve
     (if (and (sd:v "ve") (setq pt (sd:getpt "\nDiem chen ban ve cau thang da (goc trai tren): " nil)))
       (progn
         (setq x0 (car pt) y0 (cadr pt))
         (sd:text (list x0 y0) (strcat "C\\U+1EA6U THANG \\U+0110\\U+00C1 " mat " - " (itoa n) " B\\U+1EACC - M\\U+0168I " (strcase (sd:st-name kieu))) (* 3.5 ds) "L" "SD-CHU")
         (setq y0 (- y0 (* 6 ds)))
         ;; mat bang thang: ve, chieu nghi, bac quat
         (setq plan (sd:st-plan n gd W nve dang cnl cnw nq gq ri ro) bb (sd:st-pbb plan))
         (sd:st-pdraw plan (- x0 (car (car bb))) (- y0 (cadr (cadr bb))) ds)
         (sd:text (list x0 (- y0 (- (cadr (cadr bb)) (cadr (car bb))) (* 4 ds)))
                  (strcat "M\\U+1EB6T B\\U+1EB0NG THANG: " (itoa nve) " v\\U+1EBF \\U+00D7 " (itoa n) " b\\U+1EADc" (if (> nq 0) (strcat ", " (itoa nq) " b\\U+1EADc qu\\U+1EA1t") ""))
                  (* 2.5 ds) "L" "SD-CHU")
         (setq y0 (- y0 (- (cadr (cadr bb)) (cadr (car bb))) (* 14 ds)))
         ;; mat cat 3 bac
         (sd:st-profile (list x0 (- y0 (* 3.0 R)) 0.0) kieu gd R tm tc nho rm led ledv ledr leds ledc)
         (sd:text (list x0 (- y0 (* 3.0 R) (* 4 ds)))
                  (strcat "M\\U+1EB6T C\\U+1EAET 3 B\\U+1EACC: m\\U+1EB7t b\\U+1EADc d\\U+00E0y " (sd:num tm) ", c\\U+1ED5 b\\U+1EADc d\\U+00E0y " (sd:num tc)
                          (if (> led 0.0) (strcat ", khe LED " (sd:num led)) ""))
                  (* 2.5 ds) "L" "SD-CHU")
         (setq y0 (- y0 (* 3.0 R) (* 14 ds)))
         ;; danh sach cac vien co du lieu SD_TILE (dung duoc SDGACHTK, SDDATHO voi kho / tam du, SDGIACONG)
         (setq x0 (car pt) rowh 0.0 col 0)
         (foreach p pcs
           (repeat (fix (+ 0.5 (nth 4 p)))
             (if (> (+ (- x0 (car pt)) (nth 2 p)) 12000.0)
               (setq x0 (car pt) y0 (- y0 rowh (* 4 ds)) rowh 0.0))
             (sd:rect (list x0 (- y0 (nth 3 p)) 0.0) (nth 2 p) (nth 3 p) "SD-GACH-CAT")
             (sd:put-xd (entlast) (sd:tile-xd mat "C" (strcat mat "-" (car p)) (nth 2 p) (nth 3 p)
                                              (* (nth 2 p) (nth 3 p)) 0 mat (nth 2 p) (nth 3 p) 0.0 (nth 5 p) "R"))
             (sd:text (list (+ x0 (/ (nth 2 p) 2.0)) (- y0 (/ (nth 3 p) 2.0))) (car p) (min (* 2.0 ds) (* 0.4 (nth 3 p))) "MC" "SD-CHU")
             (setq x0 (+ x0 (nth 2 p) (* 2 ds)) rowh (max rowh (nth 3 p)))))
         (setq y0 (- y0 rowh (* 14 ds)))
         ;; so do cat da tho
         (foreach g nest
           (setq lays nil)
           (foreach s (cadr g)
             (setq key (vl-princ-to-string (cons (caddr s) (cadr s))))
             (if (setq l (assoc key lays))
               (setq lays (subst (list key (1+ (cadr l)) (caddr l)) l lays))
               (setq lays (cons (list key 1 s) lays))))
           (setq lays (reverse lays))
           (sd:text (list (car pt) y0)
                    (strcat "S\\U+01A0 \\U+0110\\U+1ED2 C\\U+1EAET \\U+0110\\U+00C1 TH\\U+00D4 d\\U+00E0y " (sd:num (car g)) ": " (itoa (length (cadr g))) " t\\U+1EA5m")
                    (* 3.5 ds) "L" "SD-CHU")
           (setq y0 (- y0 (* 12 ds)) x0 (car pt) rowh 0.0 idx 0 maxw 14000.0)
           (foreach l lays
             (setq tp (assoc (caddr (caddr l)) (caddr g)) idx (1+ idx)
                   used (apply '+ (mapcar '(lambda (p) (* (nth 3 p) (nth 4 p))) (cadr (caddr l)))))
             (if (and (> x0 (car pt)) (> (+ (- x0 (car pt)) (nth 4 tp)) maxw))
               (setq x0 (car pt) y0 (- y0 rowh (* 12 ds)) rowh 0.0))
             (setq bx x0 base (- y0 (nth 5 tp)) rowh (max rowh (nth 5 tp)))
             (sd:rect (list bx base 0.0) (nth 4 tp) (nth 5 tp) "SD-GIACONG")
             (sd:rect (list (+ bx trim) (+ base trim) 0.0) (- (nth 4 tp) trim trim) (- (nth 5 tp) trim trim) "SD-KHUAT")
             (foreach p (cadr (caddr l))
               (sd:rect (list (+ bx trim (nth 1 p)) (+ base trim (nth 2 p)) 0.0) (nth 3 p) (nth 4 p) "SD-GACH-CAT")
               (sd:text (list (+ bx trim (nth 1 p) (/ (nth 3 p) 2)) (+ base trim (nth 2 p) (/ (nth 4 p) 2)))
                        (strcat (car p) " " (sd:rtos (nth 3 p) 0) "\\U+00D7" (sd:rtos (nth 4 p) 0))
                        (max (* 0.6 ds) (min (* 2.0 ds) (* 0.25 (min (nth 3 p) (nth 4 p))))) "MC" "SD-CHU")
               (setq lines (cons (sd:join (list mat (sd:num (car g)) (itoa idx) (itoa (cadr l)) (car p)
                                                (sd:rtos (nth 1 p) 0) (sd:rtos (nth 2 p) 0)
                                                (sd:rtos (nth 3 p) 0) (sd:rtos (nth 4 p) 0)
                                                (if (= (nth 5 p) 1) "Co" "Khong")) ";")
                                 lines)))
             (sd:text (list bx (+ y0 (* 2 ds)))
                      (strcat "T\\U+1EA4M " (itoa idx) " (\\U+00D7" (itoa (cadr l)) ") s\\U+1EED d\\U+1EE5ng "
                              (sd:rtos (/ (* 100.0 used) (* (nth 4 tp) (nth 5 tp))) 1) "%")
                      (* 2.5 ds) "L" "SD-CHU")
             (setq x0 (+ x0 (nth 4 tp) (* 0.15 (nth 4 tp)))))
           (setq y0 (- y0 rowh (* 20 ds))))))
     ;; CSV: bang vien va so do cat
     (setq fn (sd:csv-name "_CauThangDa.csv"))
     (if (setq f (sd:open fn "w"))
       (progn
         (write-line "sep=;" f)
         (write-line "Ma;Ten;Dai (mm);Rong (mm);So luong;Day (mm);Goc cat (do);Vat 45 moi vien (mm);CNC moi vien (mm);Ghi chu" f)
         (foreach p pcs
           (write-line (sd:join (list (car p) (cadr p) (sd:rtos (nth 2 p) 1) (sd:rtos (nth 3 p) 1) (itoa (fix (+ 0.5 (nth 4 p))))
                                      (sd:num (nth 5 p)) (sd:rtos (nth 6 p) 1) (sd:rtos (nth 8 p) 1) (sd:rtos (nth 9 p) 1) (nth 7 p)) ";")
                       f))
         (write-line "" f)
         (write-line "Ma VL;Day tam;Tam so;So tam giong;Ma vien;x (mm);y (mm);Rong (mm);Cao (mm);Xoay" f)
         (foreach l (reverse lines) (write-line l f))
         (setq fn (sd:close f))
         (princ (strcat "\n[SD] Da xuat: " fn))))))
  (sd:finish))

;;; ==========================================================================
;;;  COFFA (VAN KHUON): mong, cot, vach, vach thang may, thang bo
;;;  He: van phu phim -> suon (thep hop) -> gong / suon chinh (2 thep hop) -> ty ren / cay chong
;;; ==========================================================================
(setq *SD:FWDEF*
  '(("PLYT" . 18.0) ("PLYE" . 5500.0) ("PLYF" . 13.0) ("SHW" . 1220.0) ("SHH" . 2440.0)
    ("SEC" . "50x50x1.4") ("PRI" . "50x100x1.4") ("PRIN" . 2) ("FS" . 210.0)
    ("TIE" . 40.0) ("TIED" . 16.0) ("PROP" . 15.0) ("DEF" . 400.0)
    ("GAM" . 25.0) ("R" . 2.0) ("TC" . 25.0) ("CC" . 1.0) ("MET" . "ACI")
    ("S1MAX" . 400.0) ("S2MAX" . 1000.0) ("S3MAX" . 1200.0)))

(defun sd:fw (key) (sd:cfg (strcat "FW-" key) (cdr (assoc key *SD:FWDEF*))))

;; Thep hop "50x100x1.4" -> (b h t); h = chieu cao chiu uon
(defun sd:box (s / l)
  (setq l (mapcar 'atof (sd:split (strcase s t) "x")))
  (if (and (= (length l) 3) (> (caddr l) 0)) l '(50.0 50.0 1.4)))
(defun sd:box-I (s / b h tw)
  (setq b (car s) h (cadr s) tw (caddr s))
  (/ (- (* b h h h) (* (- b tw tw) (expt (- h tw tw) 3))) 12.0))
(defun sd:box-kg (s) (* 0.00785 (- (* 2 (caddr s) (+ (car s) (cadr s))) (* 4 (caddr s) (caddr s)))))

(defun sd:clampv (x lo hi) (max lo (min hi x)))
(defun sd:floor50 (x) (* 50.0 (fix (/ x 50.0))))

;; Vi tri chia deu tren doan L, cach 2 dau e, khoang <= s
(defun sd:evenpos (L s e / n d r i)
  (if (<= (- L e e) 1e-6)
    (list (/ L 2.0))
    (progn
      (setq n (max 1 (fix (+ (/ (- L e e) s) 0.999999))) d (/ (- L e e) n) i 0)
      (repeat (1+ n) (setq r (cons (+ e (* i d)) r) i (1+ i)))
      (reverse r))))

;; Ap luc ngang be tong tuoi (kPa), H = chieu cao do (mm), wall = T voi vach.
;; ACI 347: cot  p = Cc(7.2 + 785R/(T+17.8)) <= 150;
;;          vach R<=2.1 va H<=4.2m: nhu cot (<=100); R<=4.5: Cc(7.2 + 1156/(T+17.8) + 244R/(T+17.8)) <= 100
;;          R>4.5: thuy tinh. Luon >= 30 kPa va <= gamma.H.  "Thuytinh": p = gamma.H
(defun sd:fw-pressure (H wall / g rr tc cc ph p)
  (setq g (sd:fw "GAM") rr (sd:fw "R") tc (sd:fw "TC") cc (sd:fw "CC") ph (* g (/ H 1000.0)))
  (if (= (sd:fw "MET") "Thuytinh")
    ph
    (progn
      (setq p (cond ((and wall (> rr 4.5)) ph)
                    ((and wall (or (> rr 2.1) (> H 4200.0)))
                     (min 100.0 (* cc (+ 7.2 (/ 1156.0 (+ tc 17.8)) (/ (* 244.0 rr) (+ tc 17.8))))))
                    (wall (min 100.0 (* cc (+ 7.2 (/ (* 785.0 rr) (+ tc 17.8))))))
                    (t (min 150.0 (* cc (+ 7.2 (/ (* 785.0 rr) (+ tc 17.8))))))))
      (min ph (max p 30.0)))))

;; Nhip lon nhat dam lien tuc 3 nhip: uon M = qL2/10 <= f.W ; vong 0.0069qL4/EI <= L/def
(defun sd:fw-span (q W I f E def)
  (min (sqrt (/ (* 10.0 f W) q))
       (expt (/ (* E I) (* 0.0069 q def)) (/ 1.0 3.0))))

;; Thiet ke khoang cach: p (kPa), cap = suc chiu ty / cay chong (kN)
;; -> (s1 = suon, s2 = gong/suon chinh, s3 = ty/chong doc gong, luc 1 ty kN)
(defun sd:fw-design (p cap / q tp sec pri n ip wp s1 s2 s3)
  (setq q  (/ p 1000.0) tp (sd:fw "PLYT")
        s1 (sd:clampv (sd:floor50 (sd:fw-span q (/ (* tp tp) 6.0) (/ (* tp tp tp) 12.0)
                                              (sd:fw "PLYF") (sd:fw "PLYE") (sd:fw "DEF")))
                      100.0 (sd:fw "S1MAX"))
        sec (sd:box (sd:fw "SEC"))
        s2 (sd:clampv (sd:floor50 (sd:fw-span (* q s1) (/ (* 2.0 (sd:box-I sec)) (cadr sec)) (sd:box-I sec)
                                              (sd:fw "FS") 2.1e5 (sd:fw "DEF")))
                      200.0 (sd:fw "S2MAX"))
        pri (sd:box (sd:fw "PRI")) n (sd:fw "PRIN")
        ip (* n (sd:box-I pri)) wp (/ (* 2.0 ip) (cadr pri))
        s3 (sd:clampv (sd:floor50 (sd:fw-span (* q s2) wp ip (sd:fw "FS") 2.1e5 (sd:fw "DEF")))
                      200.0 (sd:fw "S3MAX")))
  (if (> (* q s2 s3) (* 1000.0 cap)) (setq s3 (max 200.0 (sd:floor50 (/ (* 1000.0 cap) (* q s2))))))
  (list s1 s2 s3 (/ (* q s2 s3) 1000.0)))

(defun sd:fw-note (p sp captxt)
  (strcat "p = " (sd:rtos p 1) " kPa (" (if (= (sd:fw "MET") "Thuytinh") "th\\U+1EE7y t\\U+0129nh"
                                            (strcat "ACI 347, R=" (sd:num (sd:fw "R")) " m/h, T=" (sd:num (sd:fw "TC")) "\\U+00B0C"))
          "); v\\U+00E1n " (sd:num (sd:fw "PLYT")) "mm; s\\U+01B0\\U+1EDDn " (sd:fw "SEC") " @" (sd:num (car sp))
          "; g\\U+00F4ng/s\\U+01B0\\U+1EDDn ch\\U+00EDnh " (itoa (sd:fw "PRIN")) "\\U+00D7" (sd:fw "PRI") " @" (sd:num (cadr sp))
          "; " captxt " @" (sd:num (caddr sp)) " (" (sd:rtos (cadddr sp) 1) " kN)"))

;;; --------------------------------------------------------------------------
;;;  Thong ke coffa: (dt-van tam-nguyen tam-cat dt-cat dai-suon dai-gong so-ty dai-ty so-chong)
;;; --------------------------------------------------------------------------
(defun sd:fwq0 () (list 0.0 0 0 0.0 0.0 0.0 0 0.0 0))
(defun sd:fwq+ (a b) (mapcar '+ a b))
(defun sd:fwq* (a k) (mapcar '(lambda (x) (* x k)) a))
(defun sd:fwq-set (q i v) (sd:replace-nth i (+ (nth i q) v) q))

;; Mat dung 1 mat coffa. o = goc trai duoi, L x H, sp = khoang cach, opens = ((x y w h)...),
;; tx = vi tri ty tren moi gong (nil = khong ty), ys = cao do gong (nil = tu chia). Tra ve thong ke.
(defun sd:fw-panel (o L H sp opens tx ys sc title / shw shh x y ww hh nf nc ca xs sec pri prin
                      ntie inop q)
  (setq shw (sd:fw "SHW") shh (sd:fw "SHH") nf 0 nc 0 ca 0.0
        sec (sd:box (sd:fw "SEC")) pri (sd:box (sd:fw "PRI")) prin (sd:fw "PRIN") ntie 0)
  ;; tam van 1220x2440 dat dung, tu goc trai duoi
  (setq x 0.0)
  (while (< x (- L 1.0))
    (setq y 0.0 ww (min shw (- L x)))
    (while (< y (- H 1.0))
      (setq hh (min shh (- H y)))
      (sd:rect (sd:p+ o x y) ww hh "SD-CF-VAN")
      (if (and (equal ww shw 0.5) (equal hh shh 0.5))
        (setq nf (1+ nf))
        (progn (setq nc (1+ nc) ca (+ ca (* ww hh)))
               (sd:text (sd:p+ o (+ x (/ ww 2)) (+ y (/ hh 2))) (strcat (sd:rtos ww 0) "\\U+00D7" (sd:rtos hh 0))
                        (* 1.6 sc) "MC" "SD-CF-VAN")))
      (setq y (+ y shh)))
    (setq x (+ x shw)))
  ;; suon dung
  (setq xs (sd:evenpos L (car sp) (/ (car sec) 2.0)))
  (foreach x xs (sd:rect (sd:p+ o (- x (/ (car sec) 2.0)) 0) (car sec) H "SD-CF-SUON"))
  ;; gong / suon chinh ngang (2 thep hop, khe 20 cho ty)
  (if (null ys) (setq ys (sd:evenpos H (cadr sp) (min 200.0 (/ (cadr sp) 2.0)))))
  (foreach y ys
    (sd:rect (sd:p+ o -100 (+ y 10)) (+ L 200) (car pri) "SD-CF-GONG")
    (if (> prin 1) (sd:rect (sd:p+ o -100 (- y 10 (car pri))) (+ L 200) (car pri) "SD-CF-GONG"))
    (foreach x tx
      (setq inop (vl-some '(lambda (r) (and (< (car r) x (+ (car r) (caddr r))) (< (cadr r) y (+ (cadr r) (cadddr r))))) opens))
      (if (not inop)
        (progn
          (sd:circle (sd:p+ o x y) (max 15.0 (* 0.8 sc)) "SD-CF-TY")
          (sd:line (sd:p+ o (- x (* 1.2 sc)) y) (sd:p+ o (+ x (* 1.2 sc)) y) "SD-CF-TY")
          (setq ntie (1+ ntie))))))
  ;; lo mo
  (foreach r opens
    (sd:rect (sd:p+ o (car r) (cadr r)) (caddr r) (cadddr r) "SD-KHUAT")
    (sd:line (sd:p+ o (car r) (cadr r)) (sd:p+ o (+ (car r) (caddr r)) (+ (cadr r) (cadddr r))) "SD-KHUAT")
    (sd:line (sd:p+ o (car r) (+ (cadr r) (cadddr r))) (sd:p+ o (+ (car r) (caddr r)) (cadr r)) "SD-KHUAT")
    (sd:text (sd:p+ o (+ (car r) (/ (caddr r) 2)) (+ (cadr r) (/ (cadddr r) 2)))
             (strcat "L\\U+1ED6 " (sd:rtos (caddr r) 0) "\\U+00D7" (sd:rtos (cadddr r) 0)) (* 2.0 sc) "MC" "SD-CHU"))
  ;; kich thuoc
  (sd:use-dimstyle sc)
  (sd:dimchain (mapcar '(lambda (y) (sd:p+ o 0 y)) (append '(0.0) ys (list H))) "V" (sd:p+ o (* -10 sc) 0))
  (sd:dim o (sd:p+ o 0 H) "V" (sd:p+ o (* -18 sc) 0))
  (if (and tx (vl-every '(lambda (x) (<= 0 x L)) tx))
    (sd:dimchain (mapcar '(lambda (x) (sd:p+ o x 0)) (append '(0.0) tx (list L))) "H" (sd:p+ o 0 (* -10 sc))))
  (sd:dim o (sd:p+ o L 0) "H" (sd:p+ o 0 (* -18 sc)))
  (sd:text (sd:p+ o 0 (+ H (* 5 sc))) title (* 3.0 sc) "L" "SD-CHU")
  (sd:text (sd:p+ o 0 (+ H (* 1.5 sc))) (strcat "S\\U+01B0\\U+1EDDn @" (sd:num (car sp)) "; g\\U+00F4ng @" (sd:num (cadr sp))
                                                (if tx (strcat "; ty @" (sd:num (caddr sp))) ""))
           (* 2.0 sc) "L" "SD-CHU")
  ;; thong ke
  (setq q (list (- (* L H) (apply '+ (cons 0.0 (mapcar '(lambda (r) (* (caddr r) (cadddr r))) opens))))
                nf nc ca (* H (length xs)) (* prin (+ L 200) (length ys)) ntie 0.0 0))
  q)

;; Bang khoi luong coffa + ghi CSV (them vao file chung cua ban ve)
;; Dang ky khoi luong coffa (XDATA "SD_VK") len tieu de bang khoi luong coffa e.
;; *SD:VKID* = (ten-cau-kien loai be-tong-m3 lenh) do lenh coffa dat truoc khi ve bang.
;; rows: ((hang-muc quy-cach don-vi khoi-luong) ...); o trong -> lay theo dong tren.
(defun sd:vk-reg (e rows area / id hm qc xd)
  (if (and e (setq id *SD:VKID*))
    (progn
      (setq hm "" qc "")
      (foreach r rows
        (if (/= (vl-string-trim " " (car r)) "") (setq hm (vl-string-trim " " (car r))))
        (if (/= (cadr r) "") (setq qc (cadr r)))
        ;; bo dong khoi luong = 0 (vd van san khi chi ve dam)
        (if (not (equal (distof (cadddr r) 2) 0.0 1e-9))
          (setq xd (cons (cons 1000 (sd:join (list hm (if (= (car r) "") qc (cadr r)) (caddr r) (cadddr r)) "|")) xd))))
      (entmod (append (entget e)
                      (list (list -3 (append (list "SD_VK" (cons 1000 (car id)) (cons 1000 (cadr id)) (cons 1000 (cadddr id))
                                                   (cons 1040 area) (cons 1040 (caddr id)))
                                             (reverse xd)
                                             ;; tang hien hanh (dong dac biet "@T|tang")
                                             (if (and *SD:TANG* (/= *SD:TANG* "")) (list (cons 1000 (strcat "@T|" *SD:TANG*)))))))))
      (princ (strcat "\n[SD] Da dang ky khoi luong coffa " (car id) ": van khuon " (sd:rtos area 2) " m2"
                     (if (> (caddr id) 0) (strcat ", be tong " (sd:rtos (caddr id) 3) " m3") "") " (SDKL xuat Excel).")))))

(defun sd:fw-table (pt name q tieL nprop sc / shw shh sec pri nsh rows fn f e0)
  (setq shw (sd:fw "SHW") shh (sd:fw "SHH") sec (sd:box (sd:fw "SEC")) pri (sd:box (sd:fw "PRI"))
        nsh (+ (nth 1 q) (fix (+ (/ (* 1.15 (nth 3 q)) (* shw shh)) 0.999999))))
  (setq rows (list (list "V\\U+00E1n ph\\U+1EE7 phim" (strcat "d\\U+00E0y " (sd:num (sd:fw "PLYT")) ", " (sd:num shw) "\\U+00D7" (sd:num shh)) "m\\U+00B2" (sd:rtos (/ (car q) 1e6) 2))
                   (list "  T\\U+1EA5m nguy\\U+00EAn / t\\U+1EA5m c\\U+1EAFt" "" "t\\U+1EA5m" (strcat (itoa (nth 1 q)) " / " (itoa (nth 2 q))))
                   (list "  S\\U+1ED1 t\\U+1EA5m c\\U+1EA7n c\\U+1EA5p" "c\\U+1EAFt +15%" "t\\U+1EA5m" (itoa nsh))
                   (list "S\\U+01B0\\U+1EDDn" (strcat "h\\U+1ED9p " (sd:fw "SEC")) "m" (sd:rtos (/ (nth 4 q) 1000.0) 1))
                   (list "" "" "kg" (sd:rtos (* (/ (nth 4 q) 1000.0) (sd:box-kg sec)) 1))
                   (list "G\\U+00F4ng / s\\U+01B0\\U+1EDDn ch\\U+00EDnh" (strcat "h\\U+1ED9p " (sd:fw "PRI")) "m" (sd:rtos (/ (nth 5 q) 1000.0) 1))
                   (list "" "" "kg" (sd:rtos (* (/ (nth 5 q) 1000.0) (sd:box-kg pri)) 1))))
  (if (> (nth 6 q) 0)
    (setq rows (append rows (list (list "Ty ren + b\\U+00E1t chu\\U+1ED3n" (strcat "D" (sd:num (sd:fw "TIED")) ", L=" (sd:rtos tieL 0)) "b\\U+1ED9" (itoa (nth 6 q)))))))
  (if (> nprop 0)
    (setq rows (append rows (list (list "C\\U+00E2y ch\\U+1ED1ng" (strcat "SC " (sd:num (sd:fw "PROP")) " kN") "c\\U+00E2y" (itoa nprop))))))
  (if pt
    (progn
      (setq e0 (entlast))
      (sd:table2 pt (strcat "KH\\U+1ED0I L\\U+01AF\\U+1EE2NG COFFA " name)
                 '(("H\\U+1EA0NG M\\U+1EE4C" 50) ("QUY C\\U+00C1CH" 44) ("\\U+0110V" 12) ("KH\\U+1ED0I L\\U+01AF\\U+1EE2NG" 26))
                 (mapcar '(lambda (r) (list "R" r nil)) rows) -1 sc)
      (sd:vk-reg (if e0 (entnext e0) (entnext)) rows (/ (car q) 1e6))))
  (setq fn (sd:csv-name "_KhoiLuongCoffa.csv"))
  (if (setq f (sd:open fn "a"))
    (progn
      (foreach r rows
        (write-line (sd:join (cons name (mapcar '(lambda (s) (vl-string-subst "m2" "m\\U+00B2" s)) r)) ";") f))
      (setq fn (sd:close f))
      (princ (strcat "\n[SD] Da ghi them vao: " fn)))))

;; Mat bang 1 mat coffa doc doan a->b (mat be tong), nv = goc phap tuyen ra ngoai
(defun sd:fw-faceplan (a b nv sp / tp sec pri fa L)
  (setq tp (sd:fw "PLYT") sec (sd:box (sd:fw "SEC")) pri (sd:box (sd:fw "PRI"))
        fa (angle a b) L (distance a b))
  (sd:pline (list a b (polar b nv tp) (polar a nv tp)) t "SD-CF-VAN")
  (foreach s (sd:evenpos L (car sp) (/ (car sec) 2.0))
    (sd:pline (mapcar '(lambda (p) (polar (polar a fa (+ s (car p))) nv (cadr p)))
                      (list (list (/ (car sec) -2) tp) (list (/ (car sec) 2) tp)
                            (list (/ (car sec) 2) (+ tp (cadr sec))) (list (/ (car sec) -2) (+ tp (cadr sec)))))
              t "SD-CF-SUON"))
  (sd:pline (mapcar '(lambda (p) (polar (polar a fa (car p)) nv (cadr p)))
                    (list (list -100 (+ tp (cadr sec))) (list (+ L 100) (+ tp (cadr sec)))
                          (list (+ L 100) (+ tp (cadr sec) (cadr pri))) (list -100 (+ tp (cadr sec) (cadr pri)))))
            t "SD-CF-GONG"))

;; Ty xuyen vach tai diem p (tren mat 1), xuyen qua be day t theo huong nv (vao trong vach)
;; Ty xuyen vach tai diem p (tren mat 1), xuyen qua be day t1 theo huong nv; co bat chuon 2 dau
(defun sd:fw-tieplan (p nv t1 / ext e1 e2)
  (setq ext (+ (sd:fw "PLYT") (cadr (sd:box (sd:fw "SEC"))) (cadr (sd:box (sd:fw "PRI"))) 80.0)
        e1  (polar p (+ nv pi) (- ext 30.0))
        e2  (polar p nv (+ t1 ext -30.0)))
  (sd:line (polar p (+ nv pi) ext) (polar p nv (+ t1 ext)) "SD-CF-TY")
  (foreach e (list e1 e2)
    (sd:line (polar e (+ nv (/ pi 2)) 50.0) (polar e (- nv (/ pi 2)) 50.0) "SD-CF-TY")))

;;; --------------------------------------------------------------------------
;;;  SDCOFFASET - Thong so coffa
;;; --------------------------------------------------------------------------
(defun c:SDCOFFASET (/ v sp p)
  (sd:begin)
  (if (not (sd:dlg "Thong so coffa (SDCOFFASET)"
                   (mapcar '(lambda (f) (list (car f) (cadr f) (caddr f) (sd:fw (car f)) (cadddr f)))
                           '(("PLYT" "Van phu phim - chieu day (mm)" real)
                             ("PLYE" "Van - modun dan hoi E (MPa)" real)
                             ("PLYF" "Van - ung suat uon cho phep (MPa)" real)
                             ("SHW" "Kho tam van - rong (mm)" real)
                             ("SHH" "Kho tam van - dai (mm)" real)
                             ("SEC" "Suon - thep hop bxhxt (mm)" str)
                             ("PRI" "Gong / suon chinh - thep hop bxhxt" str)
                             ("PRIN" "So thanh thep hop ghep cho gong" int)
                             ("FS" "Thep hop - ung suat cho phep (MPa)" real)
                             ("TIED" "Ty ren - duong kinh (mm)" real)
                             ("TIE" "Ty ren - tai trong cho phep (kN)" real)
                             ("PROP" "Cay chong - tai trong cho phep (kN)" real)
                             ("DEF" "Do vong cho phep L/..." real)
                             ("MET" "Ap luc ngang be tong" kw (("ACI" . "ACI 347") ("Thuytinh" . "Thuy tinh gamma.H")))
                             ("GAM" "Trong luong rieng be tong (kN/m3)" real)
                             ("R" "Toc do do theo chieu cao (m/h)" real)
                             ("TC" "Nhiet do be tong (do C)" real)
                             ("CC" "He so Cc (1.0 PC; 1.2 phu gia cham dong)" real)
                             ("S1MAX" "Khoang cach suon toi da (mm)" real)
                             ("S2MAX" "Khoang cach gong toi da (mm)" real)
                             ("S3MAX" "Khoang cach ty / chong toi da (mm)" real)))))
    (exit))
  (foreach f *SD:FV* (sd:cfg-put (strcat "FW-" (car f)) (cdr f)))
  (foreach h '(1000.0 3300.0 4500.0)
    (setq p (sd:fw-pressure h t) sp (sd:fw-design p (sd:fw "TIE")))
    (princ (strcat "\n  Vach cao " (sd:num (/ h 1000.0)) " m: p = " (sd:rtos p 1) " kPa -> suon @" (sd:num (car sp))
                   ", gong @" (sd:num (cadr sp)) ", ty @" (sd:num (caddr sp)) " (" (sd:rtos (cadddr sp) 1) " kN)")))
  (sd:finish))

;;; --------------------------------------------------------------------------
;;;  SDCOFFACOT - Coffa cot chu nhat
;;; --------------------------------------------------------------------------
(defun c:SDCOFFACOT (/ sc name bx by hc p sp tp sec pri lc mida midb pt o d wa ex q qa qb ys nlev ntie tieL tx)
  (sd:begin)
  (if (not (sd:dlg "Coffa cot (SDCOFFACOT)"
                   (list (list "name" "Ten cot" 'str (cond (*SD:FCN*) ("C1")))
                         (list "bx" "Canh b - theo X (mm)" 'real (cond (*SD:FCB*) (400.0)))
                         (list "by" "Canh h - theo Y (mm)" 'real (cond (*SD:FCH*) (600.0)))
                         (list "hc" "Chieu cao do be tong (mm)" 'real (cond (*SD:FCHH*) (3300.0)))
                         (list "sc" "Ty le ve 1/" 'int 25))))
    (exit))
  (setq name (sd:v "name") bx (sd:v "bx") by (sd:v "by") hc (sd:v "hc") sc (float (sd:v "sc"))
        *SD:FCN* name *SD:FCB* bx *SD:FCH* by *SD:FCHH* hc)
  (setq p  (sd:fw-pressure hc nil)
        sp (sd:fw-design p (sd:fw "TIE"))
        tp (sd:fw "PLYT") sec (sd:box (sd:fw "SEC")) pri (sd:box (sd:fw "PRI"))
        d  (+ tp (cadr sec))
        ;; nhip gong = canh cot + 2 lop van, suon + ty goc; vuot s3 -> them ty xuyen cot
        mida (max 0 (1- (fix (+ (/ (+ bx (* 2 d) 120.0) (caddr sp)) 0.999999))))
        midb (max 0 (1- (fix (+ (/ (+ by (* 2 d) 120.0) (caddr sp)) 0.999999)))))
  (if (setq pt (sd:getpt "\nTam cot tren mat bang chi tiet: " nil))
    (progn
      (setq o (sd:p+ pt (/ bx -2.0) (/ by -2.0)))
      ;; ---- mat bang
      (sd:rect o bx by "SD-BETONG")
      (sd:fw-faceplan (sd:p+ o (- tp) 0) (sd:p+ o (+ bx tp) 0) (* 1.5 pi) sp)
      (sd:fw-faceplan (sd:p+ o (+ bx tp) by) (sd:p+ o (- tp) by) (* 0.5 pi) sp)
      (sd:fw-faceplan (sd:p+ o 0 by) (sd:p+ o 0 0) pi sp)
      (sd:fw-faceplan (sd:p+ o bx 0) (sd:p+ o bx by) 0.0 sp)
      (setq ex (+ d (cadr pri) 60.0))
      (foreach c (list (sd:p+ o (- ex) (- ex)) (sd:p+ o (+ bx ex) (- ex)) (sd:p+ o (+ bx ex) (+ by ex)) (sd:p+ o (- ex) (+ by ex)))
        (sd:circle c 15.0 "SD-CF-TY"))
      (foreach x (cdr (reverse (cdr (sd:evenpos bx (/ bx (1+ mida)) 0.0))))
        (sd:fw-tieplan (sd:p+ o x 0) (* 0.5 pi) by))
      (foreach y (cdr (reverse (cdr (sd:evenpos by (/ by (1+ midb)) 0.0))))
        (sd:fw-tieplan (sd:p+ o 0 y) 0.0 bx))
      (sd:use-dimstyle sc)
      (sd:dim o (sd:p+ o bx 0) "H" (sd:p+ o 0 (- (+ ex (* 8 sc)))))
      (sd:dim o (sd:p+ o 0 by) "V" (sd:p+ o (- (+ ex (* 8 sc))) 0))
      (sd:text (sd:p+ o 0 (- (+ ex (* 18 sc)))) (strcat "M\\U+1EB6T B\\U+1EB0NG COFFA C\\U+1ED8T " name " (" (sd:num bx) "\\U+00D7" (sd:num by) ")")
               (* 3.0 sc) "L" "SD-CHU")
      ;; ---- mat dung 2 mat (mat b co phu 2 lop van, mat h nam trong)
      (setq wa (+ bx tp tp) ys (sd:evenpos hc (cadr sp) (min 200.0 (/ (cadr sp) 2.0))) nlev (length ys))
      (setq tx (append (list -60.0) (cdr (reverse (cdr (sd:evenpos wa (/ wa (1+ mida)) 0.0)))) (list (+ wa 60.0))))
      (setq qa (sd:fw-panel (sd:p+ pt (+ (/ bx 2.0) ex (* 30 sc)) (/ by -2.0)) wa hc sp nil tx ys sc
                            (strcat "M\\U+1EB6T \\U+0110\\U+1EE8NG COFFA C\\U+1ED8T " name " - M\\U+1EB6T b (\\U+00D72)")))
      (setq tx (append (list (- -60.0 tp)) (cdr (reverse (cdr (sd:evenpos by (/ by (1+ midb)) 0.0)))) (list (+ by tp 60.0))))
      (setq qb (sd:fw-panel (sd:p+ pt (+ (/ bx 2.0) ex (* 60 sc) wa) (/ by -2.0)) by hc sp nil tx ys sc
                            (strcat "M\\U+1EB6T \\U+0110\\U+1EE8NG COFFA C\\U+1ED8T " name " - M\\U+1EB6T h (\\U+00D72)")))
      (setq q    (sd:fwq+ (sd:fwq* qa 2) (sd:fwq* qb 2))
            ntie (* nlev (+ 4 mida midb))
            q    (sd:replace-nth 6 ntie q)
            tieL (+ (max bx by) (* 2 (+ d (cadr pri))) 250.0))
      (sd:text (sd:p+ o 0 (- (+ ex (* 23 sc)))) (sd:fw-note p sp "ty") (* 2.0 sc) "L" "SD-CHU")
      (setq *SD:VKID* (list name "Cot" (/ (* bx by hc) 1e9) "SDCOFFACOT"))
      (sd:fw-table (sd:p+ pt (+ (/ bx 2.0) ex (* 90 sc) wa by) (+ (/ by -2.0) hc)) (strcat "C\\U+1ED8T " name) q tieL 4 sc)
      (sd:use-dimstyle *SD:SCALE*)
      (princ (strcat "\n[SD] Cot " name ": p = " (sd:rtos p 1) " kPa, suon @" (sd:num (car sp)) ", gong @"
                     (sd:num (cadr sp)) ", ty @" (sd:num (caddr sp)) " (" (sd:rtos (cadddr sp) 1) " kN)"
                     (if (> (+ mida midb) 0) (strcat "; them " (itoa (+ mida midb)) " ty xuyen cot moi gong") "")))))
  (sd:finish))

;;; --------------------------------------------------------------------------
;;;  Vach: mat bang + mat cat + mat dung (dung cho vach ham, vach thang may)
;;; --------------------------------------------------------------------------
;; Mat cat dung qua vach: o = chan mat 1, day tw, cao hc, hai-mat?, ys cao do gong
(defun sd:fw-wallsection (o tw hc two ys sc / tp sec pri ext x1 x2 yb)
  (setq tp (sd:fw "PLYT") sec (sd:box (sd:fw "SEC")) pri (sd:box (sd:fw "PRI"))
        ext (+ tp (cadr sec) (cadr pri)))
  (sd:rect o tw hc "SD-BETONG")
  (foreach side (if two '(-1 1) '(-1))
    (setq x1 (if (< side 0) (car o) (+ (car o) tw)))
    (sd:rect (list (if (< side 0) (- x1 tp) x1) (cadr o)) tp hc "SD-CF-VAN")
    (sd:rect (list (if (< side 0) (- x1 tp (cadr sec)) (+ x1 tp)) (cadr o)) (cadr sec) hc "SD-CF-SUON")
    (foreach y ys
      (sd:rect (list (if (< side 0) (- x1 ext) (+ x1 tp (cadr sec))) (+ (cadr o) y (- (car pri))))
               (cadr pri) (* 2 (car pri)) "SD-CF-GONG")))
  (if two
    (foreach y ys
      (sd:line (sd:p+ o (- (+ ext 80)) y) (sd:p+ o (+ tw ext 80) y) "SD-CF-TY")
      (sd:rect (sd:p+ o (- (+ ext 20)) (- y 50)) 20 100 "SD-CF-TY")
      (sd:rect (sd:p+ o (+ tw ext) (- y 50)) 20 100 "SD-CF-TY"))
    ;; 1 mat: chong xien 60 do tu gong o 2/3 va 1/3 chieu cao xuong san
    (foreach y (list (sd:near ys (* 0.75 hc)) (sd:near ys (* 0.35 hc)))
      (if y
        (progn
          (setq x2 (- (car o) ext (/ y (/ (sin (/ pi 3)) (cos (/ pi 3))))))
          (sd:line (sd:p+ o (- ext) y) (list x2 (cadr o)) "SD-CF-CHONG")
          (sd:rect (list (- x2 100) (- (cadr o) 20)) 200 20 "SD-CF-CHONG")))))
  (sd:text (sd:p+ o (/ tw 2) (* -12 sc)) (if two "M\\U+1EB6T C\\U+1EAET V\\U+00C1CH (2 M\\U+1EB6T, TY XUY\\U+00CAN)" "M\\U+1EB6T C\\U+1EAET V\\U+00C1CH (1 M\\U+1EB6T, CH\\U+1ED0NG XI\\U+00CAN)")
           (* 2.5 sc) "MC" "SD-CHU"))

(defun sd:near (lst v / best)
  (foreach x lst (if (or (null best) (< (abs (- x v)) (abs (- best v)))) (setq best x)))
  best)

;; "x,y,w,h;x,y,w,h" -> ((x y w h) ...)
(defun sd:parse-opens (s / r l)
  (foreach tok (sd:split s ";")
    (setq l (mapcar 'atof (sd:split (vl-string-trim " " tok) ",")))
    (if (and (= (length l) 4) (> (caddr l) 0) (> (cadddr l) 0)) (setq r (cons l r))))
  (reverse r))

;;; --------------------------------------------------------------------------
;;;  SDCOFFAVACH - Coffa vach / vach ham (1 hoac 2 mat), co lo mo
;;; --------------------------------------------------------------------------
(defun c:SDCOFFAVACH (/ sc name lw tw hc two opens p sp cap pt o tx q ys nprop tieL ex)
  (sd:begin)
  (if (not (sd:dlg "Coffa vach / vach ham (SDCOFFAVACH)"
                   (list (list "name" "Ten vach" 'str (cond (*SD:FWN*) ("V1")))
                         (list "lw" "Chieu dai vach (mm)" 'real (cond (*SD:FWL*) (6000.0)))
                         (list "tw" "Chieu day vach (mm)" 'real (cond (*SD:FWT*) (300.0)))
                         (list "hc" "Chieu cao do (mm)" 'real (cond (*SD:FWH*) (3500.0)))
                         (list "two" "Kieu coffa" 'kw "Haimat"
                               '(("Haimat" . "2 mat, ty xuyen") ("Motmat" . "1 mat (vach ham), chong xien")))
                         (list "op" "Lo mo x,y,rong,cao;... (mm, de trong neu khong)" 'str "")
                         (list "sc" "Ty le ve 1/" 'int 50))))
    (exit))
  (setq name (sd:v "name") lw (sd:v "lw") tw (sd:v "tw") hc (sd:v "hc") two (/= (sd:v "two") "Motmat"))
  (setq opens (sd:parse-opens (sd:v "op"))
        sc    (float (sd:v "sc"))
        *SD:FWN* name *SD:FWL* lw *SD:FWT* tw *SD:FWH* hc)
  (setq cap (if two (sd:fw "TIE") (sd:fw "PROP"))
        p   (sd:fw-pressure hc t)
        sp  (sd:fw-design p cap))
  (if (setq pt (sd:getpt "\nDiem chen (goc trai duoi mat bang vach): " nil))
    (progn
      (setq ex (+ (sd:fw "PLYT") (cadr (sd:box (sd:fw "SEC"))) (cadr (sd:box (sd:fw "PRI")))))
      ;; ---- mat bang
      (setq o pt)
      (sd:rect o lw tw "SD-BETONG")
      (sd:fw-faceplan o (sd:p+ o lw 0) (* 1.5 pi) sp)
      (if two (sd:fw-faceplan (sd:p+ o lw tw) (sd:p+ o 0 tw) (* 0.5 pi) sp))
      ;; van dau vach
      (sd:rect (sd:p+ o (- (sd:fw "PLYT")) 0) (sd:fw "PLYT") tw "SD-CF-VAN")
      (sd:rect (sd:p+ o lw 0) (sd:fw "PLYT") tw "SD-CF-VAN")
      (setq tx (sd:evenpos lw (caddr sp) (min 300.0 (/ (caddr sp) 2.0))))
      (if two (foreach x tx (sd:fw-tieplan (sd:p+ o x 0) (* 0.5 pi) tw)))
      (sd:text (sd:p+ o 0 (- (+ ex (* 12 sc)))) (strcat "M\\U+1EB6T B\\U+1EB0NG COFFA V\\U+00C1CH " name " (d\\U+00E0y " (sd:num tw) ")")
               (* 3.0 sc) "L" "SD-CHU")
      ;; ---- mat dung + mat cat
      (setq ys (sd:evenpos hc (cadr sp) (min 200.0 (/ (cadr sp) 2.0))))
      (setq q (sd:fw-panel (sd:p+ o 0 (+ tw ex (* 40 sc))) lw hc sp opens tx ys sc
                           (strcat "M\\U+1EB6T \\U+0110\\U+1EE8NG COFFA V\\U+00C1CH " name (if two " (m\\U+1EB7t 1, m\\U+1EB7t 2 t\\U+01B0\\U+01A1ng t\\U+1EF1)" ""))))
      (sd:fw-wallsection (sd:p+ o (+ lw (* 40 sc) (if two 0 (* 0.6 hc))) (+ tw ex (* 40 sc))) tw hc two ys sc)
      ;; thong ke: 2 mat + dau vach + thanh lo
      (if two (setq q (sd:fwq* q 2)))
      (setq q (sd:fwq-set q 0 (+ (* 2 tw hc)
                                 (apply '+ (cons 0.0 (mapcar '(lambda (r) (* 2 tw (+ (caddr r) (cadddr r)))) opens)))))
            tieL (+ tw (* 2 ex) 250.0)
            nprop (if two 0 (* 2 (length tx))))
      (if (not two) (setq q (sd:replace-nth 6 0 q)))
      (sd:text (sd:p+ o 0 (- (+ ex (* 17 sc)))) (sd:fw-note p sp (if two "ty" "ch\\U+1ED1ng")) (* 2.0 sc) "L" "SD-CHU")
      (setq *SD:VKID* (list name "Vach"
                            (/ (* tw (- (* lw hc) (apply '+ (cons 0.0 (mapcar '(lambda (r) (* (caddr r) (cadddr r))) opens))))) 1e9)
                            "SDCOFFAVACH"))
      (sd:fw-table (sd:p+ o (+ lw (* 40 sc) (* 1.2 hc) (* 30 sc)) (+ tw ex (* 40 sc) hc)) (strcat "V\\U+00C1CH " name) q tieL nprop sc)
      (sd:use-dimstyle *SD:SCALE*)))
  (sd:finish))

;;; --------------------------------------------------------------------------
;;;  SDCOFFATM - Coffa vach thang may (hop loi trong + mat ngoai, lo cua)
;;; --------------------------------------------------------------------------
;;; --------------------------------------------------------------------------
;;;  SDCOFFATM - che do chon mat bang thang may tren ban ve: polyline mat trong long gieng (hinh bat ky,
;;;  1 hoac nhieu gieng) + polyline mat ngoai loi (hoac offset 1 chieu day vach). Moi canh trong = 1 mat vach;
;;;  cua: chon 2 mep cua tren mat vach. Sinh mat bang coffa (van, suon, gong, ty, goc) + mat dung tung mat
;;;  trong + bang khoi luong (mat ngoai quy doi theo chu vi ngoai / chu vi trong).
;;; --------------------------------------------------------------------------
;; Dien tich co dau cua da giac (> 0: nguoc chieu kim dong ho)
(defun sd:parea (pts / s)
  (setq s 0.0)
  (mapcar '(lambda (p q) (setq s (+ s (- (* (car p) (cadr q)) (* (car q) (cadr p))))))
          pts (append (cdr pts) (list (car pts))))
  (/ s 2.0))
;; Dinh polyline kin -> danh sach diem 2D nguoc chieu kim dong ho, bo dinh trung
(defun sd:poly-ccw (e / pts r)
  (setq pts (mapcar '(lambda (p) (list (car p) (cadr p))) (car (sd:tm-pts e))))
  (foreach p pts (if (or (null r) (> (distance p (car r)) 1.0)) (setq r (cons p r))))
  (setq r (reverse r))
  (if (and (cdr r) (< (distance (car r) (last r)) 1.0)) (setq r (reverse (cdr (reverse r)))))
  (if (< (sd:parea r) 0) (reverse r) r))
;; Canh da giac CCW -> ((a b phap-tuyen L) ...); trong = phap tuyen vao trong (ben trai), ngoai = ra ngoai
(defun sd:poly-walls (pts inner / r)
  (mapcar '(lambda (a b) (setq r (cons (list (append a '(0.0)) (append b '(0.0))
                                             (+ (angle a b) (if inner (* 0.5 pi) (* -0.5 pi))) (distance a b))
                                       r)))
          pts (append (cdr pts) (list (car pts))))
  (reverse r))
(defun sd:perim (pts) (apply '+ (mapcar 'distance pts (append (cdr pts) (list (car pts))))))
;; Offset polyline e ra phia ngoai mot doan d -> diem CCW (doi tuong tam bi xoa)
(defun sd:poly-out (e d / o best r)
  (setq o (vlax-ename->vla-object e))
  (foreach s (list d (- d))
    (if (not (vl-catch-all-error-p (setq r (vl-catch-all-apply 'vla-Offset (list o s)))))
      (foreach n (sd:sa->list r)
        (if (or (null best) (> (vla-get-Area n) (vla-get-Area best)))
          (progn (if best (vla-Delete best)) (setq best n))
          (vla-Delete n)))))
  (if best (progn (setq r (sd:poly-ccw (vlax-vla-object->ename best))) (vla-Delete best) r)))
;; Diem p -> (chi-so-canh vi-tri-doc-canh) canh gan nhat
(defun sd:wall-at (walls p / i best d a b t1 q)
  (setq i 0)
  (foreach w walls
    (setq a (car w) b (cadr w)
          t1 (max 0.0 (min (cadddr w) (* (cos (- (angle a p) (angle a b))) (distance a p))))
          q (polar a (angle a b) t1) d (distance (list (car q) (cadr q)) (list (car p) (cadr p))) i (1+ i))
    (if (or (null best) (< d (car best))) (setq best (list d i t1))))
  (cdr best))

(defun sd:cftm-real (name tw hc dh sc / ss i e shafts outs opts walls ws doors p1 p2 w1 w2 sp ex o L opens tx ys qt q x0 y0 n
                                        pin pout a b nv k vin tlen nd bb)
  (princ "\nChon polyline kin MAT TRONG long gieng thang may (1 hoac nhieu gieng): ")
  (if (setq ss (ssget '((0 . "LWPOLYLINE") (-4 . "&") (70 . 1))))
    (progn
      (setq i 0)
      (repeat (sslength ss) (setq shafts (append shafts (list (sd:poly-ccw (ssname ss i)))) i (1+ i)))
      ;; mat ngoai: chon, hoac offset (1 gieng)
      (initget "Offset")
      (setq e (entsel (strcat "\nChon polyline MAT NGOAI loi [Offset = offset mat trong " (sd:num tw) " mm] <Offset>: ")))
      (setq outs (cond ((and e (listp e) (= (cdr (assoc 0 (entget (car e)))) "LWPOLYLINE")) (sd:poly-ccw (car e)))
                       ((sd:poly-out (ssname ss 0) tw))))
      (if (and (> (length shafts) 1) (or (null e) (not (listp e))))
        (princ "\n[SD] Nhieu gieng: nen chon polyline mat ngoai ca loi (dang lay offset gieng thu nhat)."))
      ;; tat ca mat trong
      (setq walls (apply 'append (mapcar '(lambda (s) (sd:poly-walls s t)) shafts)))
      ;; danh so canh tren mat bang de chon cua
      (setq i 0)
      (foreach w walls
        (setq i (1+ i))
        (sd:text (polar (mapcar '(lambda (x y) (/ (+ x y) 2.0)) (car w) (cadr w)) (caddr w) (* 4.0 sc))
                 (strcat "V" (itoa i)) (* 2.5 sc) "MC" "SD-CHU"))
      ;; cua: 2 mep cua tren mat vach, lap
      (while (and (setq p1 (sd:getpt "\nCua: chon mep cua thu nhat tren mat trong vach <het cua>: " nil))
                  (setq p2 (sd:getpt "\nMep cua thu hai: " p1)))
        (setq w1 (sd:wall-at walls p1) w2 (sd:wall-at walls p2))
        (if (= (car w1) (car w2))
          (setq doors (cons (list (car w1) (min (cadr w1) (cadr w2)) (abs (- (cadr w2) (cadr w1)))) doors))
          (princ "\n[SD] 2 mep cua phai cung 1 mat vach - bo qua.")))
      (setq sp (sd:fw-design (sd:fw-pressure hc t) (sd:fw "TIE"))
            ex (+ (sd:fw "PLYT") (cadr (sd:box (sd:fw "SEC"))) (cadr (sd:box (sd:fw "PRI")))))
      ;; ---- mat bang: van + suon + gong mat trong / ngoai, ty, goc trong, cua
      (foreach w walls (sd:fw-faceplan (car w) (cadr w) (caddr w) sp))
      (foreach w (sd:poly-walls outs nil) (sd:fw-faceplan (car w) (cadr w) (caddr w) sp))
      (setq i 0)
      (foreach w walls
        (setq i (1+ i) a (car w) b (cadr w) L (cadddr w) nv (+ (caddr w) pi)
              ws (vl-remove-if-not '(lambda (dd) (= (car dd) i)) doors))
        (foreach x (sd:evenpos L (caddr sp) (min 300.0 (/ (caddr sp) 2.0)))
          (if (not (vl-some '(lambda (dd) (< (- (cadr dd) 50) x (+ (cadr dd) (caddr dd) 50))) ws))
            (sd:fw-tieplan (polar a (angle a b) x) nv tw)))
        (foreach dd ws
          (sd:pline (list (polar a (angle a b) (cadr dd)) (polar a (angle a b) (+ (cadr dd) (caddr dd)))
                          (polar (polar a (angle a b) (+ (cadr dd) (caddr dd))) nv tw) (polar (polar a (angle a b) (cadr dd)) nv tw))
                    t "SD-KHUAT")
          (sd:text (polar (polar a (angle a b) (+ (cadr dd) (/ (caddr dd) 2))) nv (/ tw 2)) "C\\U+1EECA" (* 2.0 sc) "MC" "SD-CHU")))
      ;; goc trong loi (dinh loi cua da giac CCW): thep goc L
      (foreach s shafts
        (mapcar '(lambda (pp p pn)
                   (if (> (sd:turn pp p pn) 0)
                     (sd:pline (list (polar p (angle p pp) 150.0) p (polar p (angle p pn) 150.0)) nil "SD-CF-GONG")))
                (cons (last s) s) s (append (cdr s) (list (car s)))))
      (setq bb (list (apply 'min (mapcar 'car outs)) (apply 'min (mapcar 'cadr outs)) (apply 'max (mapcar 'car outs)) (apply 'max (mapcar 'cadr outs)))
            o (list (car bb) (cadr bb) 0.0))
      (sd:text (sd:p+ o 0 (- (+ ex (* 12 sc)))) (strcat "M\\U+1EB6T B\\U+1EB0NG COFFA L\\U+00D5I THANG M\\U+00C1Y " name " (theo m\\U+1EB7t b\\U+1EB1ng ch\\U+1ECDn)") (* 3.0 sc) "L" "SD-CHU")
      ;; ---- mat dung tung mat trong
      (setq ys (sd:evenpos hc (cadr sp) (min 200.0 (/ (cadr sp) 2.0)))
            x0 (+ (caddr bb) ex (* 40 sc)) y0 (cadr bb) qt (sd:fwq0) i 0)
      (sd:use-dimstyle sc)
      (foreach w walls
        (setq i (1+ i) L (cadddr w)
              opens (mapcar '(lambda (dd) (list (cadr dd) 0.0 (caddr dd) dh)) (vl-remove-if-not '(lambda (dd) (= (car dd) i)) doors))
              tx (sd:evenpos L (caddr sp) (min 300.0 (/ (caddr sp) 2.0))))
        (setq q (sd:fw-panel (list x0 y0 0.0) L hc sp opens tx ys sc
                             (strcat "M\\U+1EB6T TRONG V\\U+00C1CH V" (itoa i) (if opens " (c\\U+00F3 c\\U+1EEDa)" ""))))
        (setq qt (sd:fwq+ qt q) x0 (+ x0 L (* 30 sc))))
      ;; mat ngoai: quy doi theo ty le chu vi ngoai / trong (ty dem 1 lan), cong ma cua
      (setq pin (apply '+ (mapcar 'sd:perim shafts)) pout (sd:perim outs)
            tlen (nth 6 qt) k (/ pout pin)
            qt (sd:fwq+ qt (sd:fwq* (sd:replace-nth 6 0 qt) k))
            qt (sd:replace-nth 6 tlen qt) nd 0)
      (foreach dd doors (setq qt (sd:fwq-set qt 0 (* tw (+ (caddr dd) dh dh))) nd (1+ nd)))
      (setq vin (apply '+ (mapcar 'sd:parea shafts)))
      (sd:wall-note o tw ex sc (sd:fw-pressure hc t) sp)
      (setq *SD:VKID* (list name "Vach" (/ (- (* (- (sd:parea outs) vin) hc) (apply '+ (mapcar '(lambda (dd) (* (caddr dd) dh tw)) doors))) 1e9) "SDCOFFATM"))
      (sd:fw-table (list x0 (+ y0 hc) 0.0) (strcat "L\\U+00D5I THANG M\\U+00C1Y " name) qt (+ tw (* 2 ex) 250.0) 0 sc)
      (sd:use-dimstyle *SD:SCALE*)
      (princ (strcat "\n[SD] " (itoa (length shafts)) " gieng, " (itoa (length walls)) " mat vach trong (chu vi " (sd:num pin)
                     " mm), chu vi ngoai " (sd:num pout) " mm, " (itoa nd) " cua.")))
    (princ "\n[SD] Khong chon duoc polyline kin.")))

(defun c:SDCOFFATM (/ sc name lx ly tw hc dw dh dside doff p sp pt o i walls L opens q qt tx ys tieL ex x0 y0 a b nv tlen)
  (sd:begin)
  (if (not (sd:dlg "Coffa loi thang may (SDCOFFATM)"
                   (list (list "nguon" "Hinh dang loi" 'kw (cond (*SD:TMSRC*) ("Nhap"))
                               '(("Nhap" . "Nhap kich thuoc (long gieng chu nhat)") ("Banve" . "Chon mat bang thang may tren ban ve (hinh thuc te)")))
                         (list "name" "Ten loi thang may" 'str (cond (*SD:TMN*) ("TM1")))
                         (list "lx" "Long gieng theo X (mm)" 'real (cond (*SD:TMX*) (2200.0)) nil '("nguon" "Nhap"))
                         (list "ly" "Long gieng theo Y (mm)" 'real (cond (*SD:TMY*) (2200.0)) nil '("nguon" "Nhap"))
                         (list "tw" "Chieu day vach (mm)" 'real (cond (*SD:TMT*) (250.0)))
                         (list "hc" "Chieu cao do 1 dot (mm)" 'real (cond (*SD:TMH*) (3300.0)))
                         (list "dw" "Cua thang - rong (mm)" 'real 1100.0 nil '("nguon" "Nhap"))
                         (list "dh" "Cua thang - cao (mm)" 'real 2200.0)
                         (list "dside" "Cua o vach" 'kw "1" '(("1" . "1 - duoi") ("2" . "2 - phai") ("3" . "3 - tren") ("4" . "4 - trai")) '("nguon" "Nhap"))
                         (list "doff" "Mep cua toi goc trong (mm), -1 = giua" 'real0 -1.0 nil '("nguon" "Nhap"))
                         (list "sc" "Ty le ve 1/" 'int 50))))
    (exit))
  (setq name (sd:v "name") lx (sd:v "lx") ly (sd:v "ly") tw (sd:v "tw") hc (sd:v "hc") dw (sd:v "dw") dh (sd:v "dh")
        dside (atoi (sd:v "dside")))
  (setq doff (if (< (sd:v "doff") 0) (/ (- (if (member dside '(1 3)) lx ly) dw) 2.0) (sd:v "doff"))
        sc   (float (sd:v "sc"))
        *SD:TMN* name *SD:TMX* lx *SD:TMY* ly *SD:TMT* tw *SD:TMH* hc *SD:TMSRC* (sd:v "nguon"))
  (setq p (sd:fw-pressure hc t) sp (sd:fw-design p (sd:fw "TIE"))
        ex (+ (sd:fw "PLYT") (cadr (sd:box (sd:fw "SEC"))) (cadr (sd:box (sd:fw "PRI")))))
  (if (= (sd:v "nguon") "Banve")
    (sd:cftm-real name tw hc dh sc)
  (if (setq pt (sd:getpt "\nGoc trai duoi long gieng tren mat bang: " nil))
    (progn
      (setq o pt)
      ;; ---- mat bang: vach bao quanh long gieng
      (sd:rect (sd:p+ o (- tw) (- tw)) (+ lx tw tw) (+ ly tw tw) "SD-BETONG")
      (sd:rect o lx ly "SD-BETONG")
      ;; mat trong (hop loi): 4 canh trong long gieng, phap tuyen vao tam
      (setq walls (list (list (sd:p+ o 0 0) (sd:p+ o lx 0) (* 0.5 pi) lx)
                        (list (sd:p+ o lx 0) (sd:p+ o lx ly) pi ly)
                        (list (sd:p+ o lx ly) (sd:p+ o 0 ly) (* 1.5 pi) lx)
                        (list (sd:p+ o 0 ly) (sd:p+ o 0 0) 0.0 ly)))
      (foreach w walls (sd:fw-faceplan (car w) (cadr w) (caddr w) sp))
      ;; mat ngoai
      (sd:fw-faceplan (sd:p+ o (- tw) (- tw)) (sd:p+ o (+ lx tw) (- tw)) (* 1.5 pi) sp)
      (sd:fw-faceplan (sd:p+ o (+ lx tw) (- tw)) (sd:p+ o (+ lx tw) (+ ly tw)) 0.0 sp)
      (sd:fw-faceplan (sd:p+ o (+ lx tw) (+ ly tw)) (sd:p+ o (- tw) (+ ly tw)) (* 0.5 pi) sp)
      (sd:fw-faceplan (sd:p+ o (- tw) (+ ly tw)) (sd:p+ o (- tw) (- tw)) pi sp)
      ;; goc trong: thep goc L (ky hieu)
      (foreach c (list (list o 0.0) (list (sd:p+ o lx 0) (* 0.5 pi)) (list (sd:p+ o lx ly) pi) (list (sd:p+ o 0 ly) (* 1.5 pi)))
        (sd:pline (list (polar (car c) (cadr c) 150.0) (car c) (polar (car c) (+ (cadr c) (* 0.5 pi)) 150.0)) nil "SD-CF-GONG"))
      ;; ty xuyen vach
      (setq i 0)
      (foreach w walls
        (setq i (1+ i) a (car w) b (cadr w) L (cadddr w) nv (+ (caddr w) pi))
        (foreach x (sd:evenpos L (caddr sp) (min 300.0 (/ (caddr sp) 2.0)))
          (if (not (and (= i dside) (< (- doff 50) x (+ doff dw 50))))
            (sd:fw-tieplan (polar a (angle a b) x) nv tw))))
      ;; cua
      (setq a (car (nth (1- dside) walls)) b (cadr (nth (1- dside) walls)) nv (+ (caddr (nth (1- dside) walls)) pi))
      (sd:pline (list (polar a (angle a b) doff) (polar a (angle a b) (+ doff dw))
                      (polar (polar a (angle a b) (+ doff dw)) nv tw) (polar (polar a (angle a b) doff) nv tw))
                t "SD-KHUAT")
      (sd:text (polar (polar a (angle a b) (+ doff (/ dw 2))) nv (/ tw 2)) "C\\U+1EECA" (* 2.0 sc) "MC" "SD-CHU")
      (sd:text (sd:p+ o (- tw) (- (+ tw ex (* 12 sc)))) (strcat "M\\U+1EB6T B\\U+1EB0NG COFFA L\\U+00D5I THANG M\\U+00C1Y " name)
               (* 3.0 sc) "L" "SD-CHU")
      (sd:use-dimstyle sc)
      (sd:dim o (sd:p+ o lx 0) "H" (sd:p+ o 0 (/ ly 2)))
      (sd:dim o (sd:p+ o 0 ly) "V" (sd:p+ o (/ lx 2) 0))
      ;; ---- mat dung trai 4 mat trong (mat ngoai tuong tu, dai hon 2 lan day vach)
      (setq ys (sd:evenpos hc (cadr sp) (min 200.0 (/ (cadr sp) 2.0)))
            x0 (+ (car o) lx tw ex (* 40 sc)) y0 (cadr o) qt (sd:fwq0) i 0)
      (foreach w walls
        (setq i (1+ i) L (cadddr w)
              opens (if (= i dside) (list (list doff 0.0 dw dh)))
              tx (sd:evenpos L (caddr sp) (min 300.0 (/ (caddr sp) 2.0))))
        (setq q (sd:fw-panel (list x0 y0 0.0) L hc sp opens tx ys sc
                             (strcat "M\\U+1EB6T TRONG V\\U+00C1CH " (itoa i) (if (= i dside) " (c\\U+00F3 c\\U+1EEDa)" ""))))
        (setq qt (sd:fwq+ qt q) x0 (+ x0 L (* 30 sc))))
      ;; mat ngoai ~ mat trong + 2 lan day vach moi canh; ty dem 1 lan (xuyen ca 2 mat)
      (setq tlen (nth 6 qt)
            qt (sd:fwq+ qt (sd:fwq-set (sd:replace-nth 6 0 qt) 0 (* 8 tw hc)))
            qt (sd:fwq-set qt 0 (* tw (+ dw dh dh)))
            qt (sd:replace-nth 6 tlen qt)
            tieL (+ tw (* 2 ex) 250.0))
      (sd:wall-note o tw ex sc p sp)
      (setq *SD:VKID* (list name "Vach" (/ (- (* (- (* (+ lx tw tw) (+ ly tw tw)) (* lx ly)) hc) (* dw dh tw)) 1e9) "SDCOFFATM"))
      (sd:fw-table (list x0 (+ y0 hc) 0.0) (strcat "L\\U+00D5I THANG M\\U+00C1Y " name) qt tieL 0 sc)
      (sd:use-dimstyle *SD:SCALE*))))
  (sd:finish))

(defun sd:wall-note (o tw ex sc p sp)
  (sd:text (sd:p+ o (- tw) (- (+ tw ex (* 17 sc)))) (sd:fw-note p sp "ty") (* 2.0 sc) "L" "SD-CHU"))

;;; --------------------------------------------------------------------------
;;;  SDCOFFAMONG - Coffa mong don / mong bang / dai coc
;;; --------------------------------------------------------------------------
(defun c:SDCOFFAMONG (/ sc typ name bx ly hm p sp pt o ex ys qa qb q ns nprop sides br f)
  (sd:begin)
  (if (not (sd:dlg "Coffa mong (SDCOFFAMONG)"
                   (list (list "typ" "Loai mong" 'kw "Don" '(("Don" . "Mong don / dai coc") ("Bang" . "Mong bang / dam mong")))
                         (list "name" "Ten mong" 'str (cond (*SD:FMN*) ("M1")))
                         (list "bx" "Canh X (mong bang: chieu dai doan) (mm)" 'real (cond (*SD:FMX*) (2000.0)))
                         (list "ly" "Canh Y (mong bang: be rong) (mm)" 'real (cond (*SD:FMY*) (1600.0)))
                         (list "hm" "Chieu cao mong (mm)" 'real (cond (*SD:FMH*) (700.0)))
                         (list "sc" "Ty le ve 1/" 'int 25))))
    (exit))
  (setq typ (sd:v "typ") name (sd:v "name") bx (sd:v "bx") ly (sd:v "ly") hm (sd:v "hm")
        sc   (float (sd:v "sc"))
        *SD:FMN* name *SD:FMX* bx *SD:FMY* ly *SD:FMH* hm)
  ;; mong thap: ap luc thuy tinh, coffa chong xien vao coc dong (khong ty)
  (setq p  (* (sd:fw "GAM") (/ hm 1000.0))
        sp (sd:fw-design (max p 5.0) (sd:fw "PROP"))
        ex (+ (sd:fw "PLYT") (cadr (sd:box (sd:fw "SEC"))) (cadr (sd:box (sd:fw "PRI")))))
  (if (setq pt (sd:getpt "\nGoc trai duoi mong tren mat bang: " nil))
    (progn
      (setq o pt)
      (sd:rect o bx ly "SD-BETONG")
      (setq sides (if (= typ "Don")
                    (list (list o (sd:p+ o bx 0) (* 1.5 pi)) (list (sd:p+ o bx 0) (sd:p+ o bx ly) 0.0)
                          (list (sd:p+ o bx ly) (sd:p+ o 0 ly) (* 0.5 pi)) (list (sd:p+ o 0 ly) o pi))
                    (list (list o (sd:p+ o bx 0) (* 1.5 pi)) (list (sd:p+ o bx ly) (sd:p+ o 0 ly) (* 0.5 pi)))))
      (setq nprop 0)
      (foreach s sides
        (sd:fw-faceplan (car s) (cadr s) (caddr s) sp)
        ;; chong xien 45 do + coc dong
        (foreach x (sd:evenpos (distance (car s) (cadr s)) (caddr sp) 150.0)
          (setq br (polar (car s) (angle (car s) (cadr s)) x))
          (sd:line (polar br (caddr s) ex) (polar br (caddr s) (+ ex hm)) "SD-CF-CHONG")
          (sd:circle (polar br (caddr s) (+ ex hm)) 30.0 "SD-CF-CHONG")
          (setq nprop (1+ nprop))))
      (sd:use-dimstyle sc)
      (sd:dim o (sd:p+ o bx 0) "H" (sd:p+ o 0 (- (+ ex hm (* 8 sc)))))
      (sd:dim o (sd:p+ o 0 ly) "V" (sd:p+ o (- (+ ex hm (* 8 sc))) 0))
      (sd:text (sd:p+ o 0 (- (+ ex hm (* 18 sc)))) (strcat "M\\U+1EB6T B\\U+1EB0NG COFFA M\\U+00D3NG " name)
               (* 3.0 sc) "L" "SD-CHU")
      (sd:text (sd:p+ o 0 (- (+ ex hm (* 23 sc)))) (sd:fw-note p sp "ch\\U+1ED1ng xi\\U+00EAn") (* 2.0 sc) "L" "SD-CHU")
      ;; mat dung thanh mong
      (setq ys (if (<= hm 400.0) (list (/ hm 2.0)) (sd:evenpos hm (cadr sp) 100.0)))
      (setq qa (sd:fw-panel (sd:p+ o (+ bx ex hm (* 40 sc)) 0) bx hm sp nil nil ys sc
                            (strcat "TH\\U+00C0NH M\\U+00D3NG " name " - C\\U+1EA0NH " (sd:num bx) " (\\U+00D72)")))
      (setq qb (if (= typ "Don")
                 (sd:fw-panel (sd:p+ o (+ bx ex hm (* 40 sc)) (+ hm (* 40 sc))) ly hm sp nil nil ys sc
                              (strcat "TH\\U+00C0NH M\\U+00D3NG " name " - C\\U+1EA0NH " (sd:num ly) " (\\U+00D72)"))
                 (sd:fwq0)))
      ;; mat cat dien hinh thanh mong + chong xien
      (setq f (sd:p+ o (+ bx ex hm (* 40 sc) bx (* 40 sc) ex hm) 0))
      (sd:rect f 400.0 hm "SD-BETONG")
      (sd:rect (sd:p+ f (- (sd:fw "PLYT")) 0) (sd:fw "PLYT") hm "SD-CF-VAN")
      (sd:rect (sd:p+ f (- (+ (sd:fw "PLYT") (cadr (sd:box (sd:fw "SEC"))))) 0) (cadr (sd:box (sd:fw "SEC"))) hm "SD-CF-SUON")
      (foreach y ys (sd:rect (sd:p+ f (- ex) (- y 50)) (cadr (sd:box (sd:fw "PRI"))) 100 "SD-CF-GONG"))
      (sd:line (sd:p+ f (- ex) (last ys)) (sd:p+ f (- (+ ex (last ys))) 0) "SD-CF-CHONG")
      (sd:rect (sd:p+ f (- (+ ex (last ys) 25)) -400) 50 500 "SD-CF-CHONG")
      (sd:text (sd:p+ f 0 (* -12 sc)) "M\\U+1EB6T C\\U+1EAET TH\\U+00C0NH M\\U+00D3NG" (* 2.5 sc) "L" "SD-CHU")
      (setq q (sd:fwq+ (sd:fwq* qa 2) (sd:fwq* qb 2)))
      (setq *SD:VKID* (list name "Mong" (/ (* bx ly hm) 1e9) "SDCOFFAMONG"))
      (sd:fw-table (sd:p+ f (* 40 sc) hm) (strcat "M\\U+00D3NG " name) q 0.0 nprop sc)
      (sd:use-dimstyle *SD:SCALE*)))
  (sd:finish))

;;; --------------------------------------------------------------------------
;;;  SDCOFFATHANG - Coffa thang bo (1 ve): van day, suon, xa go, cay chong, van thanh bac
;;; --------------------------------------------------------------------------
(defun c:SDCOFFATHANG (/ sc name bw nr rh tg ts lc al q sp pt o prof i tp sec pri
                         slen nb nprop xs xb a b ptop pbot hb q2)
  (sd:begin)
  (if (not (sd:dlg "Coffa thang bo (SDCOFFATHANG)"
                   (list (list "name" "Ten ve thang" 'str (cond (*SD:STN*) ("VT1")))
                         (list "bw" "Be rong ve thang (mm)" 'real (cond (*SD:STB*) (1200.0)))
                         (list "nr" "So bac (so co thang)" 'int (cond (*SD:STNR*) (11)))
                         (list "rh" "Chieu cao bac (mm)" 'real (cond (*SD:STR*) (150.0)))
                         (list "tg" "Be rong mat bac (mm)" 'real (cond (*SD:STG*) (280.0)))
                         (list "ts" "Chieu day ban thang (mm)" 'real (cond (*SD:STT*) (120.0)))
                         (list "lc" "Chieu nghi / dam chieu nghi tren (mm, >= 300)" 'real (cond (*SD:STL*) (1200.0)))
                         (list "sc" "Ty le ve 1/" 'int 25))))
    (exit))
  (setq name (sd:v "name") bw (sd:v "bw") nr (sd:v "nr") rh (sd:v "rh") tg (sd:v "tg") ts (sd:v "ts")
        lc   (max (sd:v "lc") 300.0)
        sc   (float (sd:v "sc"))
        *SD:STN* name *SD:STB* bw *SD:STNR* nr *SD:STR* rh *SD:STG* tg *SD:STT* ts *SD:STL* lc)
  (setq al (atan rh tg)
        ;; tai trong (kPa): ban + bac (trung binh r/2) + thi cong 2.5 + van khuon 0.5
        q  (+ (* (sd:fw "GAM") (/ (+ (/ ts (cos al)) (/ rh 2.0)) 1000.0)) 2.5 0.5)
        sp (sd:fw-design q (sd:fw "PROP"))
        tp (sd:fw "PLYT") sec (sd:box (sd:fw "SEC")) pri (sd:box (sd:fw "PRI")))
  (if (setq pt (sd:getpt "\nDiem chan bac dau tien (cao do san duoi): " nil))
    (progn
      (setq o pt)
      ;; ---- mat cat doc: bien dang be tong
      (setq prof (list (list 0.0 0.0)) i 1)
      (repeat nr
        (setq prof (append prof (list (list (* (1- i) tg) (* i rh))
                                      (list (if (< i nr) (* i tg) (+ (* (1- nr) tg) lc)) (* i rh))))
              i (1+ i)))
      ;; day ban thang: song song duong y = (rh/tg)x, ha ts/cos; chieu nghi day ts
      (setq hb (/ ts (cos al))
            xb (/ hb (/ (sin al) (cos al)))                         ; giao day nghieng voi san
            ptop (list (/ (+ (- (* nr rh) ts) hb) (/ (sin al) (cos al))) (- (* nr rh) ts)) ; giao voi day chieu nghi
            pbot (list xb 0.0))
      (setq prof (append prof (list (list (+ (* (1- nr) tg) (max lc 0.0)) (- (* nr rh) ts)) ptop pbot)))
      (sd:pline (mapcar '(lambda (p) (sd:p+ o (car p) (cadr p))) prof) t "SD-BETONG")
      (setq slen (distance pbot ptop) a (angle pbot ptop))
      ;; van day nghieng + chieu nghi
      (sd:pline (list (sd:p+ o (car pbot) (cadr pbot)) (sd:p+ o (car ptop) (cadr ptop))
                      (polar (sd:p+ o (car ptop) (cadr ptop)) (- a (/ pi 2)) tp)
                      (polar (sd:p+ o (car pbot) (cadr pbot)) (- a (/ pi 2)) tp))
                t "SD-CF-VAN")
      (if (> lc 0)
        (sd:rect (sd:p+ o (car ptop) (- (cadr ptop) tp)) (- (+ (* (1- nr) tg) lc) (car ptop)) tp "SD-CF-VAN"))
      ;; suon ngang (cat ngang) doc theo do doc @s1
      (setq xs (sd:evenpos slen (car sp) 100.0))
      (foreach s xs
        (setq b (polar (polar (sd:p+ o (car pbot) (cadr pbot)) a s) (- a (/ pi 2)) tp))
        (sd:pline (list (polar b a (/ (car sec) -2)) (polar b a (/ (car sec) 2))
                        (polar (polar b a (/ (car sec) 2)) (- a (/ pi 2)) (cadr sec))
                        (polar (polar b a (/ (car sec) -2)) (- a (/ pi 2)) (cadr sec)))
                  t "SD-CF-SUON"))
      ;; xa go doc (2 thep hop) duoi suon
      (setq b (polar (sd:p+ o (car pbot) (cadr pbot)) (- a (/ pi 2)) (+ tp (cadr sec))))
      (sd:pline (list b (polar b a slen) (polar (polar b a slen) (- a (/ pi 2)) (cadr pri)) (polar b (- a (/ pi 2)) (cadr pri)))
                t "SD-CF-GONG")
      ;; cay chong dung @s3 theo xa go
      (setq nprop 0)
      (foreach s (sd:evenpos slen (caddr sp) 200.0)
        (setq b (polar (polar (sd:p+ o (car pbot) (cadr pbot)) a s) (- a (/ pi 2)) (+ tp (cadr sec) (cadr pri))))
        (if (> (- (cadr b) (cadr o)) 300.0)
          (progn
            (sd:line b (list (car b) (cadr o)) "SD-CF-CHONG")
            (sd:rect (list (- (car b) 75) (cadr o)) 150 10 "SD-CF-CHONG")
            (setq nprop (1+ nprop)))))
      ;; chong chieu nghi
      (if (> lc 0)
        (foreach x (sd:evenpos (- (+ (* (1- nr) tg) lc) (car ptop)) (caddr sp) 200.0)
          (setq b (sd:p+ o (+ (car ptop) x) (- (cadr ptop) tp (cadr sec) (cadr pri))))
          (sd:rect (list (- (car b) (/ (car sec) 2)) (+ (cadr b) (cadr pri))) (car sec) (cadr sec) "SD-CF-SUON")
          (sd:line b (list (car b) (cadr o)) "SD-CF-CHONG")
          (setq nprop (1+ nprop))))
      ;; van thanh bac (co bac)
      (setq i 1)
      (repeat nr
        (if (< i nr)
          (sd:rect (sd:p+ o (- (* i tg) tp) (* i rh)) tp rh "SD-CF-VAN"))
        (setq i (1+ i)))
      ;; kich thuoc
      (sd:use-dimstyle sc)
      (sd:dimchain (mapcar '(lambda (i) (sd:p+ o (* i tg) (* nr rh))) (sd:range 0 (1- nr))) "H" (sd:p+ o 0 (+ (* nr rh) (* 10 sc))))
      (sd:dim o (sd:p+ o 0 (* nr rh)) "V" (sd:p+ o (* -10 sc) 0))
      (sd:text (sd:p+ o 0 (* -12 sc)) (strcat "M\\U+1EB6T C\\U+1EAET D\\U+1ECCC COFFA THANG " name ": " (itoa nr) " b\\U+1EADc " (sd:num rh) "\\U+00D7" (sd:num tg)
                                             ", b\\U+1EA3n d\\U+00E0y " (sd:num ts) ", r\\U+1ED9ng " (sd:num bw))
               (* 3.0 sc) "L" "SD-CHU")
      (sd:text (sd:p+ o 0 (* -17 sc))
               (strcat "q = " (sd:rtos q 1) " kPa; v\\U+00E1n " (sd:num tp) "mm; s\\U+01B0\\U+1EDDn ngang " (sd:fw "SEC") " @" (sd:num (car sp))
                       "; x\\U+00E0 g\\U+1ED3 d\\U+1ECDc " (itoa (sd:fw "PRIN")) "\\U+00D7" (sd:fw "PRI") " @" (sd:num (cadr sp))
                       " theo b\\U+1EC1 r\\U+1ED9ng; c\\U+00E2y ch\\U+1ED1ng @" (sd:num (caddr sp)) " (" (sd:rtos (cadddr sp) 1) " kN)")
               (* 2.0 sc) "L" "SD-CHU")
      ;; thong ke: van day + co bac + 2 van thanh ben (dien tich mat cat)
      (setq nb (length (sd:evenpos bw (cadr sp) 150.0))
            q2 (list (+ (* bw (+ slen (max 0.0 (- (+ (* (1- nr) tg) lc) (car ptop)))))
                        (* (1- nr) rh bw)
                        (* 2 (abs (sd:area prof))))
                     0 0 0.0
                     (* (+ bw 200.0) (+ (length xs) (if (> lc 0) (length (sd:evenpos (- (+ (* (1- nr) tg) lc) (car ptop)) (caddr sp) 200.0)) 0)))
                     (* nb (sd:fw "PRIN") (+ slen lc))
                     0 0.0 (* nb nprop)))
      ;; quy doi tam van theo dien tich (thang cat nhieu)
      (setq q2 (sd:replace-nth 3 (car q2) q2) q2 (sd:replace-nth 2 1 q2))
      (setq *SD:VKID* (list name "Thang" (/ (* (abs (sd:area prof)) bw) 1e9) "SDCOFFATHANG"))
      (sd:fw-table (sd:p+ o (+ (* nr tg) lc (* 30 sc)) (* nr rh)) (strcat "THANG " name) q2 0.0 (* nb nprop) sc)
      (sd:use-dimstyle *SD:SCALE*)))
  (sd:finish))

(defun sd:range (a b / r) (while (<= a b) (setq r (cons a r) a (1+ a))) (reverse r))

;;; ==========================================================================
;;;  COFFA DAM SAN + GIAN GIAO DO + HE GIANG
;;;  San: van -> suon (thep hop nho) @s1 -> xa go chinh (2 thep hop) @a2 -> dau U chan giao @a1
;;; ==========================================================================
(setq *SD:GIDEF*
  '(("TYPE" . "Nem")                         ; Nem = giao nem/ringlock, Khung = giao khung H, Chong = cay chong
    ("SP" . "900,1200,1500,1800")            ; giao nem: chieu dai thanh giang ngang
    ("CAP" . 25.0)                           ; giao nem: tai trong cho phep 1 chan (kN)
    ("LIFT" . 1500.0)                        ; giao nem: khoang cach cac tang giang ngang
    ("STD" . "3000,2500,2000,1500,1000,500") ; giao nem: cac doan cay dung
    ("FH" . 1700.0) ("FW" . 1250.0)          ; giao khung: cao, rong khung
    ("FBR" . "1200,1500,1800")               ; giao khung: khoang cach khung (giang cheo)
    ("FCAP" . 20.0)                          ; giao khung: tai 1 chan (kN)
    ("PROPS" . "K102:1800-3100:20,K103:2000-3500:16,K104:2200-4000:12") ; cay chong: ma:min-max:kN
    ("PSP" . "800,1000,1200,1500")           ; cay chong: khoang cach
    ("JMIN" . 100.0) ("JMAX" . 500.0)        ; kich chan / kich dau U (mm)
    ("BRN" . 4) ("BRM" . 3)                  ; giang cheo: moi BRN hang, moi BRM nhip (+ hang/nhip bien)
    ("LL" . 2.5) ("VIB" . 2.0)))             ; hoat tai thi cong, dam be tong (kPa)

(defun sd:gi (key) (sd:cfg (strcat "GI-" key) (cdr (assoc key *SD:GIDEF*))))
(defun sd:numlist (s) (vl-remove 0.0 (mapcar 'atof (sd:split s ","))))

;; Cay chong phu hop chieu cao Hu: (ma min max kN) hoac nil
(defun sd:gi-prop (Hu / r f)
  (foreach tok (sd:split (sd:gi "PROPS") ",")
    (setq f (sd:split (vl-string-translate ":-" ",," tok) ","))
    (if (and (not r) (= (length f) 4) (<= (atof (nth 1 f)) Hu (atof (nth 2 f))))
      (setq r (list (car f) (atof (nth 1 f)) (atof (nth 2 f)) (atof (nth 3 f))))))
  r)

;; Danh sach khoang cach cho phep theo 2 phuong (a1 doc xa go, a2 giua cac xa go) va tai 1 chan
(defun sd:gi-lists (Hu / typ pr)
  (setq typ (sd:gi "TYPE"))
  (cond ((= typ "Khung") (list (sd:numlist (sd:gi "FBR")) (list (sd:gi "FW")) (sd:gi "FCAP")))
        ((= typ "Chong")
         (setq pr (sd:gi-prop Hu))
         (list (sd:numlist (sd:gi "PSP")) (sd:numlist (sd:gi "PSP")) (if pr (nth 3 pr) 0.0)))
        (t (list (sd:numlist (sd:gi "SP")) (sd:numlist (sd:gi "SP")) (sd:gi "CAP")))))

;; Tai san (kPa): be tong + van khuon 0.5 + thi cong + dam
(defun sd:gi-load (ts) (+ (* (sd:fw "GAM") (/ ts 1000.0)) 0.5 (sd:gi "LL") (sd:gi "VIB")))

;; Thiet ke he do san: q kPa -> (s1 a1 a2 tai-chan) ; thu giam s1 de tang nhip suon neu can
(defun sd:gi-design (q l1 l2 cap / qq tp sec pri ip wp s1 lj lb best s)
  (setq qq (/ q 1000.0) tp (sd:fw "PLYT") sec (sd:box (sd:fw "SEC")) pri (sd:box (sd:fw "PRI"))
        ip (* (sd:fw "PRIN") (sd:box-I pri)) wp (/ (* 2.0 ip) (cadr pri))
        s  (sd:clampv (sd:floor50 (sd:fw-span qq (/ (* tp tp) 6.0) (/ (* tp tp tp) 12.0)
                                              (sd:fw "PLYF") (sd:fw "PLYE") (sd:fw "DEF")))
                      100.0 (sd:fw "S1MAX")))
  (while (>= s 150.0)
    (setq lj (sd:fw-span (* qq s) (/ (* 2.0 (sd:box-I sec)) (cadr sec)) (sd:box-I sec) (sd:fw "FS") 2.1e5 (sd:fw "DEF")))
    (foreach a2 l2
      (if (<= a2 lj)
        (progn
          (setq lb (sd:fw-span (* qq a2) wp ip (sd:fw "FS") 2.1e5 (sd:fw "DEF")))
          (foreach a1 l1
            (if (and (<= a1 lb) (<= (/ (* qq a1 a2) 1000.0) cap)
                     (or (null best) (> (* a1 a2) (* (nth 1 best) (nth 2 best)))))
              (setq best (list s a1 a2 (/ (* qq a1 a2) 1000.0))))))))
    (setq s (- s 50.0)))
  (cond (best)
        (t (princ "\n[!] Khong tim duoc luoi giao thoa man - dung khoang cach nho nhat, can kiem tra lai.")
           (list 150.0 (apply 'min l1) (apply 'min l2) (/ (* qq (apply 'min l1) (apply 'min l2)) 1000.0)))))

;; Cau tao chieu cao giao tu san den mat dau U (Hu):
;; -> (kich-chan kich-dau tong-than doan-than cao-do-giang) ; nil neu khong xep duoc
(defun sd:gi-stack (Hu / typ jmin jmax S e lv lift pcs r n pr)
  (setq typ (sd:gi "TYPE") jmin (sd:gi "JMIN") jmax (sd:gi "JMAX"))
  (cond
    ((= typ "Chong")
     (if (setq pr (sd:gi-prop Hu))
       (list 0.0 0.0 Hu (list (car pr)) (list (/ Hu 2.0)))))
    ((= typ "Khung")
     (setq n (fix (/ (- Hu jmin jmin) (sd:gi "FH"))) S (* n (sd:gi "FH")) pcs (sd:repeat "khung" n))
     (if (> (- Hu S) (* 2 jmax)) (setq S (+ S 900.0) pcs (cons "khung 900" pcs)))
     (setq e (- Hu S) r 0.0 lv nil)
     (foreach p (reverse pcs) (setq r (+ r (if (= p "khung") (sd:gi "FH") 900.0)) lv (cons (+ (/ e 2) r) lv)))
     (if (and (> n 0) (<= (/ e 2) jmax)) (list (/ e 2) (/ e 2) S pcs (reverse lv))))
    (t
     (setq S (* 500.0 (fix (/ (- Hu jmin jmin) 500.0))) e (- Hu S) r S lift (sd:gi "LIFT"))
     (foreach L (sd:numlist (sd:gi "STD"))
       (while (>= r (- L 0.1)) (setq pcs (cons L pcs) r (- r L))))
     (setq lv (list (+ (/ e 2) 250.0)))
     (while (<= (+ (car lv) lift) (+ (/ e 2) S -250.0)) (setq lv (cons (+ (car lv) lift) lv)))
     (if (> (- (+ (/ e 2) S -250.0) (car lv)) 100.0) (setq lv (cons (+ (/ e 2) S -250.0) lv)))
     (if (and (> S 0) (<= (/ e 2) jmax)) (list (/ e 2) (/ e 2) S (reverse pcs) (reverse lv))))))

(defun sd:gi-pcs-str (pcs / g)
  (sd:join (mapcar '(lambda (g) (strcat (itoa (cdr g)) "\\U+00D7" (if (numberp (car g)) (sd:num (car g)) (car g))))
                   (sd:group pcs)) " + "))

;; Cat doan p1-p2 (2 dau nam ngoai da giac) bang da giac: cac doan nam trong
(defun sd:clip-seg (p1 p2 poly / u ip a r q)
  (setq u (angle p1 p2) p1 (sd:2d (polar p1 (+ u pi) 10.0)) p2 (sd:2d (polar p2 u 10.0)) a (last poly))
  (foreach b poly
    (if (setq ip (inters p1 p2 a b t)) (setq r (cons (list (distance p1 ip) (sd:2d ip)) r)))
    (setq a b))
  (foreach x (sd:sort r '(lambda (x y) (< (car x) (car y))))
    (if (not (and q (equal (cadr x) (car q) 1e-6))) (setq q (cons (cadr x) q))))
  (sd:pairs (reverse q)))
(defun sd:pairs (l / r) (while (cadr l) (setq r (cons (list (car l) (cadr l)) r) l (cddr l))) (reverse r))

;; Ky hieu giang cheo tren mat bang: zigzag giua 2 chan
(defun sd:brace-sym (a b / d n u v r i)
  (setq d (distance a b) n 4 u (angle a b) v (+ u (/ pi 2)) i 0)
  (repeat (1+ n)
    (setq r (cons (polar (polar a u (* i (/ d n))) v (if (= (rem i 2) 0) 0.0 60.0)) r) i (1+ i)))
  (sd:plinew (reverse r) nil 15.0 "SD-GIANG"))

(defun sd:leg-sym (p)
  (sd:rect (sd:p+ p -30 -30) 60 60 "SD-GIAO")
  (sd:circle p 24.0 "SD-GIAO"))

;; Hang/nhip duoc giang: bien + moi n
(defun sd:braced-p (i n every) (or (= i 0) (= i (1- n)) (= (rem i every) 0)))

;;; --------------------------------------------------------------------------
;;;  SDGIAOSET - Thong so gian giao do va he giang
;;; --------------------------------------------------------------------------
(defun c:SDGIAOSET (/ v)
  (sd:begin)
  (if (not (sd:dlg "Thong so gian giao (SDGIAOSET)"
                   (mapcar '(lambda (f) (list (car f) (cadr f) (caddr f) (sd:gi (car f)) (nth 3 f) (nth 4 f)))
                           '(("TYPE" "Loai giao" kw (("Nem" . "Giao nem / ringlock") ("Khung" . "Giao khung H") ("Chong" . "Cay chong thep")))
                             ("SP" "Giao nem: chieu dai giang co san (mm)" str nil ("TYPE" "Nem"))
                             ("CAP" "Giao nem: tai cho phep 1 chan (kN)" real nil ("TYPE" "Nem"))
                             ("LIFT" "Giao nem: buoc tang giang (mm)" real nil ("TYPE" "Nem"))
                             ("STD" "Giao nem: cac doan cay dung (mm)" str nil ("TYPE" "Nem"))
                             ("FH" "Giao khung: chieu cao khung (mm)" real nil ("TYPE" "Khung"))
                             ("FW" "Giao khung: be rong khung (mm)" real nil ("TYPE" "Khung"))
                             ("FBR" "Giao khung: khoang cach khung (mm)" str nil ("TYPE" "Khung"))
                             ("FCAP" "Giao khung: tai cho phep 1 chan (kN)" real nil ("TYPE" "Khung"))
                             ("PROPS" "Cay chong ma:min-max:kN,..." str nil ("TYPE" "Chong"))
                             ("PSP" "Cay chong: cac khoang cach (mm)" str nil ("TYPE" "Chong"))
                             ("JMIN" "Do vuon kich toi thieu (mm)" real)
                             ("JMAX" "Do vuon kich toi da (mm)" real)
                             ("STDD" "On dinh: ong cay dung D (mm)" real nil ("TYPE" "Nem" "Khung"))
                             ("STDT" "On dinh: ong cay dung day t (mm)" real nil ("TYPE" "Nem" "Khung"))
                             ("FY" "On dinh: gioi han chay fy (MPa)" real nil ("TYPE" "Nem" "Khung"))
                             ("JD" "On dinh: ty kich D (mm)" real nil ("TYPE" "Nem" "Khung"))
                             ("JT" "On dinh: ty kich day (0 = dac)" real0 nil ("TYPE" "Nem" "Khung"))
                             ("KTOP" "He so L kich dau U (2 = tu do)" real nil ("TYPE" "Nem" "Khung"))
                             ("KBOT" "He so L kich chan" real nil ("TYPE" "Nem" "Khung"))
                             ("BRN" "Giang cheo: moi ... hang" int)
                             ("BRM" "Giang cheo: moi ... nhip" int)
                             ("OSAN" "Thong ke: o san dien hinh (m2)" real)
                             ("NHIP" "Thong ke: nhip dam dien hinh (mm)" real)
                             ("LL" "Hoat tai thi cong (kPa)" real0)
                             ("VIB" "Tai trong dam be tong (kPa)" real0)))))
    (exit))
  (foreach f *SD:FV* (sd:cfg-put (strcat "GI-" (car f)) (cdr f)))
  (foreach ts '(120.0 150.0 200.0)
    (setq v (sd:gi-design (sd:gi-load ts) (car (sd:gi-lists 3000.0)) (cadr (sd:gi-lists 3000.0)) (caddr (sd:gi-lists 3000.0))))
    (princ (strcat "\n  San " (sd:num ts) ": q = " (sd:rtos (sd:gi-load ts) 2) " kPa -> suon @" (sd:num (car v))
                   ", chan giao " (sd:num (cadr v)) " x " (sd:num (caddr v)) " (" (sd:rtos (cadddr v) 1) " kN/chan)")))
  (sd:finish))

;;; --------------------------------------------------------------------------
;;;  SDGIAOH - Gian giao khung H ca tang: chon loai "Khung" tam thoi roi chay SDGIAOTANG
;;; --------------------------------------------------------------------------
(defun c:SDGIAOH (/ old r)
  (setq old (sd:gi "TYPE"))
  (sd:cfg-put "GI-TYPE" "Khung")
  (princ (strcat "\n[SD] Giao khung H: cao " (sd:num (sd:gi "FH")) ", rong " (sd:num (sd:gi "FW"))
                 ", khoang cach khung " (sd:gi "FBR") ", tai " (sd:rtos (sd:gi "FCAP") 1) " kN/chan (doi bang SDGIAOSET)."))
  (setq r (vl-catch-all-apply 'c:SDGIAOTANG nil))
  (sd:cfg-put "GI-TYPE" old)
  (if (vl-catch-all-error-p r) (princ (strcat "\n[SD] " (vl-catch-all-error-message r))))
  (princ))

(defun sd:nthcdr (i l) (repeat i (setq l (cdr l))) l)

(defun sd:gi-name ()
  (cond ((= (sd:gi "TYPE") "Khung") "Gi\\U+00E1o khung")
        ((= (sd:gi "TYPE") "Chong") "C\\U+00E2y ch\\U+1ED1ng th\\U+00E9p")
        (t "Gi\\U+00E1o n\\U+00EAm")))

(defun sd:fw-csv (name rows / fn f)
  (setq fn (sd:csv-name "_KhoiLuongCoffa.csv"))
  (if (setq f (sd:open fn "a"))
    (progn
      (foreach r rows
        (write-line (sd:join (cons name (mapcar '(lambda (s) (vl-string-subst "m2" "m\\U+00B2" s)) r)) ";") f))
      (setq fn (sd:close f))
      (princ (strcat "\n[SD] Da ghi them vao: " fn)))))

;; Mat cat gian giao: o = chan tai san duoi, xs = vi tri chan, hs = san -> day san, st = cau tao giao
(defun sd:gi-section (o xs hs ts st s1 sc title / tp sec pri x0 x1 hu jb)
  (setq tp (sd:fw "PLYT") sec (sd:box (sd:fw "SEC")) pri (sd:box (sd:fw "PRI"))
        x0 (- (car xs) 400.0) x1 (+ (last xs) 400.0)
        hu (- hs tp (cadr sec) (cadr pri))
        jb (car st))
  ;; san duoi, san tren, van, suon, xa go
  (sd:line (sd:p+ o x0 0) (sd:p+ o x1 0) "SD-BETONG")
  (sd:rect (sd:p+ o x0 hs) (- x1 x0) ts "SD-BETONG")
  (sd:rect (sd:p+ o x0 (- hs tp)) (- x1 x0) tp "SD-CF-VAN")
  (foreach s (sd:evenpos (- x1 x0) s1 75.0)
    (sd:rect (sd:p+ o (+ x0 s (/ (car sec) -2)) (- hs tp (cadr sec))) (car sec) (cadr sec) "SD-CF-SUON"))
  (sd:rect (sd:p+ o x0 hu) (- x1 x0) (cadr pri) "SD-CF-GONG")
  (sd:gi-section-legs o xs hu st)
  ;; kich thuoc
  (sd:use-dimstyle sc)
  (sd:dimchain (mapcar '(lambda (x) (sd:p+ o x 0)) xs) "H" (sd:p+ o 0 (* -8 sc)))
  (sd:dimchain (mapcar '(lambda (y) (sd:p+ o (last xs) y))
                       (append (list 0.0 jb) (if (/= (sd:gi "TYPE") "Chong") (nth 4 st)) (list (+ jb (nth 2 st)) hu (- hs tp) hs)))
               "V" (sd:p+ o (+ (last xs) 600 (* 8 sc)) 0))
  (sd:text (sd:p+ o x0 (* -16 sc)) title (* 3.0 sc) "L" "SD-CHU"))

(defun sd:gi-section-legs (o xs hu st / jb)
  (setq jb (car st))
  (foreach x xs
    (sd:rect (sd:p+ o (- x 75) 0) 150 8 "SD-GIAO")
    (sd:line (sd:p+ o x 8) (sd:p+ o x jb) "SD-GIAO")
    (sd:rect (sd:p+ o (- x 24) jb) 48 (nth 2 st) "SD-GIAO")
    (sd:line (sd:p+ o x (+ jb (nth 2 st))) (sd:p+ o x (- hu 10)) "SD-GIAO")
    (sd:pline (list (sd:p+ o (- x 60) (+ hu 40)) (sd:p+ o (- x 60) (- hu 10)) (sd:p+ o (+ x 60) (- hu 10)) (sd:p+ o (+ x 60) (+ hu 40)))
              nil "SD-GIAO"))
  (if (and (/= (sd:gi "TYPE") "Chong") (cadr xs))
    (progn
      (foreach y (nth 4 st) (sd:line (sd:p+ o (car xs) y) (sd:p+ o (last xs) y) "SD-GIANG"))
      (setq jb (nth 4 st))
      (while (cadr jb)
        (foreach pr (if (cddr xs) (list (list (car xs) (cadr xs)) (list (nth (- (length xs) 2) xs) (last xs)))
                                  (list (list (car xs) (cadr xs))))
          (sd:line (sd:p+ o (car pr) (car jb)) (sd:p+ o (cadr pr) (cadr jb)) "SD-GIANG"))
        (setq jb (cdr jb))))))

;;; --------------------------------------------------------------------------
;;;  On dinh cay dung / kich (EN 1993-1-1, duong cong c, gamma_M1 = 1.1)
;;; --------------------------------------------------------------------------
(setq *SD:GIDEF* (append *SD:GIDEF*
  '(("STDD" . 49.0) ("STDT" . 2.0) ("FY" . 235.0)     ; ong cay dung D x t (mm), fy (MPa)
    ("JD" . 34.0) ("JT" . 0.0)                        ; ty kich: D x t (t = 0: dac)
    ("KTOP" . 2.0) ("KBOT" . 1.0))))                  ; he so chieu dai tinh toan kich dau U / kich chan

;; Suc chiu nen co xet on dinh (kN) cua ong D x t (t=0: dac), chieu dai tinh toan Lo
(defun sd:gi-nrd (D tw Lo / dd A in ri lb ph chi fy)
  (setq fy (sd:gi "FY") dd (if (> tw 0) (- D tw tw) 0.0)
        A  (* (/ pi 4.0) (- (* D D) (* dd dd)))
        in (* (/ pi 64.0) (- (expt D 4) (expt dd 4)))
        ri (sqrt (/ in A))
        lb (/ (/ Lo ri) (* pi (sqrt (/ 2.1e5 fy))))
        ph (* 0.5 (+ 1.0 (* 0.49 (- lb 0.2)) (* lb lb)))
        chi (min 1.0 (/ 1.0 (+ ph (sqrt (max 0.0 (- (* ph ph) (* lb lb))))))))
  (/ (* chi A fy) 1100.0))

;; On dinh chan giao voi cau tao st, mat dau U o Hu -> (Nrd-min "chi tiet") ; nil voi cay chong (theo catalogue)
(defun sd:gi-stab (Hu st / lv gap Lstd ns nt nb)
  (if (and st (/= (sd:gi "TYPE") "Chong"))
    (progn
      (setq lv (nth 4 st) gap 0.0)
      (if (= (sd:gi "TYPE") "Khung")
        (setq Lstd (sd:gi "FH"))
        (progn
          (setq Lstd (sd:gi "LIFT"))
          (while (cadr lv) (setq gap (max gap (- (cadr lv) (car lv))) lv (cdr lv)))
          (if (> gap 0) (setq Lstd gap))))
      (setq ns (sd:gi-nrd (sd:gi "STDD") (sd:gi "STDT") Lstd)
            nt (sd:gi-nrd (sd:gi "JD") (sd:gi "JT") (* (sd:gi "KTOP") (- Hu (last (nth 4 st)))))
            nb (sd:gi-nrd (sd:gi "JD") (sd:gi "JT") (* (sd:gi "KBOT") (car (nth 4 st)))))
      (list (min ns nt nb)
            (strcat "\\U+1ED4n \\U+0111\\U+1ECBnh: th\\U+00E2n \\U+00D8" (sd:num (sd:gi "STDD")) "\\U+00D7" (sd:num (sd:gi "STDT")) " L=" (sd:rtos Lstd 0) " \\U+2192 "
                    (sd:rtos ns 1) " kN; k\\U+00EDch U L=" (sd:rtos (- Hu (last (nth 4 st))) 0) " \\U+2192 " (sd:rtos nt 1)
                    " kN; k\\U+00EDch ch\\U+00E2n \\U+2192 " (sd:rtos nb 1) " kN")))))

;; Chuan bi giao cho mat dau U Hu: (cau-tao danh-sach-khoang suc-chiu-chan chu-thich-on-dinh) hoac nil
(defun sd:gi-setup (Hu / st lst stb cap)
  (if (setq st (sd:gi-stack Hu))
    (progn
      (setq lst (sd:gi-lists Hu) cap (caddr lst) stb (sd:gi-stab Hu st))
      (if (and stb (< (car stb) cap))
        (progn (princ (strcat "\n[!] On dinh cay dung khong che: suc chiu 1 chan giam tu " (sd:rtos cap 1)
                              " xuong " (sd:rtos (car stb) 1) " kN."))
               (setq cap (car stb))))
      (list st lst cap (if stb (cadr stb) "")))))

;;; --------------------------------------------------------------------------
;;;  Cat duong thang voi o san co lo: khoang [d0 d1] theo khoang cach tu p1
;;; --------------------------------------------------------------------------
(defun sd:clip-iv (p1 p2 poly / ip a r q)
  (setq a (last poly))
  (foreach b poly
    (if (setq ip (inters p1 p2 a b t)) (setq r (cons (distance p1 ip) r)))
    (setq a b))
  (foreach x (vl-sort r '<) (if (not (and q (equal x (car q) 1e-6))) (setq q (cons x q))))
  (sd:pairs (reverse q)))

(defun sd:iv-minus (ivs cut / r a b)
  (foreach iv ivs
    (setq a (car iv) b (cadr iv))
    (foreach c (sd:sort cut '(lambda (x y) (< (car x) (car y))))
      (if (and (< (car c) b) (> (cadr c) a))
        (progn (if (> (car c) a) (setq r (cons (list a (car c)) r)))
               (setq a (max a (cadr c))))))
    (if (> b a) (setq r (cons (list a b) r))))
  (reverse r))

;; Cac doan cua p1-p2 nam trong o san (outer tru holes)
(defun sd:clip-segh (p1 p2 outer holes / u ivs)
  (setq u (angle p1 p2) p1 (sd:2d (polar p1 (+ u pi) 10.0)) p2 (sd:2d (polar p2 u 10.0))
        ivs (sd:clip-iv p1 p2 outer))
  (foreach h holes (setq ivs (sd:iv-minus ivs (sd:clip-iv p1 p2 h))))
  (mapcar '(lambda (iv) (list (sd:2d (polar p1 u (car iv))) (sd:2d (polar p1 u (cadr iv))))) ivs))

(defun sd:in-panel (p outer holes)
  (and (sd:inpoly p outer) (not (vl-some '(lambda (h) (sd:inpoly p h)) holes))))

;; Thong ke tich luy (khoa . so)
(defun sd:bom+ (key n) (setq *SD:BOM* (sd:addcnt key n *SD:BOM*)))
(defun sd:bom (key) (cond ((cdr (assoc key *SD:BOM*))) (0)))

;; Vi tri chan giao cach dung khoang chuan a (khop chieu dai thanh giang); dau cuoi bu bang
;; 1 khoang chuan ngan hon trong lst neu mep con du; ca day duoc can giua.
(defun sd:fixpos (L a m lst / r x s d)
  (if (< L (+ m m 1.0))
    (list (/ L 2.0))
    (progn
      (setq x m r (list m))
      (while (<= (+ x a) (+ (- L m) 1e-6)) (setq x (+ x a) r (cons x r)))
      (if (and (> (- L x) (+ m 200.0))
               (setq s (car (vl-sort (vl-remove-if '(lambda (v) (> v (+ (- L x m) 1e-6))) lst) '>))))
        (setq x (+ x s) r (cons x r)))
      (setq d (/ (- (- L x) m) 2.0))
      (mapcar '(lambda (v) (+ v d)) (reverse r)))))

;; Dem giang ngang giua cac chan lien tiep theo chieu dai thuc (bo qua khoang vuot giang dai nhat)
(defun sd:pair-ledgers (pts lvn mx / d)
  (while (cadr pts)
    (setq d (distance (car pts) (cadr pts)))
    (if (<= d (+ mx 1.0)) (sd:bom+ (strcat "GIANG|" (sd:num (* 10.0 (fix (+ (/ d 10.0) 0.5))))) lvn))
    (setq pts (cdr pts))))

;; Ghi chan giao vao thong ke: tong chan theo cau tao + tung doan than + kich
(defun sd:bom-legs (st n)
  (sd:bom+ (strcat "CHAN|" (sd:gi-pcs-str (nth 3 st)) "|" (sd:rtos (car st) 0) "/" (sd:rtos (cadr st) 0)) n)
  (foreach p (nth 3 st) (sd:bom+ (strcat "THAN|" (if (numberp p) (sd:num p) p)) n))
  (if (/= (sd:gi "TYPE") "Chong") (progn (sd:bom+ "KICHCHAN" n) (sd:bom+ "KICHU" n))))

(defun sd:maxlist (lst) (apply 'max (append (car lst) (cadr lst))))

;;; --------------------------------------------------------------------------
;;;  Thiet ke + ve 1 o san (co the co lo). d = (s1 a1 a2 tai), st = cau tao giao.
;;;  avoid = chan giao da co (duoi dam) -> bo chan san trung (< 200 mm). Tra ve danh sach chan.
;;; --------------------------------------------------------------------------
(defun sd:san-design (ts hs / tp sec pri hu q gs d)
  (setq tp (sd:fw "PLYT") sec (sd:box (sd:fw "SEC")) pri (sd:box (sd:fw "PRI"))
        hu (- hs tp (cadr sec) (cadr pri)) q (sd:gi-load ts))
  (if (setq gs (sd:gi-setup hu))
    (progn
      (setq d (sd:gi-design q (car (cadr gs)) (cadr (cadr gs)) (caddr gs)))
      (list d (car gs) q hu (caddr gs) (cadddr gs) (cadr gs)))))

(defun sd:san-panel (outer holes dirx ds sc margin avoid / d st lst s1 a1 a2 bb ox oy xs ys sx sy p0 k bx2 rowsx row
                     legs pl cur i nleg pri mx my lvn)
  (setq d (car ds) st (cadr ds) lst (nth 6 ds)
        s1 (car d) a1 (cadr d) a2 (caddr d) bb (sd:bbox outer) ox (car (car bb)) oy (cadr (car bb))
        mx (- (car (cadr bb)) ox) my (- (cadr (cadr bb)) oy)
        pri (sd:box (sd:fw "PRI")) lvn (length (nth 4 st))
        xs (sd:fixpos mx (if dirx a1 a2) margin (if dirx (car lst) (cadr lst)))
        ys (sd:fixpos my (if dirx a2 a1) margin (if dirx (cadr lst) (car lst))))
  (sd:bom+ "VAN-SAN" (- (abs (sd:area outer)) (apply '+ (cons 0.0 (mapcar '(lambda (h) (abs (sd:area h))) holes)))))
  ;; luoi tam van, canh dai doc xa go chinh
  (setq sx (if dirx (sd:fw "SHH") (sd:fw "SHW")) sy (if dirx (sd:fw "SHW") (sd:fw "SHH")) p0 ox)
  (while (< p0 (+ ox mx))
    (setq k oy)
    (while (< k (+ oy my))
      (setq bx2 (list (list p0 k) (list (+ p0 sx) k) (list (+ p0 sx) (+ k sy)) (list p0 (+ k sy))))
      (cond ((vl-every '(lambda (p) (sd:in-panel p outer holes)) bx2) (sd:bom+ "TAM-NG" 1))
            ((vl-some '(lambda (p) (sd:in-panel p outer holes)) (cons (sd:centroid bx2) bx2)) (sd:bom+ "TAM-CAT" 1)))
      (setq k (+ k sy)))
    (setq p0 (+ p0 sx)))
  (setq p0 (+ ox sx))
  (while (< p0 (+ ox mx))
    (foreach sg (sd:clip-segh (list p0 oy) (list p0 (+ oy my)) outer holes) (sd:line (car sg) (cadr sg) "SD-CF-VAN"))
    (setq p0 (+ p0 sx)))
  (setq p0 (+ oy sy))
  (while (< p0 (+ oy my))
    (foreach sg (sd:clip-segh (list ox p0) (list (+ ox mx) p0) outer holes) (sd:line (car sg) (cadr sg) "SD-CF-VAN"))
    (setq p0 (+ p0 sy)))
  ;; suon @s1 vuong goc xa go
  (foreach s (sd:evenpos (if dirx mx my) s1 75.0)
    (foreach sg (if dirx (sd:clip-segh (list (+ ox s) oy) (list (+ ox s) (+ oy my)) outer holes)
                         (sd:clip-segh (list ox (+ oy s)) (list (+ ox mx) (+ oy s)) outer holes))
      (sd:line (car sg) (cadr sg) "SD-CF-SUON")
      (sd:bom+ "SUON-SAN" (distance (car sg) (cadr sg)))))
  ;; xa go chinh + chan giao + giang cheo doc hang
  (setq rowsx (if dirx ys xs) k 0)
  (foreach r rowsx
    (setq row nil)
    (foreach c (if dirx xs ys)
      (setq pl (if dirx (list (+ ox c) (+ oy r)) (list (+ ox r) (+ oy c))))
      (if (and (sd:in-panel pl outer holes)
               (not (vl-some '(lambda (x) (< (distance x pl) 200.0)) avoid)))
        (setq row (cons pl row))))
    (setq row (reverse row))
    (foreach sg (sd:clip-segh (if dirx (list ox (+ oy r)) (list (+ ox r) oy))
                              (if dirx (list (+ ox mx) (+ oy r)) (list (+ ox r) (+ oy my))) outer holes)
      (sd:rect (if dirx (sd:p+ (car sg) 0 (- (car pri))) (sd:p+ (car sg) (- (car pri)) 0))
               (if dirx (distance (car sg) (cadr sg)) (* 2 (car pri)))
               (if dirx (* 2 (car pri)) (distance (car sg) (cadr sg))) "SD-CF-GONG")
      (sd:bom+ "XG-SAN" (* (sd:fw "PRIN") (distance (car sg) (cadr sg)))))
    (foreach p row (sd:leg-sym p))
    (sd:pair-ledgers row lvn (sd:maxlist lst))
    (if (sd:braced-p k (length rowsx) (sd:gi "BRN"))
      (progn
        (setq i 0)
        (while (cadr (sd:nthcdr i row))
          (if (sd:braced-p i (1- (length row)) (sd:gi "BRM"))
            (progn (sd:brace-sym (nth i row) (nth (1+ i) row)) (sd:bom+ "CHEO" (max 1 (1- lvn)))))
          (setq i (1+ i)))))
    (setq legs (append legs row) k (1+ k)))
  ;; giang ngang + giang cheo phuong vuong goc
  (setq k 0)
  (foreach c (if dirx xs ys)
    (setq cur (vl-remove-if-not '(lambda (p) (vl-some '(lambda (x) (equal x p 1e-6)) legs))
                                (mapcar '(lambda (r) (if dirx (list (+ ox c) (+ oy r)) (list (+ ox r) (+ oy c)))) rowsx)))
    (sd:pair-ledgers cur lvn (sd:maxlist lst))
    (if (sd:braced-p k (length (if dirx xs ys)) (sd:gi "BRN"))
      (progn
        (setq i 0)
        (while (cadr (sd:nthcdr i cur))
          (if (sd:braced-p i (1- (length cur)) (sd:gi "BRM"))
            (progn (sd:brace-sym (nth i cur) (nth (1+ i) cur)) (sd:bom+ "CHEO" (max 1 (1- lvn)))))
          (setq i (1+ i)))))
    (setq k (1+ k)))
  (setq nleg (length legs))
  (sd:bom-legs st nleg)
  legs)

;;; --------------------------------------------------------------------------
;;;  Bang khoi luong tong hop tu *SD:BOM*
;;; --------------------------------------------------------------------------
(defun sd:bom-rows (/ rows f)
  (setq rows (list (list "V\\U+00E1n ph\\U+1EE7 phim s\\U+00E0n" (strcat "d\\U+00E0y " (sd:num (sd:fw "PLYT"))) "m\\U+00B2" (sd:rtos (/ (sd:bom "VAN-SAN") 1e6) 2))
                   (list "  T\\U+1EA5m nguy\\U+00EAn / t\\U+1EA5m c\\U+1EAFt" "1220\\U+00D72440" "t\\U+1EA5m" (strcat (itoa (fix (sd:bom "TAM-NG"))) " / " (itoa (fix (sd:bom "TAM-CAT")))))
                   (list "  S\\U+1ED1 t\\U+1EA5m c\\U+1EA7n c\\U+1EA5p" "t\\U+1EA5m c\\U+1EAFt \\U+00D70.6" "t\\U+1EA5m" (itoa (+ (fix (sd:bom "TAM-NG")) (fix (+ (* 0.6 (sd:bom "TAM-CAT")) 0.999999)))))
                   (list "S\\U+01B0\\U+1EDDn s\\U+00E0n" (strcat "h\\U+1ED9p " (sd:fw "SEC")) "m" (sd:rtos (/ (sd:bom "SUON-SAN") 1000.0) 1))
                   (list "X\\U+00E0 g\\U+1ED3 s\\U+00E0n" (strcat "h\\U+1ED9p " (sd:fw "PRI")) "m" (sd:rtos (/ (sd:bom "XG-SAN") 1000.0) 1))))
  (if (> (sd:bom "VAN-DAM") 0)
    (setq rows (append rows
                       (list (list "V\\U+00E1n \\U+0111\\U+00E1y + th\\U+00E0nh d\\U+1EA7m" (strcat "d\\U+00E0y " (sd:num (sd:fw "PLYT"))) "m\\U+00B2" (sd:rtos (/ (sd:bom "VAN-DAM") 1e6) 2))
                             (list "S\\U+01B0\\U+1EDDn d\\U+1EA7m" (strcat "h\\U+1ED9p " (sd:fw "SEC")) "m" (sd:rtos (/ (sd:bom "SUON-DAM") 1000.0) 1))
                             (list "X\\U+00E0 g\\U+1ED3 ngang d\\U+01B0\\U+1EDBi d\\U+1EA7m" (strcat "h\\U+1ED9p " (sd:fw "PRI")) "m" (sd:rtos (/ (sd:bom "XG-DAM") 1000.0) 1))))))
  (foreach e (sd:sort *SD:BOM* '(lambda (a b) (< (car a) (car b))))
    (setq f (sd:split (car e) "|"))
    (cond ((= (car f) "CHAN")
           (setq rows (append rows (list (list (strcat (sd:gi-name) " - ch\\U+00E2n") (cadr f) "ch\\U+00E2n" (itoa (fix (cdr e))))
                                         (list "  K\\U+00EDch ch\\U+00E2n / k\\U+00EDch U" (caddr f) "b\\U+1ED9" (itoa (fix (cdr e))))))))
          ((and (= (car f) "GIANG") (> (cdr e) 0) (/= (sd:gi "TYPE") "Chong"))
           (setq rows (append rows (list (list "Gi\\U+1EB1ng ngang" (strcat "L=" (cadr f)) "thanh" (itoa (fix (cdr e))))))))))
  (if (and (> (sd:bom "CHEO") 0) (/= (sd:gi "TYPE") "Chong"))
    (setq rows (append rows (list (list "Gi\\U+1EB1ng ch\\U+00E9o" "theo b\\U+1ED1 tr\\U+00ED" "thanh" (itoa (fix (sd:bom "CHEO"))))))))
  rows)

(defun sd:bom-table (title sc / rows pt e0)
  (setq rows (sd:bom-rows))
  (if (setq pt (sd:getpt "\nDiem chen bang khoi luong <Enter bo qua>: " nil))
    (progn
      (setq e0 (entlast))
      (sd:table2 pt title '(("H\\U+1EA0NG M\\U+1EE4C" 50) ("QUY C\\U+00C1CH" 56) ("\\U+0110V" 12) ("KH\\U+1ED0I L\\U+01AF\\U+1EE2NG" 24))
                 (mapcar '(lambda (r) (list "R" r nil)) rows) -1 sc)
      (sd:vk-reg (if e0 (entnext e0) (entnext)) rows (/ (+ (sd:bom "VAN-SAN") (sd:bom "VAN-DAM")) 1e6)))
    (if *SD:VKID* (princ "\n[SD] Bo qua bang -> khoi luong coffa khong duoc dang ky cho SDKL.")))
  (sd:fw-csv title rows))

;;; --------------------------------------------------------------------------
;;;  SDCOFFASAN - Coffa san + gian giao do + giang (1 hay nhieu o san chon tay)
;;; --------------------------------------------------------------------------
(defun c:SDCOFFASAN (/ sc ss i e polys ts hs dirx ds d st bb pt)
  (sd:begin)
  (if (not (sd:dlg "Coffa san + gian giao (SDCOFFASAN)"
                   (list (list "name" "Ten o san / khu vuc (cho bang khoi luong)" 'str (cond (*SD:SNAME*) ("S1")))
                         (list "ts" "Chieu day san (mm)" 'real (cond (*SD:SLT*) (150.0)))
                         (list "hs" "Chieu cao tu san duoi den day san (mm)" 'real (cond (*SD:SLH*) (3300.0)))
                         (list "dir" "Xa go chinh chay theo phuong" 'kw "X" '("X" "Y"))
                         (list "sc" "Ty le ve 1/" 'int 50))))
    (exit))
  (setq sc (float (sd:v "sc")) *SD:BOM* nil)
  (princ "\nChon cac o san (polyline kin, mep dam / vach bao quanh): ")
  (if (not (setq ss (ssget '((0 . "LWPOLYLINE")))))
    (princ "\n[SD] Chua chon o san.")
    (progn
      (setq i 0)
      (repeat (sslength ss)
        (setq e (ssname ss i) i (1+ i))
        (if (vlax-curve-isClosed e) (setq polys (cons (sd:curve-pts e) polys))))
      (setq ts (sd:v "ts") hs (sd:v "hs") *SD:SLT* ts *SD:SLH* hs
            dirx (/= "Y" (sd:v "dir")))
      (if (not (setq ds (sd:san-design ts hs)))
        (princ "\n[SD] Khong cau tao duoc chieu cao giao voi loai giao hien tai (SDGIAOSET).")
        (progn
          (setq d (car ds) st (cadr ds))
          (foreach poly polys
            (sd:san-panel poly nil dirx ds sc 300.0 nil)
            (setq bb (sd:bbox poly))
            (sd:use-dimstyle sc)
            (sd:dim (car bb) (list (car (cadr bb)) (cadr (car bb))) "H" (sd:p+ (car bb) 0 (* -6 sc)))
            (sd:dim (car bb) (list (car (car bb)) (cadr (cadr bb))) "V" (sd:p+ (car bb) (* -6 sc) 0)))
          (setq bb (sd:bbox (car polys)))
          (sd:san-note (list (car (car bb)) (- (cadr (car bb)) (* 14 sc))) ts ds sc)
          (if (setq pt (sd:getpt "\nDiem chen mat cat gian giao (chan tai cao do san duoi) <Enter bo qua>: " nil))
            (sd:gi-section pt (sd:evenpos (* 4 (cadr d)) (cadr d) 0.0) hs ts st (car d) sc "M\\U+1EB6T C\\U+1EAET \\U+0110I\\U+1EC2N H\\U+00CCNH COFFA S\\U+00C0N + GI\\U+00C0N GI\\U+00C1O"))
          (setq *SD:SNAME* (sd:v "name")
                *SD:VKID* (list (sd:v "name") "San" (/ (* (sd:bom "VAN-SAN") ts) 1e9) "SDCOFFASAN"))
          (sd:bom-table (strcat "COFFA S\\U+00C0N " (sd:v "name") " + GI\\U+00C0N GI\\U+00C1O") sc)
          (princ (strcat "\n[SD] " (itoa (length polys)) " o san: chan giao " (sd:num (cadr d)) "x" (sd:num (caddr d))
                         ", tai " (sd:rtos (cadddr d) 1) "/" (sd:rtos (nth 4 ds) 1) " kN/chan."))
          (sd:use-dimstyle *SD:SCALE*)))))
  (sd:finish))

(defun sd:san-note (p ts ds sc / d st)
  (setq d (car ds) st (cadr ds))
  (sd:text p (strcat "COFFA S\\U+00C0N d\\U+00E0y " (sd:num ts) ": q = " (sd:rtos (nth 2 ds) 2) " kPa; v\\U+00E1n " (sd:num (sd:fw "PLYT"))
                     "; s\\U+01B0\\U+1EDDn " (sd:fw "SEC") " @" (sd:num (car d)) "; x\\U+00E0 g\\U+1ED3 " (itoa (sd:fw "PRIN")) "\\U+00D7" (sd:fw "PRI")
                     " @" (sd:num (caddr d)) "; ch\\U+00E2n gi\\U+00E1o " (sd:num (cadr d)) "\\U+00D7" (sd:num (caddr d)) " ("
                     (sd:rtos (cadddr d) 1) "/" (sd:rtos (nth 4 ds) 1) " kN)")
           (* 2.5 sc) "L" "SD-CHU")
  (sd:text (sd:p+ p 0 (* -5 sc))
           (strcat (sd:gi-name) ": k\\U+00EDch ch\\U+00E2n " (sd:rtos (car st) 0) " + " (sd:gi-pcs-str (nth 3 st))
                   " + k\\U+00EDch U " (sd:rtos (cadr st) 0) "; gi\\U+1EB1ng ngang " (itoa (length (nth 4 st)))
                   " t\\U+1EA7ng; gi\\U+1EB1ng ch\\U+00E9o h\\U+00E0ng bi\\U+00EAn + m\\U+1ED7i " (itoa (sd:gi "BRN")) " h\\U+00E0ng, m\\U+1ED7i " (itoa (sd:gi "BRM")) " nh\\U+1ECBp")
           (* 2.5 sc) "L" "SD-CHU")
  (if (/= (nth 5 ds) "") (sd:text (sd:p+ p 0 (* -10 sc)) (nth 5 ds) (* 2.5 sc) "L" "SD-CHU")))

;;; --------------------------------------------------------------------------
;;;  Dam: thiet ke, mat bang, mat cat
;;;  dd = (c aL nj hu st qb ps sp cap chu-thich-on-dinh)
;;; --------------------------------------------------------------------------
(defun sd:dam-design (bb hb ts hs / tp sec pri qb ps sp hu gs lst cap c nj lj aL)
  (setq tp (sd:fw "PLYT") sec (sd:box (sd:fw "SEC")) pri (sd:box (sd:fw "PRI"))
        qb (+ (* (sd:fw "GAM") (/ hb 1000.0)) 0.5 (sd:gi "LL") (sd:gi "VIB"))
        ps (* (sd:fw "GAM") (/ (- hb ts) 1000.0))
        sp (sd:fw-design (max ps 5.0) (sd:fw "TIE"))
        hu (- hs (- hb ts) tp (cadr sec) (cadr pri)))
  (if (setq gs (sd:gi-setup hu))
    (progn
      (setq lst (cadr gs) cap (caddr gs)
            c  (cond ((car (vl-remove-if '(lambda (x) (< x (+ bb 500.0))) (vl-sort (cadr lst) '<)))) ((+ bb 500.0)))
            nj (max 2 (1+ (fix (+ (/ bb 150.0) 0.999999))))
            lj (sd:fw-span (/ (* qb (/ bb (1- nj))) 1000.0) (/ (* 2.0 (sd:box-I sec)) (cadr sec)) (sd:box-I sec)
                           (sd:fw "FS") 2.1e5 (sd:fw "DEF")))
      (foreach a (vl-sort (car lst) '>)
        (if (and (null aL) (<= a lj)
                 (<= (/ (* (/ qb 1000.0) bb a (- (* 2 c) bb)) 8.0)
                     (* (sd:fw "FS") (/ (* 2.0 (sd:fw "PRIN") (sd:box-I pri)) (cadr pri))))
                 (<= (/ (* (/ qb 1000.0) bb a) 2000.0) cap))
          (setq aL a)))
      (if (null aL)
        (progn (setq aL (apply 'min (car lst)))
               (princ (strcat "\n[!] Dam " (sd:num bb) "x" (sd:num hb) ": khoang cach chan nho nhat van chua dat, can kiem tra."))))
      (list c aL nj hu (car gs) qb ps sp cap (cadddr gs) (car lst)))))

;; Mat bang dam theo truc p1-p2: tra ve danh sach chan giao
(defun sd:dam-plan (p1 p2 bb hb ts dd sc name / ang len stations o legs k c aL nj lvn)
  (setq c (nth 0 dd) aL (nth 1 dd) nj (nth 2 dd) lvn (length (nth 4 (nth 4 dd)))
        ang (angle p1 p2) len (distance p1 p2)
        stations (sd:fixpos len aL 300.0 (nth 10 dd)))
  (sd:pline (mapcar 'sd:2d (list (polar p1 (+ ang (/ pi 2)) (/ bb 2)) (polar p2 (+ ang (/ pi 2)) (/ bb 2))
                                 (polar p2 (- ang (/ pi 2)) (/ bb 2)) (polar p1 (- ang (/ pi 2)) (/ bb 2))))
            t "SD-CF-VAN")
  (foreach v (sd:evenpos bb (/ bb (1- nj)) 0.0)
    (sd:line (polar p1 (- ang (/ pi 2)) (- (/ bb 2) v)) (polar p2 (- ang (/ pi 2)) (- (/ bb 2) v)) "SD-CF-SUON"))
  (foreach s stations
    (setq o (polar p1 ang s))
    (sd:line (polar o (+ ang (/ pi 2)) (+ (/ c 2) 150)) (polar o (- ang (/ pi 2)) (+ (/ c 2) 150)) "SD-CF-GONG")
    (foreach sg (list (/ c 2) (- (/ c 2)))
      (sd:leg-sym (sd:2d (polar o (+ ang (/ pi 2)) sg)))
      (setq legs (cons (sd:2d (polar o (+ ang (/ pi 2)) sg)) legs))))
  (setq k 0)
  (while (cadr (sd:nthcdr k stations))
    (if (sd:braced-p k (1- (length stations)) (sd:gi "BRM"))
      (foreach sg (list (/ c 2) (- (/ c 2)))
        (sd:brace-sym (sd:2d (polar (polar p1 ang (nth k stations)) (+ ang (/ pi 2)) sg))
                      (sd:2d (polar (polar p1 ang (nth (1+ k) stations)) (+ ang (/ pi 2)) sg)))))
    (setq k (1+ k)))
  (sd:text (sd:2d (polar (polar p1 ang (/ len 2)) (+ ang (/ pi 2)) (+ (/ c 2) (* 5 sc))))
           (strcat name " " (sd:num bb) "\\U+00D7" (sd:num hb) ": gi\\U+00E1o " (sd:num c) "\\U+00D7" (sd:num aL))
           (* 2.0 sc) "MC" "SD-CHU")
  (sd:dam-bom len stations dd bb hb ts)
  legs)

;; Khoi luong 1 doan dam dai len voi cac tram chan giao stations (khong ve)
(defun sd:dam-bom (len stations dd bb hb ts / c nj lvn k)
  (setq c (nth 0 dd) nj (nth 2 dd) lvn (length (nth 4 (nth 4 dd))) k 0)
  (sd:bom+ "VAN-DAM" (* len (+ bb (* 2 (- hb ts)))))
  (sd:bom+ "SUON-DAM" (+ (* nj len) (* 2 (- hb ts) (length (sd:evenpos len (car (nth 7 dd)) 50.0)))))
  (sd:bom+ "XG-DAM" (* (sd:fw "PRIN") (+ c 300.0) (length stations)))
  (sd:pair-ledgers (mapcar '(lambda (s) (list s 0.0)) stations) (* 2 lvn) 1e9)
  (sd:bom+ (strcat "GIANG|" (sd:num c)) (* lvn (length stations)))
  (while (cadr (sd:nthcdr k stations))
    (if (sd:braced-p k (1- (length stations)) (sd:gi "BRM")) (sd:bom+ "CHEO" (* 2 (max 1 (1- lvn)))))
    (setq k (1+ k)))
  (sd:bom-legs (nth 4 dd) (* 2 (length stations))))

;; Mat cat chi tiet dam tai o (tam day dam, cao do san duoi)
(defun sd:dam-section (o bb hb ts hs dd sc name / tp sec pri c aL nj hu st qb ps sp wb mb ex ys)
  (setq tp (sd:fw "PLYT") sec (sd:box (sd:fw "SEC")) pri (sd:box (sd:fw "PRI"))
        c (nth 0 dd) aL (nth 1 dd) nj (nth 2 dd) hu (nth 3 dd) st (nth 4 dd) qb (nth 5 dd) ps (nth 6 dd) sp (nth 7 dd)
        wb (+ (/ c 2) 700.0) mb (- hs (- hb ts)) ex (+ tp (cadr sec) (cadr pri)))
  (sd:pline (list (sd:p+ o (/ bb -2) mb) (sd:p+ o (/ bb 2) mb) (sd:p+ o (/ bb 2) hs) (sd:p+ o wb hs)
                  (sd:p+ o wb (+ hs ts)) (sd:p+ o (- wb) (+ hs ts)) (sd:p+ o (- wb) hs) (sd:p+ o (/ bb -2) hs))
            t "SD-BETONG")
  (sd:line (sd:p+ o (- wb) 0) (sd:p+ o wb 0) "SD-BETONG")
  (sd:rect (sd:p+ o (- (/ bb -2) tp) (- mb tp)) (+ bb tp tp) tp "SD-CF-VAN")
  (foreach v (sd:evenpos bb (/ bb (1- nj)) 0.0)
    (sd:rect (sd:p+ o (- (+ (/ bb -2) v) (/ (car sec) 2)) (- mb tp (cadr sec))) (car sec) (cadr sec) "SD-CF-SUON"))
  (sd:rect (sd:p+ o (- (+ (/ c 2) 150)) hu) (+ c 300) (cadr pri) "SD-CF-GONG")
  (setq ys (if (<= (- hb ts) 600.0) (list (/ (- hb ts) 2.0)) (sd:evenpos (- hb ts) (cadr sp) 100.0)))
  (foreach sg '(-1.0 1.0)
    (sd:rect (sd:p+ o (if (< sg 0) (- (/ bb -2) tp) (/ bb 2)) (- mb tp)) tp (+ (- hb ts) tp) "SD-CF-VAN")
    (sd:rect (sd:p+ o (if (< sg 0) (- (/ bb -2) tp (cadr sec)) (+ (/ bb 2) tp)) (- mb tp (cadr sec)))
             (cadr sec) (- hb ts) "SD-CF-SUON")
    (foreach y ys
      (sd:rect (sd:p+ o (if (< sg 0) (- (/ bb -2) ex) (+ (/ bb 2) tp (cadr sec))) (+ mb y (- (car pri))))
               (cadr pri) (* 2 (car pri)) "SD-CF-GONG"))
    (sd:line (sd:p+ o (* sg (+ (/ bb 2) ex 250)) (+ hu (cadr pri))) (sd:p+ o (* sg (+ (/ bb 2) ex)) (+ mb (car ys))) "SD-CF-CHONG")
    (sd:rect (sd:p+ o (if (< sg 0) (- wb) (+ (/ bb 2) tp)) (- hs tp)) (- wb (/ bb 2) tp) tp "SD-CF-VAN"))
  (if (> (- hb ts) 700.0)
    (foreach y ys (sd:line (sd:p+ o (- (+ (/ bb 2) ex 80)) (+ mb y)) (sd:p+ o (+ (/ bb 2) ex 80) (+ mb y)) "SD-CF-TY")))
  (sd:gi-section-legs o (list (/ c -2) (/ c 2)) hu st)
  (sd:use-dimstyle sc)
  (sd:dim (sd:p+ o (/ bb -2) mb) (sd:p+ o (/ bb 2) mb) "H" (sd:p+ o 0 (+ hs ts (* 6 sc))))
  (sd:dim (sd:p+ o (/ c -2) 0) (sd:p+ o (/ c 2) 0) "H" (sd:p+ o 0 (* -8 sc)))
  (sd:dimchain (list (sd:p+ o wb 0) (sd:p+ o wb (car st)) (sd:p+ o wb hu) (sd:p+ o wb mb) (sd:p+ o wb hs) (sd:p+ o wb (+ hs ts)))
               "V" (sd:p+ o (+ wb (* 8 sc)) 0))
  (sd:text (sd:p+ o (- wb) (* -16 sc)) (strcat "M\\U+1EB6T C\\U+1EAET COFFA D\\U+1EA6M " name " (" (sd:num bb) "\\U+00D7" (sd:num hb) ")") (* 3.0 sc) "L" "SD-CHU")
  (sd:text (sd:p+ o (- wb) (* -21 sc))
           (strcat "\\U+0110\\U+00E1y: q = " (sd:rtos qb 1) " kPa, " (itoa nj) " s\\U+01B0\\U+1EDDn d\\U+1ECDc " (sd:fw "SEC") "; x\\U+00E0 g\\U+1ED3 ngang "
                   (itoa (sd:fw "PRIN")) "\\U+00D7" (sd:fw "PRI") "; " (sd:gi-name) " " (sd:num c) "\\U+00D7" (sd:num aL)
                   " (" (sd:rtos (/ (* (/ qb 1000.0) bb aL) 2000.0) 1) "/" (sd:rtos (nth 8 dd) 1) " kN). Th\\U+00E0nh: p = "
                   (sd:rtos ps 1) " kPa, s\\U+01B0\\U+1EDDn @" (sd:num (car sp)) (if (> (- hb ts) 700.0) ", ty xuy\\U+00EAn d\\U+1EA7m" ", n\\U+1EB9p ch\\U+1ED1ng xi\\U+00EAn"))
           (* 2.0 sc) "L" "SD-CHU")
  (if (/= (nth 9 dd) "") (sd:text (sd:p+ o (- wb) (* -25 sc)) (nth 9 dd) (* 2.0 sc) "L" "SD-CHU")))

;;; --------------------------------------------------------------------------
;;;  SDCOFFADAM - Coffa 1 dam (chon truc) + mat cat + khoi luong
;;; --------------------------------------------------------------------------
(defun c:SDCOFFADAM (/ sc name bb hb ts hs dd p1 p2 pt)
  (sd:begin)
  (if (not (sd:dlg "Coffa dam (SDCOFFADAM)"
                   (list (list "name" "Ten dam" 'str (cond (*SD:BMN*) ("D1")))
                         (list "bb" "Be rong dam b (mm)" 'real (cond (*SD:BMB*) (300.0)))
                         (list "hb" "Chieu cao dam h (ke ca san) (mm)" 'real (cond (*SD:BMH*) (600.0)))
                         (list "ts" "Chieu day san (mm)" 'real (cond (*SD:SLT*) (150.0)))
                         (list "hs" "Chieu cao tu san duoi den day san (mm)" 'real (cond (*SD:SLH*) (3300.0)))
                         (list "sc" "Ty le ve 1/" 'int 20))))
    (exit))
  (setq name (sd:v "name") bb (sd:v "bb") hb (sd:v "hb") ts (sd:v "ts") hs (sd:v "hs")
        sc   (float (sd:v "sc"))
        *SD:BMN* name *SD:BMB* bb *SD:BMH* hb *SD:SLT* ts *SD:SLH* hs *SD:BOM* nil)
  (if (not (setq dd (sd:dam-design bb hb ts hs)))
    (princ "\n[SD] Khong cau tao duoc chieu cao giao duoi dam (SDGIAOSET).")
    (progn
      (if (and (setq p1 (sd:getpt "\nDiem dau truc dam tren mat bang <Enter = chi ve mat cat>: " nil))
               (setq p2 (sd:getpt "\nDiem cuoi truc dam: " p1)))
        (sd:dam-plan (sd:2d p1) (sd:2d p2) bb hb ts dd sc name))
      (if (setq pt (sd:getpt "\nDiem chen mat cat dam (tam day dam tai cao do san duoi) <Enter bo qua>: " nil))
        (sd:dam-section pt bb hb ts hs dd sc name))
      (if (> (sd:bom "VAN-DAM") 0)
        (setq *SD:VKID* (list name "Dam" (/ (* bb (- hb ts) (/ (sd:bom "VAN-DAM") (+ bb (* 2 (- hb ts))))) 1e9) "SDCOFFADAM")))
      (if *SD:BOM* (sd:bom-table (strcat "COFFA D\\U+1EA6M " name) sc))
      (sd:use-dimstyle *SD:SCALE*)))
  (sd:finish))

;;; --------------------------------------------------------------------------
;;;  Nhan dien dam / o san tu ban ve
;;; --------------------------------------------------------------------------
;; "D1 (300x600)" -> (300.0 600.0)
(defun sd:parse-size (s / i n c a b j)
  (setq i 2 n (strlen s))
  (while (and (< i n) (not a))
    (setq c (substr s i 1))
    (if (and (member c '("x" "X" "*")) (wcmatch (substr s (1- i) 1) "#") (wcmatch (substr s (1+ i) 1) "#"))
      (progn
        (setq j (1- i))
        (while (and (> j 1) (wcmatch (substr s (1- j) 1) "#")) (setq j (1- j)))
        (setq a (atof (substr s j (- i j))) b (atof (substr s (1+ i))))))
    (setq i (1+ i)))
  (if (and a b (> a 0) (> b 0)) (list a b)))

(defun sd:pt-seg (p a b / l u)
  (setq l (distance a b))
  (if (< l 1e-6) (distance p a)
    (progn
      (setq u (/ (+ (* (- (car p) (car a)) (- (car b) (car a))) (* (- (cadr p) (cadr a)) (- (cadr b) (cadr a)))) (* l l))
            u (max 0.0 (min 1.0 u)))
      (distance (sd:2d p) (list (+ (car a) (* u (- (car b) (car a)))) (+ (cadr a) (* u (- (cadr b) (cadr a)))))))))

;; Doc cac text kich thuoc trong ban ve: ((diem (b h)) ...)
(defun sd:size-texts (/ ss i ed sz r)
  (if (setq ss (ssget "_X" '((0 . "TEXT,MTEXT"))))
    (progn
      (setq i 0)
      (repeat (sslength ss)
        (setq ed (entget (ssname ss i)) i (1+ i))
        (if (setq sz (sd:parse-size (cdr (assoc 1 ed))))
          (setq r (cons (list (sd:2d (cdr (assoc 10 ed))) sz) r))))))
  r)

;; Dam tu doi tuong: polyline kin 4 dinh = vien dam; duong ho / LINE = truc dam.
;; Tra ve ((p1 p2 b h vien-ename) ...)
(defun sd:detect-beams (ss defb defh / i e ed pts d1 d2 res txts near sz p1 p2 bw o)
  (setq txts (sd:size-texts) i 0)
  (repeat (sslength ss)
    (setq e (ssname ss i) i (1+ i) ed (entget e))
    (cond
      ((and (= (cdr (assoc 0 ed)) "LWPOLYLINE") (vlax-curve-isClosed e)
            (= (length (setq pts (sd:curve-pts e))) 4))
       (setq d1 (distance (nth 0 pts) (nth 1 pts)) d2 (distance (nth 1 pts) (nth 2 pts)))
       (if (>= d1 d2)
         (setq p1 (sd:centroid (list (nth 0 pts) (nth 3 pts))) p2 (sd:centroid (list (nth 1 pts) (nth 2 pts))) bw d2)
         (setq p1 (sd:centroid (list (nth 0 pts) (nth 1 pts))) p2 (sd:centroid (list (nth 2 pts) (nth 3 pts))) bw d1))
       (setq res (cons (list p1 p2 bw nil e) res)))
      ((= (cdr (assoc 0 ed)) "LWPOLYLINE")
       (princ "\n[!] Bo qua polyline kin khong phai hinh chu nhat (dung lam cot/vach neu can)."))
      ((= (cdr (assoc 0 ed)) "LINE")
       (setq res (cons (list (sd:2d (cdr (assoc 10 ed))) (sd:2d (cdr (assoc 11 ed))) nil nil nil) res)))
      ((and (= (cdr (assoc 0 ed)) "LWPOLYLINE") (not (vlax-curve-isClosed e)))
       (setq pts (sd:curve-pts e))
       (while (cadr pts)
         (setq res (cons (list (car pts) (cadr pts) nil nil nil) res) pts (cdr pts))))))
  ;; kich thuoc tu text gan nhat (<= 1500 mm tu truc dam)
  (mapcar '(lambda (bm / best dmin d)
             (foreach tx txts
               (setq d (sd:pt-seg (car tx) (car bm) (cadr bm)))
               (if (and (< d 1500.0) (or (null dmin) (< d dmin))) (setq dmin d best (cadr tx))))
             (list (car bm) (cadr bm)
                   (cond ((caddr bm)) ((car best)) (defb))
                   (cond ((cadr best)) (defh))
                   (nth 4 bm)))
          res))

;; Vien dam tu truc + be rong (doi tuong tam)
(defun sd:beam-outline (bm / a ang e)
  (setq ang (angle (car bm) (cadr bm)) a (/ (caddr bm) 2.0))
  (sd:pline (mapcar 'sd:2d (list (polar (car bm) (+ ang (/ pi 2)) a) (polar (cadr bm) (+ ang (/ pi 2)) a)
                                 (polar (cadr bm) (- ang (/ pi 2)) a) (polar (car bm) (- ang (/ pi 2)) a)))
            t "SD-OSAN")
  (setq e (entlast))
  (setq *SD:TMP* (cons (vlax-ename->vla-object e) *SD:TMP*))
  e)

;; O san = vung san - dam - cot/vach - lo. Tra ve ((vien (lo ...)) ...)
(defun sd:detect-panels (outline-e beams obst auto / R rg ents loops bb res outers ok)
  (setq R (sd:region outline-e) bb (sd:bbox (sd:curve-pts outline-e)))
  (if (null R)
    (princ "\n[SD] Khong tao duoc region tu duong bao san.")
    (progn
      (foreach e (append (mapcar '(lambda (bm) (cond ((nth 4 bm)) ((sd:beam-outline bm)))) beams) obst)
        (if (setq rg (sd:region e))
          (if (vl-catch-all-error-p (vl-catch-all-apply 'vla-Boolean (list R 2 rg)))
            (vl-catch-all-apply 'vla-Delete (list rg)))))
      (setq ents (sd:region->ents R "SD-OSAN"))
      (foreach e ents
        (if (= (cdr (assoc 0 (entget e))) "LWPOLYLINE")
          (setq loops (cons (list (sd:curve-pts e) e) loops))
          (princ "\n[!] Bo qua o san co bien cong.")))
      ;; vong nam trong vong khac = lo; phan con lai = o san
      (foreach lp loops
        (if (not (vl-some '(lambda (x) (and (not (eq x lp)) (sd:inpoly (car (car lp)) (car x))
                                            (> (abs (sd:area (car x))) (abs (sd:area (car lp))))))
                          loops))
          (setq outers (cons lp outers))))
      (foreach o outers
        (setq ok (or (not auto)
                     (not (vl-some '(lambda (p) (or (equal (car p) (car (car bb)) 1.0) (equal (car p) (car (cadr bb)) 1.0)
                                                    (equal (cadr p) (cadr (car bb)) 1.0) (equal (cadr p) (cadr (cadr bb)) 1.0)))
                                   (car o)))))
        (if (and ok (> (abs (sd:area (car o))) 2e5))
          (setq res (cons (list (car o)
                                (mapcar 'car (vl-remove-if-not
                                               '(lambda (x) (and (not (eq x o)) (sd:inpoly (car (car x)) (car o))
                                                                 (< (abs (sd:area (car x))) (abs (sd:area (car o))))))
                                               loops)))
                          res))
          (entdel (cadr o))))))
  res)

;;; --------------------------------------------------------------------------
;;;  SDGIAOTANG - Mat bang gian giao tong the ca tang: tu nhan dam + o san
;;; --------------------------------------------------------------------------
(defun c:SDGIAOTANG (/ sc ss ssc sso es obst outline auto beams panels defb defh ts hs dirx ds dcache dd
                       key blegs n bb all pt i e p ptb types)
  (sd:begin)
  (if (not (sd:dlg "Gian giao ca tang (SDGIAOTANG)"
                   (list (list "name" "Ten tang / khu vuc (cho bang khoi luong)" 'str (cond (*SD:GTNAME*) ("TANG")))
                         (list "defb" "Be rong dam mac dinh (khong co text bxh) (mm)" 'real (cond (*SD:BMB*) (300.0)))
                         (list "defh" "Chieu cao dam mac dinh (mm)" 'real (cond (*SD:BMH*) (600.0)))
                         (list "ts" "Chieu day san (mm)" 'real (cond (*SD:SLT*) (150.0)))
                         (list "hs" "Chieu cao tu san duoi den day san (mm)" 'real (cond (*SD:SLH*) (3300.0)))
                         (list "dir" "Xa go san chay theo phuong" 'kw "X" '("X" "Y"))
                         (list "sec" "Ve mat cat dien hinh san + tung loai dam" 'tog t)
                         (list "sc" "Ty le ve 1/" 'int 100))))
    (exit))
  (setq sc (float (sd:v "sc")) *SD:BOM* nil)
  (princ "\nChon cac dam (polyline chu nhat = vien dam, hoac LINE / polyline ho = truc dam): ")
  (if (not (setq ss (ssget '((0 . "LINE,LWPOLYLINE")))))
    (princ "\n[SD] Chua chon dam.")
    (progn
      (princ "\nChon cot / vach (polyline kin) <Enter neu khong>: ")
      (setq ssc (ssget '((0 . "LWPOLYLINE"))))
      (princ "\nChon lo san (polyline kin) <Enter neu khong>: ")
      (setq sso (ssget '((0 . "LWPOLYLINE"))))
      (setq es (entsel "\nChon duong bao san (polyline kin) <Enter = tu lay theo dam bien>: "))
      (setq defb (sd:v "defb") defh (sd:v "defh") ts (sd:v "ts") hs (sd:v "hs")
            *SD:BMB* defb *SD:BMH* defh *SD:SLT* ts *SD:SLH* hs)
      (setq dirx (/= "Y" (sd:v "dir")))
      ;; ---- nhan dien
      (setq beams (sd:detect-beams ss defb defh))
      (foreach s (list ssc sso)
        (if s (progn (setq i 0)
                     (repeat (sslength s) (setq e (ssname s i) i (1+ i)) (if (vlax-curve-isClosed e) (setq obst (cons e obst)))))))
      (setq auto (null es))
      (if auto
        (progn
          (setq all (apply 'append (mapcar '(lambda (bm) (list (car bm) (cadr bm))) beams))
                bb (sd:bbox all)
                p (+ defb 100.0))
          (sd:pline (list (sd:p+ (car bb) (- p) (- p)) (list (+ (car (cadr bb)) p) (- (cadr (car bb)) p))
                          (sd:p+ (cadr bb) p p) (list (- (car (car bb)) p) (+ (cadr (cadr bb)) p)))
                    t "SD-OSAN")
          (setq outline (entlast) *SD:TMP* (cons (vlax-ename->vla-object outline) *SD:TMP*)))
        (setq outline (car es)))
      (setq panels (sd:detect-panels outline beams obst auto))
      (setq types nil)
      (foreach bm beams (setq types (sd:addcnt (strcat (sd:num (caddr bm)) "x" (sd:num (cadddr bm))) 1 types)))
      (princ (strcat "\n[SD] Nhan dien: " (itoa (length beams)) " doan dam ("
                     (sd:join (mapcar '(lambda (x) (strcat (car x) ": " (itoa (cdr x)))) types) ", ")
                     "), " (itoa (length panels)) " o san."))
      ;; ---- dam
      (foreach bm beams
        (setq key (list (caddr bm) (cadddr bm)))
        (if (not (setq dd (cdr (assoc key dcache))))
          (setq dd (sd:dam-design (caddr bm) (cadddr bm) ts hs) dcache (cons (cons key dd) dcache)))
        (if dd
          (setq blegs (append blegs (sd:dam-plan (car bm) (cadr bm) (caddr bm) (cadddr bm) ts dd sc
                                                 (strcat "D" (sd:num (caddr bm)) "x" (sd:num (cadddr bm))))))
          (princ (strcat "\n[!] Khong cau tao duoc giao cho dam " (sd:num (caddr bm)) "x" (sd:num (cadddr bm))))))
      ;; ---- san
      (if (setq ds (sd:san-design ts hs))
        (foreach pn panels (sd:san-panel (car pn) (cadr pn) dirx ds sc 250.0 blegs))
        (princ "\n[!] Khong cau tao duoc giao san."))
      ;; ---- chu thich, mat cat, bang
      (setq bb (sd:bbox (apply 'append (mapcar '(lambda (bm) (list (car bm) (cadr bm))) beams)))
            p  (list (car (car bb)) (- (cadr (car bb)) (* 15 sc))))
      (sd:text p "M\\U+1EB6T B\\U+1EB0NG B\\U+1ED0 TR\\U+00CD GI\\U+00C0N GI\\U+00C1O \\U+0110\\U+1EE0 D\\U+1EA6M S\\U+00C0N" (* 4.0 sc) "L" "SD-CHU")
      (if ds (sd:san-note (sd:p+ p 0 (* -7 sc)) ts ds sc))
      (setq n 0)
      (foreach x dcache
        (if (cdr x)
          (sd:text (sd:p+ p 0 (- (* -22 sc) (* n 4 sc)))
                   (strcat "D\\U+1EA7m " (sd:num (car (car x))) "\\U+00D7" (sd:num (cadr (car x))) ": gi\\U+00E1o " (sd:num (nth 0 (cdr x)))
                           "\\U+00D7" (sd:num (nth 1 (cdr x))) ", " (sd:gi-pcs-str (nth 3 (nth 4 (cdr x)))) ", k\\U+00EDch "
                           (sd:rtos (car (nth 4 (cdr x))) 0) "/" (sd:rtos (cadr (nth 4 (cdr x))) 0)
                           ", t\\U+1EA3i ch\\U+00E2n " (sd:rtos (/ (* (/ (nth 5 (cdr x)) 1000.0) (car (car x)) (nth 1 (cdr x))) 2000.0) 1)
                           "/" (sd:rtos (nth 8 (cdr x)) 1) " kN")
                   (* 2.5 sc) "L" "SD-CHU"))
        (setq n (1+ n)))
      (if (and (sd:v "sec")
               (setq ptb (sd:getpt "\nDiem chen mat cat (cao do san duoi): " nil)))
        (progn
          (if ds (sd:gi-section ptb (sd:evenpos (* 4 (cadr (car ds))) (cadr (car ds)) 0.0) hs ts (cadr ds) (car (car ds)) (/ sc 2.5)
                                "M\\U+1EB6T C\\U+1EAET \\U+0110I\\U+1EC2N H\\U+00CCNH S\\U+00C0N"))
          (if ds (setq ptb (sd:p+ ptb (+ (* 4 (cadr (car ds))) 3000.0) 0)))
          (foreach x dcache
            (if (cdr x)
              (progn
                (sd:dam-section ptb (car (car x)) (cadr (car x)) ts hs (cdr x) (/ sc 2.5)
                                (strcat "D" (sd:num (car (car x))) "x" (sd:num (cadr (car x)))))
                (setq ptb (sd:p+ ptb (+ (nth 0 (cdr x)) 3000.0) 0)))))))
      (setq *SD:GTNAME* (sd:v "name")
            *SD:VKID* (list (sd:v "name") "San + Dam" 0.0 "SDGIAOTANG"))
      (sd:bom-table (strcat "GI\\U+00C0N GI\\U+00C1O T\\U+1ED4NG TH\\U+1EC2 " (sd:v "name")) sc)
      (princ (strcat "\n[SD] Tong: " (itoa (fix (apply '+ (mapcar 'cdr (vl-remove-if-not '(lambda (x) (wcmatch (car x) "CHAN|*")) *SD:BOM*)))))
                     " chan giao, " (sd:rtos (/ (+ (sd:bom "VAN-SAN") (sd:bom "VAN-DAM")) 1e6) 1) " m2 van."))
      (sd:use-dimstyle *SD:SCALE*)))
  (sd:finish))

;;; --------------------------------------------------------------------------
;;;  SDGIAOTK - Thong ke gian giao theo tang (dien tich san, dam, chieu cao tang)
;;;             + bang dinh muc theo to hop chieu cao / chieu day san / loai dam
;;; --------------------------------------------------------------------------
(setq *SD:GIDEF* (append *SD:GIDEF* '(("OSAN" . 36.0) ("NHIP" . 7000.0))))  ; o san dien hinh (m2), nhip dam dien hinh (mm)

(defun sd:bom-merge (a b k)
  (foreach e b (setq a (sd:addcnt (car e) (* k (cdr e)) a)))
  a)

;; Dem o san chu nhat lx x ly (khong ve), ghi vao *SD:BOM*
(defun sd:count-panel (lx ly ds / d st lst s1 a1 a2 xs ys nx ny lvn i rb bb2 cb bc)
  (setq d (car ds) st (cadr ds) lst (nth 6 ds) s1 (car d) a1 (cadr d) a2 (caddr d) lvn (length (nth 4 st))
        xs (sd:fixpos lx a1 250.0 (car lst)) ys (sd:fixpos ly a2 250.0 (cadr lst))
        nx (length xs) ny (length ys))
  (sd:bom+ "VAN-SAN" (* lx ly))
  (sd:bom+ "SUON-SAN" (* ly (length (sd:evenpos lx s1 75.0))))
  (sd:bom+ "XG-SAN" (* (sd:fw "PRIN") lx ny))
  (repeat ny (sd:pair-ledgers (mapcar '(lambda (x) (list x 0.0)) xs) lvn 1e9))
  (repeat nx (sd:pair-ledgers (mapcar '(lambda (y) (list 0.0 y)) ys) lvn 1e9))
  (setq i 0 rb 0) (repeat ny (if (sd:braced-p i ny (sd:gi "BRN")) (setq rb (1+ rb))) (setq i (1+ i)))
  (setq i 0 bb2 0) (repeat (1- nx) (if (sd:braced-p i (1- nx) (sd:gi "BRM")) (setq bb2 (1+ bb2))) (setq i (1+ i)))
  (setq i 0 cb 0) (repeat nx (if (sd:braced-p i nx (sd:gi "BRN")) (setq cb (1+ cb))) (setq i (1+ i)))
  (setq i 0 bc 0) (repeat (1- ny) (if (sd:braced-p i (1- ny) (sd:gi "BRM")) (setq bc (1+ bc))) (setq i (1+ i)))
  (sd:bom+ "CHEO" (* (+ (* rb bb2) (* cb bc)) (max 1 (1- lvn))))
  (sd:bom-legs st (* nx ny)))

;; "300x600:120;220x500:80" -> ((300 600 120) (220 500 80))  (dai theo m)
(defun sd:parse-beams (s / r f sz)
  (foreach tok (sd:split (vl-string-translate ";" "," s) ",")
    (setq f (sd:split (vl-string-trim " " tok) ":"))
    (if (and (= (length f) 2) (setq sz (sd:parse-size (car f))) (> (atof (cadr f)) 0))
      (setq r (cons (list (car sz) (cadr sz) (atof (cadr f))) r))))
  (reverse r))
(defun sd:beams-str (bl)
  (sd:join (mapcar '(lambda (b) (strcat (sd:num (car b)) "x" (sd:num (cadr b)) ":" (sd:rtos (caddr b) 1))) bl) ","))

;; Thong ke 1 tang: fl = (ten H dien-tich ts dam so-tang) -> (bom ghi-chu)
(defun sd:floor-bom (fl / H A ts hs ds side ap span dd b0 note)
  (setq H (nth 1 fl) A (nth 2 fl) ts (nth 3 fl) hs (- H ts) *SD:BOM* nil
        ap (sd:gi "OSAN") side (* 1000.0 (sqrt ap)) span (sd:gi "NHIP"))
  (if (and (> A 0) (setq ds (sd:san-design ts hs)))
    (progn
      (sd:count-panel side side ds)
      (setq b0 *SD:BOM* *SD:BOM* (sd:bom-merge nil b0 (/ A ap))
            note (strcat "s\\U+00E0n " (sd:num (cadr (car ds))) "\\U+00D7" (sd:num (caddr (car ds)))))))
  (foreach bm (nth 4 fl)
    (if (setq dd (sd:dam-design (car bm) (cadr bm) ts hs))
      (progn
        (setq b0 *SD:BOM* *SD:BOM* nil)
        (sd:dam-bom span (sd:fixpos span (nth 1 dd) 300.0 (nth 10 dd)) dd (car bm) (cadr bm) ts)
        (setq *SD:BOM* (sd:bom-merge b0 *SD:BOM* (/ (* 1000.0 (caddr bm)) span))
              note (strcat (if note (strcat note "; ") "") (sd:num (car bm)) "x" (sd:num (cadr bm)) " "
                           (sd:num (nth 0 dd)) "\\U+00D7" (sd:num (nth 1 dd)))))))
  (list *SD:BOM* (cond (note) (""))))

(defun sd:ceil1 (x) (if (> x (fix x)) (1+ (fix x)) (fix x)))
(defun sd:sum-keys (bom pat / s)
  (setq s 0.0)
  (foreach e bom (if (wcmatch (car e) pat) (setq s (+ s (cdr e)))))
  s)

;; Hang muc tong hop theo thu tu: (ten don-vi mau-khoa)
(defun sd:tk-items (boms / keys r)
  (foreach b boms (foreach e b (if (not (member (car e) keys)) (setq keys (cons (car e) keys)))))
  (setq r (list (list "V\\U+00E1n ph\\U+1EE7 phim" "m\\U+00B2" "VAN-*") (list "T\\U+1EA5m v\\U+00E1n quy \\U+0111\\U+1ED5i (+10%)" "t\\U+1EA5m" "TAMQD")
                (list "S\\U+01B0\\U+1EDDn" "m" "SUON-*") (list "X\\U+00E0 g\\U+1ED3" "m" "XG-*") (list "Ch\\U+00E2n gi\\U+00E1o" "ch\\U+00E2n" "CHAN|*")))
  (foreach k (vl-sort (vl-remove-if-not '(lambda (k) (wcmatch k "THAN|*")) keys) '<)
    (setq r (append r (list (list (strcat "  Th\\U+00E2n " (substr k 6)) "c\\U+00E2y" k)))))
  (if (/= (sd:gi "TYPE") "Chong")
    (progn
      (setq r (append r (list (list "K\\U+00EDch \\U+0111\\U+1EA7u U" "b\\U+1ED9" "KICHU") (list "K\\U+00EDch ch\\U+00E2n" "b\\U+1ED9" "KICHCHAN"))))
      (foreach k (sd:sort (vl-remove-if-not '(lambda (k) (wcmatch k "GIANG|*")) keys)
                          '(lambda (a b) (< (atof (substr a 7)) (atof (substr b 7)))))
        (setq r (append r (list (list (strcat "Gi\\U+1EB1ng ngang L=" (substr k 7)) "thanh" k)))))
      (setq r (append r (list (list "Gi\\U+1EB1ng ch\\U+00E9o" "thanh" "CHEO"))))))
  r)

(defun sd:tk-val (bom it / v)
  (cond ((= (caddr it) "TAMQD")
         (sd:ceil1 (* 1.1 (/ (sd:sum-keys bom "VAN-*") (* (sd:fw "SHW") (sd:fw "SHH"))))))
        ((= (cadr it) "m\\U+00B2") (/ (sd:sum-keys bom (caddr it)) 1e6))
        ((= (cadr it) "m") (/ (sd:sum-keys bom (caddr it)) 1000.0))
        (t (sd:ceil1 (- (sd:sum-keys bom (caddr it)) 1e-6)))))

(defun sd:tk-fmt (v unit) (if (member unit '("m\\U+00B2" "m")) (sd:rtos v 1) (itoa (fix v))))

;; Nhap so lieu tang bang tay / tu ban ve
(defun sd:tk-input (/ fls n more nm H A ts bm cnt ss i e r)
  (setq n 1 more t)
  (while more
    (if (not (sd:dlg (strcat "So lieu tang (SDGIAOTK) - tang thu " (itoa (1+ (length fls))))
                     (list (list "nm" "Ten tang" 'str (strcat "T" (itoa n)))
                           (list "H" "Chieu cao tang (san den san, mm)" 'real (cond (*SD:TKH*) (3300.0)))
                           (list "A" "Dien tich san can do (m2, da tru dam)" 'real0 0.0)
                           (list "selA" "Lay dien tich tu cac o san tren ban ve" 'tog nil)
                           (list "ts" "Chieu day san (mm)" 'real (cond (*SD:SLT*) (150.0)))
                           (list "dam" "Dam bxh:dai(m);... vd 300x600:120;220x500:80" 'str "")
                           (list "selB" "Chon dam tren ban ve (thay o tren)" 'tog nil)
                           (list "cnt" "So tang giong nhau" 'int 1)
                           (list "more" "Nhap them tang khac sau khi OK" 'tog nil))))
      (setq more nil)
      (progn
        (setq nm (sd:v "nm") H (sd:v "H") A (sd:v "A") ts (sd:v "ts") cnt (sd:v "cnt") more (sd:v "more")
              bm (sd:parse-beams (sd:v "dam")))
        (if (sd:v "selA")
          (progn
            (setq A 0.0)
            (princ "\nChon cac o san (polyline kin): ")
            (if (setq ss (ssget '((0 . "LWPOLYLINE"))))
              (progn (setq i 0)
                     (repeat (sslength ss) (setq e (ssname ss i) i (1+ i))
                       (if (vlax-curve-isClosed e) (setq A (+ A (/ (abs (vla-get-Area (vlax-ename->vla-object e))) 1e6)))))))
            (princ (strcat "\n  Dien tich: " (sd:rtos A 2) " m2"))))
        (if (sd:v "selB")
          (progn
            (princ "\nChon cac dam: ")
            (setq bm nil)
            (if (setq ss (ssget '((0 . "LINE,LWPOLYLINE"))))
              (foreach b (sd:detect-beams ss (cond (*SD:BMB*) (300.0)) (cond (*SD:BMH*) (600.0)))
                (setq e (assoc (list (caddr b) (cadddr b)) bm)
                      bm (if e (subst (list (car e) (+ (cadr e) (/ (distance (car b) (cadr b)) 1000.0))) e bm)
                           (cons (list (list (caddr b) (cadddr b)) (/ (distance (car b) (cadr b)) 1000.0)) bm)))))
            (setq bm (mapcar '(lambda (x) (list (car (car x)) (cadr (car x)) (cadr x))) bm))
            (princ (strcat "\n  Dam: " (sd:beams-str bm)))))
        (setq *SD:TKH* H *SD:SLT* ts
              fls (cons (list nm H A ts bm cnt) fls) n (+ n cnt)))))
  (reverse fls))

;; Doc CSV: Tang;CaoTang(mm);DienTichSan(m2);DaySan(mm);Dam(300x600:120,220x500:80);SoTang
(defun sd:gi-csv (/ fn f ln fl r)
  (if (and (setq fn (getfiled "Chon file so lieu tang (CSV)" (getvar "DWGPREFIX") "csv" 0))
           (setq f (sd:open fn "r")))
    (progn
      (while (setq ln (read-line f))
        (setq fl (mapcar '(lambda (x) (vl-string-trim " \t\"" x)) (sd:split ln ";")))
        (if (and (>= (length fl) 4) (> (atof (nth 1 fl)) 0))
          (setq r (cons (list (nth 0 fl) (atof (nth 1 fl)) (atof (nth 2 fl)) (atof (nth 3 fl))
                              (if (nth 4 fl) (sd:parse-beams (nth 4 fl)))
                              (if (and (nth 5 fl) (> (atoi (nth 5 fl)) 0)) (atoi (nth 5 fl)) 1))
                        r))))
      (setq fn (sd:close f))))
  (reverse r))

(defun c:SDGIAOTK (/ mode sc fls res items cols rows pt tot fn f hl tl v line i)
  (sd:begin)
  (setq sc (sd:sc))
  (if (not (sd:dlg "Thong ke gian giao (SDGIAOTK)"
                   (list (list "mode" "Che do" 'kw "Tang"
                               '(("Tang" . "Nhap tung tang") ("Csv" . "Doc file CSV") ("Dinhmuc" . "Bang dinh muc to hop"))))))
    (exit))
  (setq mode (sd:v "mode"))
  (if (= mode "Dinhmuc")
    (sd:tk-norms sc)
    (progn
      (setq fls (if (= mode "Csv") (sd:gi-csv) (sd:tk-input)))
      (if (null fls)
        (princ "\n[SD] Khong co so lieu tang.")
        (progn
          ;; tinh tung tang
          (setq res (mapcar 'sd:floor-bom fls)
                items (sd:tk-items (mapcar 'car res)))
          ;; hang dau: thong so tang
          (setq rows (list (list "R" (append (list "Chi\\U+1EC1u cao t\\U+1EA7ng" "mm") (mapcar '(lambda (x) (sd:num (nth 1 x))) fls) (list "")) nil)
                           (list "R" (append (list "Di\\U+1EC7n t\\U+00EDch s\\U+00E0n" "m\\U+00B2") (mapcar '(lambda (x) (sd:rtos (nth 2 x) 1)) fls)
                                             (list (sd:rtos (apply '+ (mapcar '(lambda (x) (* (nth 5 x) (nth 2 x))) fls)) 1))) nil)
                           (list "R" (append (list "D\\U+1EA7m" "m") (mapcar '(lambda (x) (sd:rtos (apply '+ (cons 0.0 (mapcar 'caddr (nth 4 x)))) 1)) fls)
                                             (list (sd:rtos (apply '+ (mapcar '(lambda (x) (* (nth 5 x) (apply '+ (cons 0.0 (mapcar 'caddr (nth 4 x)))))) fls)) 1))) nil)))
          (foreach it items
            (setq tot 0.0 i 0
                  line (mapcar '(lambda (r / v) (setq v (sd:tk-val (car r) it) tot (+ tot (* v (nth 5 (nth i fls)))) i (1+ i))
                                  (sd:tk-fmt v (cadr it)))
                               res))
            (setq rows (append rows (list (list "R" (append (list (car it) (cadr it)) line (list (sd:tk-fmt tot (cadr it)))) nil)))))
          (setq cols (append (list (list "H\\U+1EA0NG M\\U+1EE4C" 44) (list "\\U+0110V" 12))
                             (mapcar '(lambda (x) (list (strcat (car x) (if (> (nth 5 x) 1) (strcat " (\\U+00D7" (itoa (nth 5 x)) ")") "")) 24)) fls)
                             (list (list "T\\U+1ED4NG" 26))))
          ;; ghi chu luoi giao
          (setq i 0)
          (foreach r res
            (setq rows (append rows (list (list "W" (strcat (car (nth i fls)) ": " (sd:gi-name) " " (cadr r))))) i (1+ i)))
          (if (setq pt (sd:getpt "\nDiem chen bang thong ke (goc trai tren): " nil))
            (sd:table2 pt (strcat "B\\U+1EA2NG TH\\U+1ED0NG K\\U+00CA GI\\U+00C0N GI\\U+00C1O \\U+0110\\U+1EE0 D\\U+1EA6M S\\U+00C0N (" (sd:gi-name) ")") cols rows -1 sc))
          ;; CSV
          (setq fn (sd:csv-name "_ThongKeGianGiao.csv"))
          (if (setq f (sd:open fn "w"))
            (progn
              (write-line (sd:join (mapcar '(lambda (c) (vl-string-subst "x" "\\U+00D7" (car c))) cols) ";") f)
              (foreach r rows
                (if (= (car r) "R") (write-line (sd:join (mapcar '(lambda (s) (vl-string-subst "m2" "m\\U+00B2" s)) (cadr r)) ";") f)))
              (setq fn (sd:close f))
              (princ (strcat "\n[SD] Da xuat: " fn))))))))
  (sd:finish))

;; Bang dinh muc: chan giao / 100 m2 san theo (chieu cao tang x chieu day san) va / 100 m dam theo (loai dam x chieu cao)
(defun sd:tk-norms (sc / hl tl bl rows cols pt ds dd span cell)
  (if (not (sd:dlg "Bang dinh muc gian giao (SDGIAOTK)"
                   (list (list "hl" "Cac chieu cao tang (mm)" 'str "3000,3300,3600,4200,4500,5100")
                         (list "tl" "Cac chieu day san (mm)" 'str "120,150,180,200,250")
                         (list "bl" "Cac loai dam bxh, cach nhau ;" 'str "220x500;300x600;300x700;400x800"))))
    (exit))
  (setq hl (sd:numlist (sd:v "hl"))
        tl (sd:numlist (sd:v "tl"))
        bl (vl-remove nil (mapcar 'sd:parse-size (sd:split (sd:v "bl") ";")))
        span (sd:gi "NHIP"))
  ;; san
  (setq rows nil)
  (foreach H hl
    (setq rows (cons (list "R" (cons (sd:num H)
                                     (mapcar '(lambda (ts / ds)
                                                (setq *SD:BOM* nil)
                                                (if (setq ds (sd:san-design ts (- H ts)))
                                                  (progn
                                                    (sd:count-panel (* 1000.0 (sqrt (sd:gi "OSAN"))) (* 1000.0 (sqrt (sd:gi "OSAN"))) ds)
                                                    (strcat (itoa (sd:ceil1 (* (/ 100.0 (sd:gi "OSAN")) (sd:sum-keys *SD:BOM* "CHAN|*"))))
                                                            " (" (sd:num (cadr (car ds))) "\\U+00D7" (sd:num (caddr (car ds))) ")"))
                                                  "-"))
                                             tl))
                           nil)
                     rows)))
  (setq cols (cons (list "H T\\U+1EA6NG / S\\U+00C0N" 26) (mapcar '(lambda (ts) (list (strcat "d\\U+00E0y " (sd:num ts)) 30)) tl)))
  (if (setq pt (sd:getpt "\nDiem chen bang dinh muc san: " nil))
    (sd:table2 pt (strcat "\\U+0110\\U+1ECANH M\\U+1EE8C CH\\U+00C2N GI\\U+00C1O / 100 m\\U+00B2 S\\U+00C0N (" (sd:gi-name) ", l\\U+01B0\\U+1EDBi a1\\U+00D7a2)") cols (reverse rows) -1 sc))
  ;; dam
  (setq rows nil)
  (foreach bm bl
    (setq rows (cons (list "R" (cons (strcat (sd:num (car bm)) "\\U+00D7" (sd:num (cadr bm)))
                                     (mapcar '(lambda (H / dd)
                                                (setq *SD:BOM* nil)
                                                (if (setq dd (sd:dam-design (car bm) (cadr bm) (car tl) (- H (car tl))))
                                                  (progn
                                                    (sd:dam-bom span (sd:fixpos span (nth 1 dd) 300.0 (nth 10 dd)) dd (car bm) (cadr bm) (car tl))
                                                    (strcat (itoa (sd:ceil1 (* (/ 100000.0 span) (sd:sum-keys *SD:BOM* "CHAN|*"))))
                                                            " (" (sd:num (nth 0 dd)) "\\U+00D7" (sd:num (nth 1 dd)) ")"))
                                                  "-"))
                                             hl))
                           nil)
                     rows)))
  (setq cols (cons (list "D\\U+1EA6M / H T\\U+1EA6NG" 26) (mapcar '(lambda (H) (list (sd:num H) 30)) hl)))
  (if (setq pt (sd:getpt "\nDiem chen bang dinh muc dam: " nil))
    (sd:table2 pt (strcat "\\U+0110\\U+1ECANH M\\U+1EE8C CH\\U+00C2N GI\\U+00C1O / 100 m D\\U+1EA6M (" (sd:gi-name) ", c\\U+00D7aL)") cols (reverse rows) -1 sc))
  (setq *SD:BOM* nil))

;;; --------------------------------------------------------------------------
;;;  SDSO - Danh so tu dong (dat moi hoac sua text co san)
;;; --------------------------------------------------------------------------
(defun c:SDSO (/ sc mode pre suf n st pt e ed val)
  (sd:begin)
  (setq sc (sd:sc))
  (if (not (sd:dlg "Danh so tu dong (SDSO)"
                   (list (list "mode" "Cach danh so" 'kw "Dat" '(("Dat" . "Dat text moi") ("Sua" . "Gan vao text co san")))
                         (list "pre" "Tien to (vd C, D, BM)" 'str (cond (*SD:SOPRE*) ("")))
                         (list "suf" "Hau to" 'str "")
                         (list "n" "So bat dau" 'int0 (cond (*SD:SON*) (1)))
                         (list "st" "Buoc tang" 'int 1))))
    (exit))
  (setq mode (sd:v "mode") pre (sd:v "pre") suf (sd:v "suf") n (sd:v "n") st (sd:v "st") *SD:SOPRE* pre)
  (if (= mode "Dat")
    (while (setq pt (getpoint (strcat "\nDiem dat [" pre (itoa n) suf "] <Enter ket thuc>: ")))
      (sd:text (sd:w pt) (strcat pre (itoa n) suf) (* 3.0 sc) "MC" "SD-CHU")
      (setq n (+ n st)))
    (while (progn (setvar "ERRNO" 0)
                  (setq e (entsel (strcat "\nChon text de gan [" pre (itoa n) suf "] <Enter ket thuc>: ")))
                  (or e (= (getvar "ERRNO") 7)))
      (if (and e (wcmatch (cdr (assoc 0 (setq ed (entget (car e))))) "TEXT,MTEXT,ATTRIB"))
        (progn
          (setq val (strcat pre (itoa n) suf))
          (entmod (subst (cons 1 val) (assoc 1 ed) ed))
          (entupd (car e))
          (setq n (+ n st))))))
  (setq *SD:SON* n)
  (sd:finish))

;;; --------------------------------------------------------------------------
;;;  SDLEN - Tong chieu dai doi tuong theo layer
;;; --------------------------------------------------------------------------
(defun c:SDLEN (/ ss i e l lay res rec tot pt)
  (sd:begin)
  (if (setq ss (ssget '((0 . "LINE,LWPOLYLINE,POLYLINE,ARC,CIRCLE,SPLINE,ELLIPSE"))))
    (progn
      (setq i 0 tot 0.0)
      (repeat (sslength ss)
        (setq e (ssname ss i) i (1+ i)
              l (sd:len e) tot (+ tot l)
              lay (cdr (assoc 8 (entget e))))
        (if (setq rec (assoc lay res))
          (setq res (subst (list lay (1+ (cadr rec)) (+ (caddr rec) l)) rec res))
          (setq res (cons (list lay 1 l) res))))
      (princ "\n----------------------------------------------")
      (foreach r (sd:sort res '(lambda (a b) (< (car a) (car b))))
        (princ (strcat "\n" (car r) ": " (itoa (cadr r)) " doi tuong, L = "
                       (sd:rtos (caddr r) 0) " mm (" (sd:rtos (/ (caddr r) 1000.0) 3) " m)")))
      (princ (strcat "\nTONG: " (itoa (sslength ss)) " doi tuong, L = "
                     (sd:rtos tot 0) " mm (" (sd:rtos (/ tot 1000.0) 3) " m)"))
      (princ "\n----------------------------------------------")
      (if (setq pt (sd:getpt "\nDiem ghi tong chieu dai len ban ve <Enter bo qua>: " nil))
        (sd:text pt (strcat "L = " (sd:rtos (/ tot 1000.0) 2) " m") (* 2.5 (sd:sc)) "L" "SD-CHU"))))
  (sd:finish))

;;; --------------------------------------------------------------------------
;;;  SDREV - Ky hieu lan sua doi (tam giac) + dam may tuy chon
;;; --------------------------------------------------------------------------
(defun c:SDREV (/ sc yn rv pt a)
  (sd:begin)
  (setq sc (sd:sc))
  (if (not (sd:dlg "Ky hieu sua doi (SDREV)"
                   (list (list "cloud" "Ve dam may sua doi truoc" 'tog nil)
                         (list "rv" "So lan sua" 'str (cond (*SD:REV*) ("1"))))))
    (exit))
  (setq yn (if (sd:v "cloud") "Co" "Khong"))
  (if (= yn "Co")
    (progn
      (setvar "CLAYER" "SD-KYHIEU")
      (command "_.REVCLOUD")
      (while (> (getvar "CMDACTIVE") 0) (command pause))))
  (setq rv (sd:v "rv"))
  (setq *SD:REV* rv)
  (if (setq pt (sd:getpt "\nVi tri ky hieu sua doi: " nil))
    (progn
      (setq a (* 7.0 sc))
      (sd:pline (list (sd:p+ pt (/ a -2) (* a -0.2887)) (sd:p+ pt (/ a 2) (* a -0.2887))
                      (sd:p+ pt 0 (* a 0.5774)))
                t "SD-KYHIEU")
      (sd:text pt rv (* 2.5 sc) "MC" "SD-CHU")))
  (sd:finish))

;;; --------------------------------------------------------------------------
;;;  SDPURGE - Don rac ban ve sau: du lieu kieu duong DGN, RegApps, block / layer / kieu chu...
;;;  khong dung (purge lap toi khi het), doi tuong dai 0, chu rong, danh sach ty le.
;;; --------------------------------------------------------------------------
(defun sd:tblcount (tbl / n r)
  (setq n 0 r (tblnext tbl t))
  (while r (setq n (1+ n) r (tblnext tbl)))
  n)
(defun sd:dictcount (name / d n)
  (setq n 0)
  (if (setq d (dictsearch (namedobjdict) name))
    (foreach g d (if (= (car g) 3) (setq n (1+ n)))))
  n)
;; ((ten so-luong) ...)
(defun sd:purge-stat ()
  (list (list "Block" (sd:tblcount "BLOCK")) (list "Layer" (sd:tblcount "LAYER")) (list "Linetype" (sd:tblcount "LTYPE"))
        (list "Text style" (sd:tblcount "STYLE")) (list "Dim style" (sd:tblcount "DIMSTYLE"))
        (list "RegApp" (sd:tblcount "APPID")) (list "Du lieu DGN" (sd:dictcount "ACAD_DGNLINESTYLECOMP"))
        (list "Ty le (scale list)" (sd:dictcount "ACAD_SCALELIST"))))
;; Xoa doi tuong dai 0 va chu rong; tra ve so doi tuong da xoa
(defun sd:purge-zero (/ ss i e ed n typ s)
  (setq n 0 i 0)
  (if (setq ss (ssget "_X" '((0 . "LINE,LWPOLYLINE,ARC,CIRCLE,TEXT,MTEXT"))))
    (repeat (sslength ss)
      (setq e (ssname ss i) ed (entget e) typ (cdr (assoc 0 ed)) i (1+ i))
      (if (cond ((= typ "LINE") (< (distance (cdr (assoc 10 ed)) (cdr (assoc 11 ed))) 1e-8))
                ((member typ '("ARC" "CIRCLE")) (< (cdr (assoc 40 ed)) 1e-8))
                ((= typ "LWPOLYLINE") (< (sd:len e) 1e-8))
                (t (= (vl-string-trim " \t" (cdr (assoc 1 ed))) "")))
        (if (not (vl-catch-all-error-p (vl-catch-all-apply 'entdel (list e)))) (setq n (1+ n))))))
  n)

(defun c:SDPURGE (/ doc st0 st1 k nz n dgn)
  (sd:begin)
  (if (not (sd:dlg "Don rac ban ve sau (SDPURGE)"
                   (list (list "note" "Purge lap toi khi het: block, layer, kieu duong, kieu chu, dim style, RegApp khong dung" 'note nil)
                         (list "dgn" "Xoa du lieu kieu duong DGN (rac tu file MicroStation)" 'tog t)
                         (list "zero" "Xoa doi tuong dai 0 va chu rong" 'tog t)
                         (list "scale" "Dat lai danh sach ty le (scale list)" 'tog t)
                         (list "audit" "Chay AUDIT sua loi sau khi don" 'tog nil))))
    (exit))
  (setq doc (sd:doc) st0 (sd:purge-stat))
  ;; du lieu DGN: tu dien ACAD_DGNLINESTYLECOMP giu kieu duong DGN khong purge duoc bang PU
  (if (and (sd:v "dgn") (dictsearch (namedobjdict) "ACAD_DGNLINESTYLECOMP"))
    (setq dgn (vl-catch-all-apply 'dictremove (list (namedobjdict) "ACAD_DGNLINESTYLECOMP"))))
  (if (sd:v "zero") (setq nz (sd:purge-zero)))
  (if (sd:v "scale") (vl-catch-all-apply 'command (list "_.-SCALELISTEDIT" "_R" "_Y" "_E")))
  ;; purge lap: muc long nhau (block trong block, layer cua block...) can nhieu vong
  (setq k 0 st1 nil)
  (while (and (< k 8) (not (equal st1 (sd:purge-stat))))
    (setq st1 (sd:purge-stat) k (1+ k))
    (vl-catch-all-apply 'vla-PurgeAll (list doc)))
  (if (sd:v "audit") (vl-catch-all-apply 'command (list "_.AUDIT" "_Y")))
  (setq st1 (sd:purge-stat))
  (princ "\n[SD] Ket qua don rac (truoc -> sau):")
  (foreach a st0
    (setq n (cadr (assoc (car a) st1)))
    (princ (strcat "\n   " (car a) ": " (itoa (cadr a)) " -> " (itoa n)
                   (if (> (cadr a) n) (strcat "  (bot " (itoa (- (cadr a) n)) ")") ""))))
  (if nz (princ (strcat "\n   Doi tuong dai 0 / chu rong da xoa: " (itoa nz))))
  (princ (strcat "\n[SD] Purge " (itoa k) " vong. Luu ban ve (QSAVE / SAVEAS) de giam dung luong file."
                 (if (> (cadr (assoc "RegApp" st1)) 0) " RegApp con lai dang duoc doi tuong su dung." "")))
  (sd:finish))

;;; --------------------------------------------------------------------------
;;;  SDSOSANH - So sanh ban ve hien hanh voi 1 ban DWG khac (ban cu / ban sua doi)
;;;  Doc ban kia qua ObjectDBX (khong mo len man hinh). Moi doi tuong Model co 1 chu ky:
;;;  loai + layer + noi dung (chu, ten block, chieu dai, ban kinh, gia tri dim) + khung bao lam tron.
;;;  Them moi: xanh la; bi xoa: do (chep bong tu ban kia sang); cung chu ky hinh dang khac vi tri: dich chuyen.
;;; --------------------------------------------------------------------------
(defun sd:rnd (x tol) (* tol (fix (+ (/ x tol) (if (minusp x) -0.5 0.5)))))
(defun sd:rs (x tol) (rtos (sd:rnd x tol) 2 (if (< tol 1.0) 3 0)))
(defun sd:prop (o p / r)
  (if (vlax-property-available-p o p)
    (if (not (vl-catch-all-error-p (setq r (vl-catch-all-apply 'vlax-get-property (list o p)))))
      (cond ((numberp r) r) ((= (type r) 'STR) r) ((= (type r) 'variant) (vlax-variant-value r)) (t r)))))
;; Khung bao ((x1 y1) (x2 y2)) hoac nil
(defun sd:obj-bbox (o / mn mx r)
  (setq r (vl-catch-all-apply 'vla-GetBoundingBox (list o 'mn 'mx)))
  (if (and (not (vl-catch-all-error-p r)) mn mx)
    (list (vlax-safearray->list mn) (vlax-safearray->list mx))))
;; Chu ky doi tuong -> (khoa-day-du khoa-hinh-dang tam bbox o) hoac nil
(defun sd:ss-sig (o tol / bb nm ex a b)
  (if (setq bb (sd:obj-bbox o))
    (progn
      (setq nm (vla-get-ObjectName o) ex "")
      (foreach p '(TextString EffectiveName Name Length Radius Measurement TextOverride Area)
        (if (and (setq a (sd:prop o p)) (or (numberp a) (= (type a) 'STR)) (not (and (= p 'Name) (/= nm "AcDbBlockReference"))))
          (setq ex (strcat ex "|" (if (numberp a) (sd:rs a tol) a)))))
      ;; block co thuoc tinh: them gia tri thuoc tinh (sua so hieu / cao do trong block cung la thay doi)
      (if (and (= nm "AcDbBlockReference") (= (sd:prop o 'HasAttributes) :vlax-true)
               (not (vl-catch-all-error-p (setq a (vl-catch-all-apply 'vlax-invoke (list o 'GetAttributes))))))
        (foreach t1 a (setq ex (strcat ex "|" (vla-get-TagString t1) "=" (vla-get-TextString t1)))))
      (setq a (car bb) b (cadr bb)
            ex (strcat nm "|" (vla-get-Layer o) ex))
      (list (strcat ex "|" (sd:rs (car a) tol) "," (sd:rs (cadr a) tol) "," (sd:rs (car b) tol) "," (sd:rs (cadr b) tol))
            (strcat ex "|" (sd:rs (- (car b) (car a)) tol) "," (sd:rs (- (cadr b) (cadr a)) tol))
            (list (/ (+ (car a) (car b)) 2.0) (/ (+ (cadr a) (cadr b)) 2.0))
            bb o))))
;; Danh sach chu ky cua 1 khong gian (Model) - bo qua layer ket qua so sanh
(defun sd:ss-sigs (space tol / r g)
  (vlax-for o space
    (if (and (not (wcmatch (strcase (vla-get-Layer o)) "SD-SS-*")) (setq g (sd:ss-sig o tol)))
      (setq r (cons g r))))
  r)
;; Hieu 2 danh sach da sap xep theo khoa (nth i): (chi-trong-a chi-trong-b), dem ca phan tu trung khoa
(defun sd:ss-diff (a b i / ra rb ka kb)
  (setq a (sd:sort a '(lambda (x y) (< (nth i x) (nth i y)))) b (sd:sort b '(lambda (x y) (< (nth i x) (nth i y)))))
  (while (and a b)
    (setq ka (nth i (car a)) kb (nth i (car b)))
    (cond ((= ka kb) (setq a (cdr a) b (cdr b)))
          ((< ka kb) (setq ra (cons (car a) ra) a (cdr a)))
          (t (setq rb (cons (car b) rb) b (cdr b)))))
  (list (append (reverse ra) a) (append (reverse rb) b)))
;; Ghep cap dich chuyen: cung khoa hinh dang (nth 1) -> ((moi . cu) ...) + phan con lai
(defun sd:ss-moves (add del / pairs ra rd ka kd)
  (setq add (sd:sort add '(lambda (x y) (< (cadr x) (cadr y)))) del (sd:sort del '(lambda (x y) (< (cadr x) (cadr y)))))
  (while (and add del)
    (setq ka (cadr (car add)) kd (cadr (car del)))
    (cond ((= ka kd) (setq pairs (cons (cons (car add) (car del)) pairs) add (cdr add) del (cdr del)))
          ((< ka kd) (setq ra (cons (car add) ra) add (cdr add)))
          (t (setq rd (cons (car del) rd) del (cdr del)))))
  (list pairs (append (reverse ra) add) (append (reverse rd) del)))
;; Khung danh dau quanh bbox, le m
(defun sd:ss-box (bb m lay / a b)
  (setq a (car bb) b (cadr bb))
  (sd:plinew (list (list (- (car a) m) (- (cadr a) m)) (list (+ (car b) m) (- (cadr a) m))
                   (list (+ (car b) m) (+ (cadr b) m)) (list (- (car a) m) (+ (cadr b) m)))
             t (* 0.15 m) lay))
;; Mo DWG kia: dang mo trong AutoCAD -> dung luon; nguoc lai ObjectDBX. -> (doc . dbx-tu-mo) hoac chuoi loi
(defun sd:ss-open (fn / d r dbx)
  (vlax-for x (vla-get-Documents (vlax-get-acad-object))
    (if (= (strcase (vla-get-FullName x)) (strcase fn)) (setq d x)))
  (cond
    (d (cons d nil))
    ((vl-catch-all-error-p
       (setq dbx (vl-catch-all-apply 'vla-GetInterfaceObject
                                     (list (vlax-get-acad-object) (strcat "ObjectDBX.AxDbDocument." (substr (getvar "ACADVER") 1 2))))))
     (strcat "khong tao duoc ObjectDBX: " (vl-catch-all-error-message dbx)))
    ((vl-catch-all-error-p (setq r (vl-catch-all-apply 'vla-Open (list dbx fn))))
     (vlax-release-object dbx)
     (strcat "khong mo duoc file: " (vl-catch-all-error-message r)))
    (t (cons dbx t))))

(defun c:SDSOSANH (/ doc ms fn tol op other cur old d add del mv m n1 n2 n3 objs r sc)
  (sd:begin)
  (setq sc (sd:sc))
  (if (not (sd:dlg "So sanh 2 ban ve DWG (SDSOSANH)"
                   (list (list "note" "So ban hien hanh (ban moi) voi 1 file DWG khac (ban cu); chi so Model" 'note nil)
                         (list "op" "Thao tac" 'kw "Sosanh" '(("Sosanh" . "So sanh voi file DWG khac") ("Xoa" . "Xoa ket qua so sanh truoc")))
                         (list "tol" "Dung sai toa do (don vi ve)" 'real 1.0 nil '("op" "Sosanh"))
                         (list "bong" "Chep bong doi tuong bi xoa (mau do) tu ban kia" 'tog t '("op" "Sosanh")))))
    (exit))
  (setq doc (sd:doc) ms (vla-get-ModelSpace doc) tol (max 1e-6 (cond ((sd:v "tol")) (1.0))))
  ;; xoa ket qua cu (layer SD-SS-*)
  (if (setq r (ssget "_X" '((8 . "SD-SS-*"))))
    (progn (setq n1 0) (repeat (sslength r) (entdel (ssname r n1)) (setq n1 (1+ n1)))))
  (cond
    ((= (sd:v "op") "Xoa") (princ "\n[SD] Da xoa ket qua so sanh truoc."))
    ((not (setq fn (getfiled "Chon ban ve de so sanh (ban cu / ban truoc sua doi)" (getvar "DWGPREFIX") "dwg" 0))))
    ((= (type (setq op (sd:ss-open fn))) 'STR) (princ (strcat "\n[SD] " op)))
    (t
     (princ "\n[SD] Dang doc 2 ban ve...")
     (setq other (car op)
           cur (sd:ss-sigs ms tol)
           old (sd:ss-sigs (vla-get-ModelSpace other) tol)
           d (sd:ss-diff cur old 0)
           mv (sd:ss-moves (car d) (cadr d))
           add (cadr mv) del (caddr mv) mv (car mv)
           m (* 1.5 sc))
     (sd:make-layer "SD-SS-THEM" 3 "Continuous" 35)
     (sd:make-layer "SD-SS-XOA" 1 "Continuous" 35)
     (sd:make-layer "SD-SS-DICH" 5 "Continuous" 35)
     (foreach g add (sd:ss-box (nth 3 g) m "SD-SS-THEM"))
     (foreach g del (sd:ss-box (nth 3 g) m "SD-SS-XOA"))
     ;; bong doi tuong bi xoa: chep tu ban kia, dua ve layer do
     (if (and del (sd:v "bong"))
       (progn
         (setq objs (vl-catch-all-apply 'vla-CopyObjects
                                        (list other (vlax-make-variant (vlax-safearray-fill (vlax-make-safearray vlax-vbObject (cons 0 (1- (length del))))
                                                                                            (mapcar 'last del)))
                                              ms)))
         (if (vl-catch-all-error-p objs)
           (princ (strcat "\n[SD] Khong chep duoc bong doi tuong bi xoa (" (vl-catch-all-error-message objs) "), chi ve khung do."))
           (foreach o (vlax-safearray->list (vlax-variant-value objs))
             (vl-catch-all-apply 'vla-put-Layer (list o "SD-SS-XOA"))
             (vl-catch-all-apply 'vla-put-Color (list o 256))))))
     (foreach p mv
       (sd:ss-box (nth 3 (car p)) m "SD-SS-DICH")
       (sd:line (nth 2 (cdr p)) (nth 2 (car p)) "SD-SS-DICH")
       (sd:solid3 (nth 2 (car p))
                  (polar (nth 2 (car p)) (+ (angle (nth 2 (car p)) (nth 2 (cdr p))) 0.25) (* 2 sc))
                  (polar (nth 2 (car p)) (- (angle (nth 2 (car p)) (nth 2 (cdr p))) 0.25) (* 2 sc)) "SD-SS-DICH"))
     (if (cdr op) (vlax-release-object other))
     (setq n1 (length add) n2 (length del) n3 (length mv))
     (princ (strcat "\n[SD] So sanh voi " fn ": ban nay " (itoa (length cur)) " doi tuong, ban kia " (itoa (length old)) "."
                    "\n   Them moi (xanh la, SD-SS-THEM): " (itoa n1)
                    "\n   Bi xoa (do, SD-SS-XOA): " (itoa n2)
                    "\n   Dich chuyen (xanh duong, SD-SS-DICH, mui ten tu vi tri cu): " (itoa n3)
                    (if (= (+ n1 n2 n3) 0) "\n   Hai ban ve giong nhau (trong dung sai)." "")
                    "\n[SD] Tat / bat tung loai bang layer; chay lai SDSOSANH -> Xoa de go ket qua."))))
  (sd:finish))

;;; --------------------------------------------------------------------------
;;;  SDNOITHEP - Toi uu cat noi thep trong vung cho phep noi
;;;  Vung noi: dam / san lop tren -> 1/3 giua nhip; lop duoi -> gan goi (goi + Ln/4 moi ben);
;;;  cot -> nua giua chieu cao thong thuy (hoac nua duoi, ngay tren san); hoac nhap tay.
;;;  Quy hoach dong tren luoi 50 mm: moi doan <= cay thuong pham, moi doan noi chong nam tron trong vung,
;;;  it moi noi nhat roi it hao hut cat nhat. Noi so le 2 nhom A / B (<= 50% so thanh noi cung tiet dien):
;;;  tam moi noi 2 nhom cach nhau >= 1,3.l_noi (TCVN 5574:2018). Tuy chon coupler (noi co khi, l_noi = 0).
;;; --------------------------------------------------------------------------
;; Hao hut / 1 doan khi cat nhieu doan giong nhau tu cay dai ls (+ phat doan ngan kho thi cong)
(defun sd:np-waste (len ls / q)
  (setq q (max 1 (fix (/ ls len))))
  (+ (/ (- ls (* q len)) q) (if (< len 1500.0) 2000.0 0.0)))

;; Doan [b-lap, b] nam tron trong 1 vung (zones = ((a b) ...))
(defun sd:np-inzone (b lap zones)
  (vl-some '(lambda (z) (and (>= (- b lap -1e-6) (car z)) (<= b (+ (cadr z) 1e-6)))) zones))

;; Toi uu vi tri noi cho 1 nhom thanh dai Lb. ban = tam moi noi cua nhom kia (tranh trong khoang sole).
;; Tra ve danh sach diem cuoi doan noi (b), hoac 'FAIL
(defun sd:np-solve (Lb ls lap zones step ban sole / ends k b st best c a prev res found s)
  ;; diem cuoi doan noi hop le tren luoi
  (setq k 1)
  (while (< (setq b (* k step)) Lb)
    (if (and (> (- b lap) 0.0) (sd:np-inzone b lap zones)
             (not (vl-some '(lambda (x) (< (abs (- (- b (/ lap 2.0)) x)) (- sole 1e-6))) ban)))
      (setq ends (cons b ends)))
    (setq k (1+ k)))
  (setq ends (reverse ends))
  ;; trang thai: (b chi-phi truoc); trang thai dau: b = lap (doan dau bat dau tai 0)
  (setq st (list (list lap 0.0 nil)))
  (foreach e ends
    (setq best nil)
    (foreach s st
      (setq a (- (car s) lap))
      (if (and (> e (car s)) (<= (- e a) (+ ls 1e-6)))
        (progn (setq c (+ (cadr s) 1e6 (sd:np-waste (- e a) ls)))
               (if (or (null best) (< c (car best))) (setq best (list c s))))))
    (if best (setq st (cons (list e (car best) (cadr best)) st))))
  ;; ket thuc tai Lb
  (setq best nil)
  (foreach s st
    (setq a (- (car s) lap))
    (if (<= (- Lb a) (+ ls 1e-6))
      (progn (setq c (+ (cadr s) (sd:np-waste (- Lb a) ls)))
             (if (or (null best) (< c (car best))) (setq best (list c s))))))
  (if (null best)
    'FAIL
    (progn
      (setq s (cadr best))
      (while (caddr s) (setq res (cons (car s) res) s (caddr s)))
      res)))

;; ---- Toi uu cat toan cuc: dich tung moi noi trong vung (giu rang buoc vung, cay, so le) de tong so cay cat
;; (Best Fit Decreasing, ca nhom A + B x so cau kien) it nhat; hoa thi giu doan thua lon nhat (de tai su dung)
(defun sd:np-items (A B Lb lap na nb2 k / items)
  (foreach g (list (cons (sd:np-pieces A Lb lap) na) (cons (if (> nb2 0) (sd:np-pieces B Lb lap)) nb2))
    (if (> (cdr g) 0)
      (foreach p (car g)
        (setq items (if (assoc p items) (subst (cons p (+ (cdr (assoc p items)) (* k (cdr g)))) (assoc p items) items)
                      (cons (cons p (* k (cdr g))) items))))))
  (sd:sort items '(lambda (x y) (> (car x) (car y)))))
(defun sd:np-score (A B Lb ls lap na nb2 k / bins)
  (setq bins (sd:bfd (sd:np-items A B Lb lap na nb2 k) ls (sd:cfg "KERF" 0.0)))
  (- (* 1e9 (length bins)) (apply 'max (cons 0.0 (mapcar 'car bins)))))
(defun sd:np-valid (ends Lb ls lap zones / a ok)
  (setq a 0.0 ok t)
  (foreach b ends
    (if (or (<= b (+ a lap)) (> (- b a) (+ ls 1e-6)) (not (sd:np-inzone b lap zones))) (setq ok nil))
    (setq a (- b lap)))
  (and ok (<= (- Lb a) (+ ls 1e-6))))
(defun sd:np-stag (A B lap sole)
  (not (vl-some '(lambda (x) (vl-some '(lambda (y) (< (abs (- x y)) (- sole 1e-6))) B)) A)))
(defun sd:np-improve (A B Lb ls lap zones sole na nb2 k / cand best sc0 pass changed g j try nw)
  (setq cand nil j 1)
  (while (< (* j 100.0) Lb)
    (if (sd:np-inzone (* j 100.0) lap zones) (setq cand (cons (* j 100.0) cand)))
    (setq j (1+ j)))
  (setq best (sd:np-score A B Lb ls lap na nb2 k) pass 0 changed t)
  (while (and changed (< pass 4))
    (setq changed nil pass (1+ pass))
    (foreach g (if (> nb2 0) '(0 1) '(0))
      (setq j 0)
      (repeat (length (if (= g 0) A B))
        (foreach c cand
          (setq nw (sd:replace-nth j c (if (= g 0) A B)))
          (if (and (sd:np-valid nw Lb ls lap zones)
                   (or (= nb2 0) (sd:np-stag (if (= g 0) nw A) (if (= g 0) B nw) 0.0 sole)))
            (progn
              (setq try (if (= g 0) (sd:np-score nw B Lb ls lap na nb2 k) (sd:np-score A nw Lb ls lap na nb2 k)))
              (if (< try (- best 1e-6))
                (progn (setq best try changed t)
                       (if (= g 0) (setq A nw) (setq B nw)))))))
        (setq j (1+ j)))))
  (list A B))

;; Diem cuoi doan noi -> chieu dai cac doan
(defun sd:np-pieces (ends Lb lap / a r)
  (setq a 0.0)
  (foreach b ends (setq r (cons (- b a) r) a (- b lap)))
  (reverse (cons (- Lb a) r)))

;; Vung noi theo loai thanh. Toa do doc thanh: t = 0 tai dau thanh (truc dau / chan tru - e0)
(defun sd:np-zones (loai sp cws hd vung e0 e1 / xs n i fl fr ln z Lb y hn)
  (setq xs (sd:cumul sp) n (length sp) Lb (+ e0 (last xs) e1))
  (cond
    ((= loai "Cot")
     (setq i 0)
     (foreach h sp
       (setq y (+ e0 (nth i xs)) hn (- h hd))
       (setq z (cons (if (= vung "Chan") (list (+ y 50.0) (+ y (/ hn 2.0))) (list (+ y (/ hn 4.0)) (+ y (* 0.75 hn)))) z) i (1+ i))))
    (t
     (setq i 0)
     (foreach x xs
       (setq fl (cons (- (+ e0 x) (/ (cond ((nth i cws)) ((last cws))) 2.0)) fl)
             fr (cons (+ (+ e0 x) (/ (cond ((nth i cws)) ((last cws))) 2.0)) fr) i (1+ i)))
     (setq fl (reverse fl) fr (reverse fr) i 0)
     (repeat n (setq ln (cons (- (nth (1+ i) fl) (nth i fr)) ln) i (1+ i)))
     (setq ln (reverse ln) i 0)
     (if (= loai "Tren")
       (repeat n
         (setq z (cons (list (+ (nth i fr) (/ (nth i ln) 3.0)) (- (nth (1+ i) fl) (/ (nth i ln) 3.0))) z) i (1+ i)))
       (repeat (1+ n)
         (setq z (cons (list (max 0.0 (- (nth i fl) (if (> i 0) (/ (nth (1- i) ln) 4.0) e0)))
                             (min Lb (+ (nth i fr) (if (< i n) (/ (nth i ln) 4.0) e1))))
                       z)
               i (1+ i))))))
  (reverse z))

;; Vung nhap tay "a-b, c-d" (mm tu dau thanh)
(defun sd:np-parse-zones (s / r p)
  (foreach tk (sd:split (vl-string-translate ";" "," s) ",")
    (if (setq p (vl-string-search "-" (vl-string-trim " " tk)))
      (setq tk (vl-string-trim " " tk)
            r (cons (list (atof (substr tk 1 p)) (atof (substr tk (+ p 2)))) r))))
  (vl-remove-if '(lambda (z) (<= (cadr z) (car z))) (reverse r)))

;; So moi noi cua cach chia theo cay (sd:splice) nam ngoai vung cho phep
(defun sd:np-naive (Lb d zones lap / pcs a bad n)
  (setq a 0.0 bad 0 n 0 pcs (sd:splice Lb d))
  (foreach p (if pcs (reverse (cdr (reverse pcs))))
    (setq n (1+ n))
    (if (not (sd:np-inzone (+ a p) lap zones)) (setq bad (1+ bad)))
    (setq a (- (+ a p) lap)))
  (list n bad pcs))

;; Diem ve: doc thanh t, lech ngang off (cot ve dung)
(defun sd:np-pt (o vert tt off) (if vert (sd:p+ o off tt) (sd:p+ o tt off)))

;; ---- Loi tinh: 1 thanh -> (loi Lb lap sole zones solA solB na nb2); loi = nil hoac chuoi ly do
(defun sd:np-calc (loai sp cws hd vung zs e0 e1 d nb k ls cpl lapin tl solein opt / Lb lap sole zones na nb2 solA solB g r)
  (setq lap (cond (cpl 0.0) ((> lapin 0) lapin) ((sd:lap d)))
        sole (cond ((> solein 0) solein) (cpl (max 500.0 (* 35.0 d))) ((* 1.3 lap))))
  (cond
    ((null sp) (list "nhip / chieu cao tang khong hop le"))
    ((< ls (+ (* 2 lap) 1000.0)) (list "cay thuong pham qua ngan so voi l noi"))
    (t
     (setq Lb (+ e0 (apply '+ sp) e1)
           zones (if (= loai "Tuchon") (sd:np-parse-zones zs) (sd:np-zones loai sp cws hd vung e0 e1))
           na (if (and (= tl "50") (> nb 1)) (fix (+ (/ nb 2.0) 0.5)) nb) nb2 (- nb na)
           solA (if (> Lb ls) (sd:np-solve Lb ls lap zones 50.0 nil 0.0) nil))
     (if (and (> Lb ls) (> nb2 0) (listp solA))
       (setq solB (sd:np-solve Lb ls lap zones 50.0 (mapcar '(lambda (b) (- b (/ lap 2.0))) solA) sole)))
     (cond
       ((= solA 'FAIL)
        (list (strcat "khong bo tri duoc: 2 vung noi cach nhau xa hon cay " (sd:num ls) " (hoac vung qua ngan so voi l noi "
                      (sd:num lap) ") - dung coupler / vung tay") Lb lap sole zones))
       (t
        (if (= solB 'FAIL) (setq r "khong du vung de so le -> noi 100%" solB solA))
        (if (and (null solB) (> nb2 0)) (setq solB solA))
        (if (and solA opt)
          (progn
            (setq g (sd:np-improve solA solB Lb ls lap zones (if (equal solA solB) 0.0 sole) na nb2 k))
            (if (< (sd:np-score (car g) (cadr g) Lb ls lap na nb2 k) (sd:np-score solA solB Lb ls lap na nb2 k))
              (setq solA (car g) solB (if (> nb2 0) (cadr g) solB)))))
        (list r Lb lap sole zones solA solB na nb2))))))

;; ---- Ve so do cat noi 1 thanh tai o (ve dung neu cot); tags = dang ky ky hieu thep vao bang thong ke
(defun sd:np-draw (o res name loai sp cws hd e0 d k ls cpl tl sc tags / Lb lap sole zones solA solB na nb2 pcsA pcsB vert xs i tt off
                   g r items bins nbar tot eff nv rows ptab)
  (setq Lb (nth 1 res) lap (nth 2 res) sole (nth 3 res) zones (nth 4 res) solA (nth 5 res) solB (nth 6 res)
        na (nth 7 res) nb2 (nth 8 res) vert (= loai "Cot")
        pcsA (sd:np-pieces solA Lb lap) pcsB (if (> nb2 0) (sd:np-pieces (cond (solB) (solA)) Lb lap)))
  (sd:make-layer "SD-NOI-VUNG" 3 "Continuous" 25)
  (sd:use-dimstyle sc)
  ;; ---- cau kien: duong truc thanh, truc / cao do, goi
  (sd:line (sd:np-pt o vert 0 0) (sd:np-pt o vert Lb 0) "SD-KHUAT")
  (setq xs (sd:cumul sp) i 0)
  (foreach x xs
    (setq tt (+ e0 x))
    (sd:line (sd:np-pt o vert tt (* -12 sc)) (sd:np-pt o vert tt (* 12 sc)) "SD-TRUC")
    (sd:text (sd:np-pt o vert tt (* 14 sc)) (if vert (strcat "T" (itoa (1+ i))) (itoa (1+ i))) (* 2.5 sc) "MC" "SD-CHU")
    (if (and (not vert) cws)
      (sd:rect (sd:np-pt o vert (- tt (/ (cond ((nth i cws)) ((last cws))) 2.0)) (* -1.5 sc)) (cond ((nth i cws)) ((last cws))) (* 3 sc) "SD-BETONG"))
    (if (and vert (> i 0))
      (sd:rect (sd:np-pt o vert (- tt hd) (* -2.5 sc)) (* 5 sc) hd "SD-BETONG"))
    (setq i (1+ i)))
  ;; ---- vung cho phep noi
  (foreach z zones
    (sd:pline (list (sd:np-pt o vert (car z) (* -2 sc)) (sd:np-pt o vert (cadr z) (* -2 sc))
                    (sd:np-pt o vert (cadr z) (* 2 sc)) (sd:np-pt o vert (car z) (* 2 sc))) t "SD-NOI-VUNG")
    (sd:line (sd:np-pt o vert (car z) (* -2 sc)) (sd:np-pt o vert (cadr z) (* 2 sc)) "SD-NOI-VUNG"))
  ;; ---- cac doan thep nhom A (tren / phai) va B (duoi / trai)
  (foreach g (list (list "A" pcsA na 1.0) (list "B" pcsB nb2 -1.0))
    (if (and (cadr g) (> (caddr g) 0))
      (progn
        (setq tt 0.0 i 0)
        (foreach p (cadr g)
          (setq off (* (cadddr g) (+ (* 6 sc) (* (rem i 2) 1.6 sc))))
          (sd:plinew (list (sd:np-pt o vert tt off) (sd:np-pt o vert (+ tt p) off)) nil (* 0.35 sc) "SD-THEP-CHU")
          (sd:text (sd:np-pt o vert (+ tt (/ p 2.0)) (+ off (* (cadddr g) 1.6 sc))) (strcat "L=" (sd:num p)) (* 2.0 sc) "MC" "SD-CHU")
          (if (< i (1- (length (cadr g))))
            (progn
              (sd:line (sd:np-pt o vert (- (+ tt p) lap) (* (cadddr g) 5 sc)) (sd:np-pt o vert (- (+ tt p) lap) (* (cadddr g) 9.6 sc)) "SD-KYHIEU")
              (sd:line (sd:np-pt o vert (+ tt p) (* (cadddr g) 5 sc)) (sd:np-pt o vert (+ tt p) (* (cadddr g) 9.6 sc)) "SD-KYHIEU")))
          (setq tt (- (+ tt p) lap) i (1+ i)))
        (sd:text (sd:np-pt o vert (* -3 sc) (* (cadddr g) 7 sc)) (strcat (car g) ": " (itoa (caddr g)) "%%c" (sd:num d)) (* 2.5 sc) "MR" "SD-CHU")
        (if tags
          (foreach q (sd:group (cadr g))
            (setq tt 0.0 r nil)
            (foreach p (cadr g) (if (and (= p (car q)) (null r)) (setq r tt)) (setq tt (- (+ tt p) lap)))
            (sd:kt-fixed o (if vert (list (* (cadddr g) 6 sc) (+ r (/ (car q) 3.0))) (list (+ r (/ (car q) 3.0)) (* (cadddr g) 6 sc)))
                         (if vert (list (* (cadddr g) 22 sc) (+ r (/ (car q) 3.0))) (list (+ r (/ (car q) 3.0) (* 4 sc)) (* (cadddr g) 16 sc)))
                         (* (caddr g) (cdr q)) d "Thang" (list (car q)) k sc ""))))))
  ;; ---- bang cat thep + so sanh
  (setq items (sd:np-items solA (cond (solB) (solA)) Lb lap na nb2 k)
        bins (sd:bfd items ls (sd:cfg "KERF" 0.0))
        nbar (length bins) tot (apply '+ (mapcar '(lambda (it) (* (car it) (cdr it))) items))
        eff (if (> nbar 0) (/ tot (* nbar ls)) 1.0)
        nv (sd:np-naive Lb d zones lap))
  (setq rows (list (list "R" (list "A" (itoa na) (sd:pcs-str pcsA "x") (itoa (1- (length pcsA)))
                                   (sd:join (mapcar '(lambda (b) (sd:num (- b (/ lap 2.0)))) solA) "; ")) nil)))
  (if (> nb2 0)
    (setq rows (append rows (list (list "R" (list "B" (itoa nb2) (sd:pcs-str pcsB "x") (itoa (1- (length pcsB)))
                                                  (sd:join (mapcar '(lambda (b) (sd:num (- b (/ lap 2.0)))) (cond (solB) (solA))) "; ")) nil)))))
  (setq ptab (sd:np-pt o vert (if vert (+ Lb (* 20 sc)) 0.0) (if vert (* 30 sc) (* -24 sc))))
  (sd:table2 ptab (strcat "S\\U+01A0 \\U+0110\\U+1ED2 C\\U+1EAET N\\U+1ED0I TH\\U+00C9P " name " - %%c" (sd:num d) ", L thanh = " (sd:num Lb) " mm, "
                          (if cpl "COUPLER" (strcat "l n\\U+1ED1i = " (sd:num lap))) ", " tl "% c\\U+00F9ng ti\\U+1EBFt di\\U+1EC7n")
             '(("NH\\U+00D3M" 14) ("S\\U+1ED0 THANH" 16) ("C\\U+00C1C \\U+0110O\\U+1EA0N (mm)" 60) ("S\\U+1ED0 M\\U+1ED0I N\\U+1ED0I" 18) ("T\\U+00C2M M\\U+1ED0I N\\U+1ED0I T\\U+1EEA \\U+0110\\U+1EA6U THANH (mm)" 70))
             rows -1 sc)
  (setq r (- (* -8 sc (+ 1 (length rows))) (* 7 sc)))
  (foreach ln (list (strcat "C\\U+1EAFt t\\U+1EEB c\\U+00E2y " (sd:num ls) ": " (itoa nbar) " c\\U+00E2y, t\\U+1ED5ng d\\U+00E0i \\U+0111o\\U+1EA1n " (sd:rtos (/ tot 1000.0) 1)
                            " m, hi\\U+1EC7u su\\U+1EA5t " (sd:rtos (* 100 eff) 1) "%, th\\U+00E9p " (sd:rtos (/ (* tot 0.00617 d d) 1000.0) 1) " kg"
                            (if cpl (strcat ", " (itoa (* k (+ (* na (1- (length pcsA))) (* nb2 (max 0 (1- (length pcsB))))))) " coupler") ""))
                    (strcat "M\\U+1ED1i n\\U+1ED1i n\\U+1EB1m tr\\U+1ECDn trong v\\U+00F9ng cho ph\\U+00E9p (xanh), nh\\U+00F3m B so le nh\\U+00F3m A >= " (sd:num sole) " mm.")
                    (if (> (car nv) 0)
                      (strcat "So v\\U+1EDBi chia theo c\\U+00E2y (" (sd:pcs-str (caddr nv) "x") "): " (itoa (cadr nv)) "/" (itoa (car nv))
                              " m\\U+1ED1i n\\U+1ED1i n\\U+1EB1m ngo\\U+00E0i v\\U+00F9ng cho ph\\U+00E9p.")
                      "Thanh ng\\U+1EAFn h\\U+01A1n c\\U+00E2y th\\U+01B0\\U+01A1ng ph\\U+1EA9m: kh\\U+00F4ng c\\U+1EA7n n\\U+1ED1i."))
    (sd:text (sd:p+ ptab 0 r) ln (* 2.2 sc) "ML" "SD-CHU")
    (setq r (- r (* 4 sc))))
  (sd:use-dimstyle *SD:SCALE*)
  (list nbar eff))

;; ---- Doc du lieu dam / cot da ve (SD_NOI) -> danh sach viec: (ten nhan loai sp cws hd e0 e1 d nb k)
;; dam: 2 viec (thep tren, thep duoi; moc 15d cong vao doan dau thanh); cot: ghep cac tang cung ten + cung n, d -> 1 chong cot
(defun sd:np-jobs (ss / i x r cots key e g sp hd)
  (setq i 0)
  (if ss
    (repeat (sslength ss)
      (setq x (mapcar 'cdr (cdadr (assoc -3 (entget (ssname ss i) '("SD_NOI"))))) i (1+ i))
      ;; so thanh / so cau kien luon la so nguyen
      (setq x (if (= (car x) "DAM")
                (sd:replace-nth 11 (fix (nth 11 x)) (sd:replace-nth 9 (fix (nth 9 x)) (sd:replace-nth 7 (fix (nth 7 x)) x)))
                (sd:replace-nth 8 (fix (nth 8 x)) (sd:replace-nth 4 (fix (nth 4 x)) x))))
      (cond
        ((= (car x) "DAM")
         ;; ("DAM" ten nhip goi e0 e1 moc ntop dtop nbot dbot k tang)
         (foreach t1 (list (list "Tren" "thep tren" (nth 7 x) (nth 8 x)) (list "Duoi" "thep duoi" (nth 9 x) (nth 10 x)))
           (setq e (if (= (nth 6 x) 1) (sd:hk15 (nth 3 t1)) 0.0))
           (setq r (cons (list (nth 1 x) (cadr t1) (car t1) (sd:parse-spacing (nth 2 x)) (sd:parse-spacing (nth 3 x)) 0.0
                               (+ (nth 4 x) e) (+ (nth 5 x) e) (nth 3 t1) (nth 2 t1) (nth 11 x))
                         r))))
        ((= (car x) "COT")
         ;; ("COT" ten Hf hd n d c noi k tang)
         (setq key (list (strcase (nth 1 x)) (nth 4 x) (nth 5 x) (nth 8 x)))
         (if (setq e (assoc key cots))
           (setq cots (subst (cons key (cons (list (nth 9 x) (nth 2 x) (nth 3 x)) (cdr e))) e cots))
           (setq cots (cons (list key (list (nth 9 x) (nth 2 x) (nth 3 x))) cots)))))))
  (foreach c cots
    (setq g (sd:sort (cdr c) '(lambda (p q) (sd:fl< (car p) (car q))))
          sp (mapcar 'cadr g) hd (caddr (car g)))
    (setq r (cons (list (car (car c)) (strcat "cot " (itoa (length sp)) " tang" (if (/= (car (car g)) "") (strcat " " (car (car g)) "-" (car (last g))) ""))
                        "Cot" sp nil hd 0.0 0.0 (nth 2 (car c)) (nth 1 (car c)) (nth 3 (car c)))
                  r)))
  (reverse r))

;; Dam da ve (SDDAMDUNG, du lieu SD_NOI) trung ten voi thanh nhap tay: "D1" / "D1-TREN" / "D1 tren" -> (ename . ban ghi SD_NOI) hoac nil
(defun sd:np-find-beam (name / ss i x r nm e)
  (setq nm (strcase (vl-string-trim " " name)) i 0)
  (if (setq ss (ssget "_X" '((0 . "TEXT") (-3 ("SD_NOI")))))
    (repeat (sslength ss)
      (setq e (ssname ss i) x (mapcar 'cdr (cdadr (assoc -3 (entget e '("SD_NOI"))))) i (1+ i))
      (if (and (not r) (= (car x) "DAM")
               (or (= nm (strcase (nth 1 x))) (wcmatch nm (strcat (strcase (nth 1 x)) "[- _]*"))))
        (setq r (cons e x)))))
  r)
;; Nhip tu cac truc chon tren ban ve: chon lan luot truc dau -> truc cuoi
(defun sd:np-pick-spans (/ p q r)
  (if (setq p (sd:getpt "\nChon truc dau tien cua dam (giao truc voi dam): " nil))
    (while (setq q (sd:getpt "\nTruc tiep theo <ket thuc>: " p))
      (setq r (cons (float (fix (+ (distance p q) 0.5))) r) p q)))
  (reverse r))

(defun c:SDNOITHEP (/ name loai sp cws hd e0 e1 d nb k ls cpl tl res o sc jobs ss j i nd r rows byd e items bins dd y pt nbar eff)
  (sd:begin)
  (if (not (sd:dlg "Toi uu cat noi thep (SDNOITHEP)"
                   (list (list "src" "Nguon du lieu" 'kw (cond (*SD:NPSRC*) ((ssget "_X" '((0 . "TEXT") (-3 ("SD_NOI")))) "Banve") ("Nhap"))
                               '(("Nhap" . "Nhap tay 1 thanh") ("Banve" . "Doc dam / cot da ve (SDDAMDUNG, SDCOTTHEP)")))
                         (list "pv" "Pham vi doc" 'kw "Tatca" '(("Tatca" . "Tat ca trong ban ve") ("Chon" . "Chon tieu de dam / cot")) '("src" "Banve"))
                         (list "name" "Ten cau kien / thanh" 'str (cond (*SD:NPN*) ("D1-TREN")) nil '("src" "Nhap"))
                         (list "loai" "Loai thanh" 'kw (cond (*SD:NPL*) ("Tren"))
                               '(("Tren" . "Dam / san - lop tren (noi 1/3 giua nhip)") ("Duoi" . "Dam / san - lop duoi (noi gan goi)")
                                 ("Cot" . "Thep cot (noi trong chieu cao tang)") ("Tuchon" . "Vung noi nhap tay")) '("src" "Nhap"))
                         (list "sp" "Nhip truc-truc (dam) / chieu cao tang (cot), mm" 'str (cond (*SD:NPS*) ("7200,3600,7200")) nil '("src" "Nhap"))
                         (list "cw" "Be rong goi tai cac truc (dam), mm" 'str "400" nil '("loai" "Tren" "Duoi"))
                         (list "dotruc" "Lay nhip bang cach chon cac truc tren ban ve (dam ve bang ban cu / CAD thuong)" 'tog nil nil '("loai" "Tren" "Duoi" "Tuchon"))
                         (list "hd" "Chieu cao dam dinh cot (cot), mm" 'real 500.0 nil '("loai" "Cot"))
                         (list "vung" "Vung noi thep cot" 'kw "Giua" '(("Giua" . "Nua giua Hn (khang chan)") ("Chan" . "Nua duoi, ngay tren san")))
                         (list "zs" "Vung noi tay: a-b, c-d (mm tu dau thanh)" 'str "" nil '("loai" "Tuchon"))
                         (list "e0" "Doan thanh truoc truc / cao do dau (neo, thep cho), mm" 'real0 300.0 nil '("src" "Nhap"))
                         (list "e1" "Doan thanh sau truc / cao do cuoi, mm" 'real0 300.0 nil '("src" "Nhap"))
                         (list "d" "Duong kinh (mm)" 'real 20.0 nil '("src" "Nhap"))
                         (list "nb" "So thanh trong 1 cau kien" 'int 4 nil '("src" "Nhap"))
                         (list "k" "So cau kien giong nhau" 'int 1 nil '("src" "Nhap"))
                         (list "ls" "Chieu dai cay thuong pham (mm)" 'real (sd:cfg "STOCK" 11700.0))
                         (list "noi" "Kieu noi" 'kw "Chong" '(("Chong" . "Noi chong (buoc)") ("Coupler" . "Coupler ren (co khi)")))
                         (list "lap" "Chieu dai noi chong (mm, 0 = TCVN theo d)" 'real0 0.0 nil '("noi" "Chong"))
                         (list "tl" "Ty le thanh noi cung tiet dien" 'kw "50" '(("50" . "50% - so le 2 nhom A / B") ("100" . "100% - noi cung vi tri")))
                         (list "sole" "Khoang so le giua tam moi noi (mm, 0 = 1,3.l_noi / 35d coupler)" 'real0 0.0 nil '("tl" "50"))
                         (list "opt" "Toi uu cat toan cuc (dich moi noi trong vung de it cay nhat)" 'tog t)
                         (list "ve" "Ve so do tung thanh (hang loat)" 'tog t '("src" "Banve"))
                         (list "tags" "Dang ky ky hieu thep vao bang thong ke (hang loat: thep da co ky hieu khi ve)" 'tog nil '("src" "Banve"))
                         (list "mk" "So hieu thep bat dau" 'int *SD:MARK*)
                         (list "sc" "Ty le ve 1/" 'int (fix *SD:DETSCALE*)))))
    (exit))
  (setq ls (sd:v "ls") cpl (= (sd:v "noi") "Coupler") tl (sd:v "tl") sc (float (sd:v "sc")) *SD:NPSRC* (sd:v "src"))
  (if (= (sd:v "src") "Nhap")
    ;; ================= 1 thanh nhap tay
    (progn
      (setq name (sd:v "name") loai (sd:v "loai") sp (sd:parse-spacing (sd:v "sp")) cws (sd:parse-spacing (cond ((sd:v "cw")) ("400")))
            d (sd:v "d") nb (max 1 (sd:v "nb")) k (max 1 (sd:v "k")) e0 (sd:v "e0") e1 (sd:v "e1")
            *SD:NPN* name *SD:NPL* loai)
      ;; dam cung ten da ve bang SDDAMDUNG: doi chieu, de nghi dung nhip / goi / dau thanh / thep cua ban ve
      (if (and (member loai '("Tren" "Duoi")) (setq r (sd:np-find-beam name)))
        (progn
          (setq j (car (vl-remove-if-not '(lambda (jb) (= (nth 2 jb) loai)) (sd:np-jobs (ssadd (car r)))))
                r (cdr r))
          (if (and j (or (not (equal (nth 3 j) sp 0.5)) (not (equal (nth 6 j) e0 0.5)) (not (equal (nth 7 j) e1 0.5))))
            (progn
              (princ (strcat "\n[!] Dam " (nth 1 r) " da ve: " (itoa (length (nth 3 j))) " nhip " (sd:join (mapcar 'sd:num (nth 3 j)) ",")
                             ", thanh dai " (sd:num (+ (nth 6 j) (apply '+ (nth 3 j)) (nth 7 j))) " mm, "
                             (itoa (nth 9 j)) "%%c" (sd:num (nth 8 j)) "; dang nhap " (itoa (length sp)) " nhip, dai "
                             (sd:num (+ e0 (apply '+ sp) e1)) " mm."))
              (initget "Co Khong")
              (if (/= (getkword "\nDung so lieu dam da ve (nhip, goi, dau thanh + moc, so thanh, duong kinh)? [Co/Khong] <Co>: ") "Khong")
                (setq sp (nth 3 j) cws (nth 4 j) e0 (nth 6 j) e1 (nth 7 j) d (nth 8 j) nb (nth 9 j) k (nth 10 j)))))))
      ;; dam ve bang ban cu / CAD thuong: chon truc tren ban ve
      (if (and (sd:v "dotruc") (member loai '("Tren" "Duoi" "Tuchon")) (setq r (sd:np-pick-spans)))
        (setq sp r))
      (setq *SD:NPS* (sd:join (mapcar 'sd:num sp) ",")
            res (sd:np-calc loai sp cws (cond ((sd:v "hd")) (500.0)) (sd:v "vung") (sd:v "zs") e0 e1 d nb k ls cpl
                            (cond ((sd:v "lap")) (0.0)) tl (cond ((sd:v "sole")) (0.0)) (sd:v "opt")))
      (princ (strcat "\n[SD] " name ": " (itoa (length sp)) " nhip, thanh dai " (sd:num (+ e0 (apply '+ sp) e1)) " mm."))
      (cond
        ((and (car res) (null (nth 5 res)) (null (nth 1 res))) (princ (strcat "\n[SD] " (car res) ".")))
        ((and (car res) (wcmatch (car res) "khong bo tri*")) (princ (strcat "\n[SD] " name ": " (car res) ".")))
        ((setq o (sd:getpt (strcat "\nDiem chen so do (dau thanh" (if (= loai "Cot") ", ve dung" "") "): ") nil))
         (if (car res) (princ (strcat "\n[SD] " (car res) ".")))
         (sd:kt-begin (sd:v "mk") name)
         (setq r (sd:np-draw (sd:w o) res name loai sp cws (cond ((sd:v "hd")) (500.0)) e0 d k ls cpl tl sc t))
         (princ (strcat "\n[SD] " name ": " (itoa (car r)) " cay " (sd:num ls) ", hieu suat " (sd:rtos (* 100 (cadr r)) 1) "%."))
         (sd:kt-end))))
    ;; ================= hang loat tu dam / cot da ve
    (progn
      (setq ss (if (= (sd:v "pv") "Chon")
                 (progn (princ "\nChon tieu de cac dam / cot (chu MAT DUNG THEP ...): ") (ssget '((0 . "TEXT") (-3 ("SD_NOI")))))
                 (ssget "_X" '((0 . "TEXT") (-3 ("SD_NOI")))))
            jobs (sd:np-jobs ss))
      (cond
        ((null jobs) (princ "\n[SD] Khong thay dam / cot co du lieu cat noi (ve lai bang SDDAMDUNG / SDCOTTHEP ban moi)."))
        ((setq o (sd:getpt (strcat "\nDiem chen bang tong hop (" (itoa (length jobs)) " thanh): ") nil))
         ;; cot xep ngang ben phai: qua bang tong hop va dam dai nhat
         (setq o (sd:w o) j 0
               y (max (* 300 sc) (+ (* 60 sc) (apply 'max (cons 0.0 (mapcar '(lambda (jb) (if (/= (nth 2 jb) "Cot") (+ (nth 6 jb) (apply '+ (nth 3 jb)) (nth 7 jb)) 0.0)) jobs))))))
         (foreach jb jobs
           ;; jb = (ten nhan loai sp cws hd e0 e1 d nb k)
           (setq res (sd:np-calc (nth 2 jb) (nth 3 jb) (nth 4 jb) (nth 5 jb) (sd:v "vung") "" (nth 6 jb) (nth 7 jb) (nth 8 jb) (nth 9 jb)
                                 (nth 10 jb) ls cpl (cond ((sd:v "lap")) (0.0)) tl (cond ((sd:v "sole")) (0.0)) (sd:v "opt")))
           (setq items (cond ((nth 5 res) (sd:np-items (nth 5 res) (cond ((nth 6 res)) ((nth 5 res))) (nth 1 res) (nth 2 res) (nth 7 res) (nth 8 res) (nth 10 jb)))
                             ((and (nth 1 res) (null (car res))) (list (cons (nth 1 res) (* (nth 9 jb) (nth 10 jb)))))))
           ;; gom doan cat theo duong kinh (toi uu cat chung)
           (foreach it items
             (if (setq e (assoc (nth 8 jb) byd))
               (setq byd (subst (cons (car e) (cons it (cdr e))) e byd))
               (setq byd (cons (list (nth 8 jb) it) byd))))
           (setq rows (append rows (list (list "R" (list (nth 0 jb) (nth 1 jb) (strcat (itoa (nth 9 jb)) "%%c" (sd:num (nth 8 jb)) (if (> (nth 10 jb) 1) (strcat " x" (itoa (nth 10 jb))) ""))
                                                         (if (nth 1 res) (sd:num (nth 1 res)) "-")
                                                         (if (nth 5 res) (sd:pcs-str (sd:np-pieces (nth 5 res) (nth 1 res) (nth 2 res)) "x") (if (nth 1 res) (sd:num (nth 1 res)) "-"))
                                                         (if (and (nth 5 res) (> (nth 8 res) 0)) (sd:pcs-str (sd:np-pieces (cond ((nth 6 res)) ((nth 5 res))) (nth 1 res) (nth 2 res)) "x") "")
                                                         (cond ((null (nth 1 res)) (car res)) ((wcmatch (cond ((car res)) ("")) "khong bo tri*") "KHONG BO TRI DUOC")
                                                               ((null (nth 5 res)) "khong can noi") ((car res)) ("OK")))
                                                   nil))))
           ;; so do tung thanh: dam xep doc ben duoi, cot xep ngang ben phai
           (if (and (sd:v "ve") (nth 5 res))
             (progn
               (setq j (1+ j))
               (sd:kt-begin (if (= j 1) (sd:v "mk") *SD:MARK*) (nth 0 jb))
               ;; dam: xep doc duoi bang tong hop; cot (ve dung): xep ngang ben phai bang
               (setq pt (if (= (nth 2 jb) "Cot")
                          (sd:p+ o (+ y (* 230 sc (cond (i) (0)))) (- (nth 1 res)))
                          (sd:p+ o 0 (- (* -8 sc (+ 8 (length jobs))) (* 60 sc) (* 95 sc (cond (nd) (0))))))
                     i (if (= (nth 2 jb) "Cot") (1+ (cond (i) (0))) i)
                     nd (if (= (nth 2 jb) "Cot") nd (1+ (cond (nd) (0)))))
               (sd:np-draw pt res (strcat (nth 0 jb) " - " (nth 1 jb)) (nth 2 jb) (nth 3 jb) (nth 4 jb) (nth 5 jb) (nth 6 jb) (nth 8 jb)
                           (nth 10 jb) ls cpl tl sc (sd:v "tags"))
               (sd:kt-end))))
         ;; bang tong hop + cat chung theo duong kinh
         (foreach b byd
           (setq items (sd:sort (cdr b) '(lambda (p q) (> (car p) (car q))))
                 bins (sd:bfd items ls (sd:cfg "KERF" 0.0)) nbar (length bins)
                 eff (/ (apply '+ (mapcar '(lambda (it) (* (car it) (cdr it))) items)) (* (max 1 nbar) ls)))
           (setq dd (cons (list (car b) nbar eff (apply '+ (mapcar '(lambda (it) (* (car it) (cdr it))) items))) dd)))
         (setq dd (sd:sort dd '(lambda (p q) (< (car p) (car q)))))
         (sd:table2 o (strcat "T\\U+1ED4NG H\\U+1EE2P C\\U+1EAET N\\U+1ED0I TH\\U+00C9P TRONG V\\U+00D9NG CHO PH\\U+00C9P (" (itoa (length jobs)) " thanh, c\\U+00E2y " (sd:num ls) ", "
                              (if cpl "coupler" "n\\U+1ED1i ch\\U+1ED3ng") ", " tl "% c\\U+00F9ng ti\\U+1EBFt di\\U+1EC7n)")
                    '(("C\\U+1EA4U KI\\U+1EC6N" 26) ("THANH" 30) ("S\\U+1ED0 x \\U+00D8" 22) ("L THANH" 20) ("\\U+0110O\\U+1EA0N NH\\U+00D3M A (mm)" 56) ("\\U+0110O\\U+1EA0N NH\\U+00D3M B (mm)" 56) ("GHI CH\\U+00DA" 50))
                    (append rows (mapcar '(lambda (x) (list "R" (list "C\\U+1EAET CHUNG" (strcat "%%c" (sd:num (car x))) (strcat (itoa (cadr x)) " c\\U+00E2y")
                                                                      (strcat (sd:rtos (/ (cadddr x) 1000.0) 1) " m")
                                                                      (strcat "hi\\U+1EC7u su\\U+1EA5t " (sd:rtos (* 100 (caddr x)) 1) "%")
                                                                      (strcat (sd:rtos (/ (* (cadddr x) 0.00617 (car x) (car x)) 1000.0) 1) " kg") "") nil))
                                         dd))
                    -1 sc)
         (princ (strcat "\n[SD] Da toi uu " (itoa (length jobs)) " thanh; cat chung: "
                        (sd:join (mapcar '(lambda (x) (strcat "D" (sd:num (car x)) " " (itoa (cadr x)) " cay (" (sd:rtos (* 100 (caddr x)) 1) "%)")) dd) ", ")
                        (if (sd:v "tags") "" ". Ky hieu thep giu nguyen theo ban ve (khong dang ky trung).")))))))
  (sd:finish))

;;; --------------------------------------------------------------------------
;;;  SDIN - In hang loat: tim khung ten (block / polyline tren layer) trong Model, sap theo hang / cot,
;;;  in tung khung bang API in cua AutoCAD (PlotToDevice / PlotToFile); hoac in tat ca Layout.
;;;  Thiet lap luu trong ban ve (ldata "SD" "INHL") cho lan sau.
;;; --------------------------------------------------------------------------
(defun sd:sa->list (v) (if v (vlax-safearray->list (if (= (type v) 'variant) (vlax-variant-value v) v))))
(defun sd:v2 (p) (vlax-make-variant (vlax-safearray-fill (vlax-make-safearray vlax-vbDouble '(0 . 1)) (list (car p) (cadr p)))))
;; Danh sach -> lua chon hop thoai ("1" . ten) ... (khoa so de dung duoc ca dong lenh)
(defun sd:idx-choices (lst / i)
  (setq i 0)
  (mapcar '(lambda (x) (cons (itoa (setq i (1+ i))) x)) lst))
(defun sd:idx-of (x lst / p) (if (setq p (vl-position x lst)) (itoa (1+ p)) "1"))
(defun sd:idx-get (k lst) (nth (1- (atoi k)) lst))

;; Khung in trong Model: ((ll ur ten ename) ...)  mode "Block" (ten block, ke ca block dong) / "Layer" (polyline kin)
(defun sd:in-frames (mode key ss / i e o bb r nm)
  (setq i 0)
  (if (null ss)
    (setq ss (ssget "_X" (if (= mode "Block")
                           '((0 . "INSERT") (410 . "Model"))
                           (list '(0 . "LWPOLYLINE,POLYLINE") '(410 . "Model") (cons 8 key))))))
  (if ss
    (repeat (sslength ss)
      (setq e (ssname ss i) i (1+ i) o (vlax-ename->vla-object e))
      (cond
        ((= mode "Block")
         (setq nm (cond ((sd:prop o 'EffectiveName)) ((cdr (assoc 2 (entget e))))))
         (if (and (= (cdr (assoc 0 (entget e))) "INSERT") (= (strcase nm) (strcase key)) (setq bb (sd:obj-bbox o)))
           (setq r (cons (list (car bb) (cadr bb) nm e) r))))
        ((and (wcmatch (cdr (assoc 0 (entget e))) "*POLYLINE") (= (strcase (cdr (assoc 8 (entget e)))) (strcase key))
              (vlax-curve-isClosed e) (setq bb (sd:obj-bbox o)))
         (setq r (cons (list (car bb) (cadr bb) key e) r))))))
  r)

;; Sap khung: "Hang" = tren xuong, trai sang phai; "Cot" = trai sang phai, tren xuong
(defun sd:in-order (fr order / cx cy tol key r ref n)
  (if fr
    (progn
      (setq tol (* 0.3 (apply 'min (mapcar '(lambda (f) (min (- (car (cadr f)) (car (car f))) (- (cadr (cadr f)) (cadr (car f))))) fr))))
      ;; gom nhom theo hang (y tam) hoac cot (x tam)
      (setq fr (mapcar '(lambda (f) (list (/ (+ (car (car f)) (car (cadr f))) 2.0) (/ (+ (cadr (car f)) (cadr (cadr f))) 2.0) f)) fr))
      (setq fr (sd:sort fr (if (= order "Cot") '(lambda (a b) (< (car a) (car b))) '(lambda (a b) (> (cadr a) (cadr b))))))
      (setq n 0 ref nil)
      (foreach f fr
        (setq key (if (= order "Cot") (car f) (cadr f)))
        (if (and ref (> (abs (- key ref)) tol)) (setq n (1+ n)))
        (setq ref key r (cons (cons n f) r)))
      (mapcar 'last
              (sd:sort r (if (= order "Cot")
                           '(lambda (a b) (if (= (car a) (car b)) (> (caddr a) (caddr b)) (< (car a) (car b))))
                           '(lambda (a b) (if (= (car a) (car b)) (< (cadr a) (cadr b)) (< (car a) (car b))))))))))

;; Kho giay tu dong: kho co kich thuoc gan nhat voi khung / ty le (mm). media = ((canonical w h) ...)
(defun sd:in-autopaper (f media sc / w h best d)
  (setq w (/ (abs (- (car (cadr f)) (car (car f)))) sc) h (/ (abs (- (cadr (cadr f)) (cadr (car f)))) sc))
  (foreach m media
    (setq d (+ (abs (- (max w h) (max (cadr m) (caddr m)))) (abs (- (min w h) (min (cadr m) (caddr m))))))
    (if (or (null best) (< d (car best))) (setq best (list d m))))
  (cadr best))

;; Danh sach kho giay cua may in dang dat tren layout: ((canonical locale w h) ...)
(defun sd:in-media (lay / r pw ph)
  (foreach c (sd:sa->list (vla-GetCanonicalMediaNames lay))
    (if (not (vl-catch-all-error-p (vl-catch-all-apply 'vla-put-CanonicalMediaName (list lay c))))
      (progn (vla-GetPaperSize lay 'pw 'ph)
             (setq r (cons (list c (vla-GetLocaleMediaName lay c) pw ph) r)))))
  (reverse r))

;; Dat cau hinh in 1 khung + in. Tra ve T / chuoi loi
(defun sd:in-one (doc lay f m cfg fn / pw ph land r)
  (setq r (vl-catch-all-apply
            '(lambda ()
               (vla-put-CanonicalMediaName lay (car m))
               (vla-put-PaperUnits lay acMillimeters)
               (vla-SetWindowToPlot lay (sd:v2 (car f)) (sd:v2 (cadr f)))
               (vla-put-PlotType lay acWindow)
               (if (= (nth 2 cfg) "Fit")
                 (progn (vla-put-UseStandardScale lay :vlax-true) (vla-put-StandardScale lay acScaleToFit))
                 (progn (vla-put-UseStandardScale lay :vlax-false) (vla-SetCustomScale lay 1.0 (float (nth 3 cfg)))))
               (vla-put-CenterPlot lay (if (nth 4 cfg) :vlax-true :vlax-false))
               (vla-GetPaperSize lay 'pw 'ph)
               (setq land (> (- (car (cadr f)) (car (car f))) (- (cadr (cadr f)) (cadr (car f)))))
               (vla-put-PlotRotation lay (if (eq land (> pw ph)) ac0degrees ac90degrees))
               (if (nth 1 cfg)
                 (progn (vla-put-PlotWithPlotStyles lay :vlax-true) (vla-put-StyleSheet lay (nth 1 cfg)))
                 (vla-put-PlotWithPlotStyles lay :vlax-false))
               (if fn (vla-PlotToFile (vla-get-Plot doc) fn) (vla-PlotToDevice (vla-get-Plot doc))))
            nil))
  (cond ((vl-catch-all-error-p r) (vl-catch-all-error-message r))
        ((eq r :vlax-false) "may in tu choi lenh in (kiem tra may in / kho giay / file dang mo)")
        (t)))

;; Vien sang khung dang hoi xac nhan
(defun sd:in-hilite (f c / a b)
  (setq a (car f) b (cadr f))
  (grdraw a (list (car b) (cadr a)) c 1) (grdraw (list (car b) (cadr a)) b c 1)
  (grdraw b (list (car a) (cadr b)) c 1) (grdraw (list (car a) (cadr b)) a c 1))

;; ---- Layer ron in: vach trang rong + loi toi manh chay theo vien (thay ron tren da toi lan da sang); chi tao khi in, in xong xoa ----
(setq *SD:RONINL* "SD-RON-IN,SD-RON-IN-LOI")
(defun sd:ronl-clear (/ ss i n)
  (setq n 0)
  (if (setq ss (ssget "_X" (list (cons 8 *SD:RONINL*))))
    (progn (setq i 0) (repeat (sslength ss) (entdel (ssname ss i)) (setq i (1+ i) n (1+ n)))))
  n)
(defun sd:ronl-copy (e lay / ed new g)
  (foreach g (entget e)
    (if (not (member (car g) '(-1 5 330 102 360 62 370 6)))
      (setq new (cons (if (= (car g) 8) (cons 8 lay) g) new))))
  (entmake (reverse new)))
(defun sd:ronl-build (lw / ss i e n)
  (sd:ronl-clear)
  (sd:make-layer "SD-RON-IN" 255 "CONTINUOUS" (sd:lw-near (fix (+ 0.5 (* 100.0 lw)))))
  (sd:make-layer "SD-RON-IN-LOI" 250 "CONTINUOUS" 9)
  (setq n 0)
  (if (setq ss (ssget "_X" (list '(0 . "LWPOLYLINE") '(-3 ("SD_TILE")) (cons 8 (sd:join *SD:RONLAY* ",")))))
    (progn
      (setq i 0)
      (repeat (sslength ss)
        (setq e (ssname ss i) i (1+ i))
        (sd:ronl-copy e "SD-RON-IN")
        (sd:ronl-copy e "SD-RON-IN-LOI")
        (setq n (1+ n)))))
  (foreach hd (sd:ron-extra)
    (setq e (handent hd))
    (sd:ronl-copy e "SD-RON-IN")
    (sd:ronl-copy e "SD-RON-IN-LOI")
    (setq n (1+ n)))
  (if (setq ss (ssget "_X" (list (cons 8 *SD:RONINL*)))) (command "_.DRAWORDER" ss "" "_F"))
  n)

(defun c:SDIN (/ doc lay old devs ctbs dev ctb mode key order scope ss fr media m paper cfg i n ok fn ext e r bp kw stop)
  (sd:begin)
  (setq doc (sd:doc) old (cond ((vlax-ldata-get "SD" "INHL")) ('())))
  (if (= (getvar "TILEMODE") 0) (setvar "TILEMODE" 1))
  (setq lay (vla-get-ActiveLayout doc))
  (vla-RefreshPlotDeviceInfo lay)
  (setq devs (vl-remove "None" (sd:sa->list (vla-GetPlotDeviceNames lay)))
        ctbs (cons "(khong)" (vl-sort (sd:sa->list (vla-GetPlotStyleTableNames lay)) '<)))
  (if (not (sd:dlg "In hang loat (SDIN) - 1. Cai dat in"
                   (list (list "dev" "Chon may in" 'kw (sd:idx-of (cond ((cdr (assoc "dev" old))) ((vla-get-ConfigName lay))) devs) (sd:idx-choices devs))
                         (list "ctb" "Chon net in" 'kw (sd:idx-of (cond ((cdr (assoc "ctb" old))) ("monochrome.ctb")) ctbs) (sd:idx-choices ctbs))
                         (list "sc" "Scaling" 'kw (cond ((cdr (assoc "sc" old))) ("Fit"))
                               (list '("Fit" . "Vua kho giay (Fit)") (cons "Tyle" (strcat "Theo ty le ban ve 1:" (itoa (fix (sd:sc)))))))
                         (list "center" "Ban in chinh giua" 'tog (if (assoc "center" old) (cdr (assoc "center" old)) t))
                         (list "ronl" "Them layer ron in (vach trang rong + loi toi manh theo vien): thay ron ca tren da toi lan da sang" 'tog (if (assoc "ronl" old) (cdr (assoc "ronl" old)) t))
                         (list "file" "In thanh file (PDF / PLT)" 'tog (cdr (assoc "file" old)))
                         (list "conf" "Xac nhan tung khung truoc khi in" 'tog (cdr (assoc "conf" old)))
                         (list "mode" "Khung in la" 'kw (cond ((cdr (assoc "mode" old))) ("Block"))
                               '(("Block" . "Block (khung ten)") ("Layer" . "Polyline kin tren layer")))
                         (list "key" "Ten block / layer khung (trong = chon khung mau)" 'str (cond ((cdr (assoc "key" old))) ("")))
                         (list "order" "Thu tu in" 'kw (cond ((cdr (assoc "order" old))) ("Hang"))
                               '(("Hang" . "Hang: tren xuong, trai sang phai") ("Cot" . "Cot: trai sang phai, tren xuong")))
                         (list "scope" "Pham vi" 'kw (cond ((cdr (assoc "scope" old))) ("Tatca"))
                               '(("Tatca" . "In toan bo khung trong Model") ("Chon" . "Chon ban ve (khung) de in")
                                 ("Layout" . "In tat ca Layout (theo page setup)"))))))
    (exit))
  (setq dev (sd:idx-get (sd:v "dev") devs) ctb (sd:idx-get (sd:v "ctb") ctbs) mode (sd:v "mode")
        key (vl-string-trim " " (sd:v "key")) order (sd:v "order") scope (sd:v "scope")
        bp (getvar "BACKGROUNDPLOT")
        *SD:VARS* (cons (cons "BACKGROUNDPLOT" bp) *SD:VARS*))   ; sd:finish khoi phuc ca khi huy giua chung
  (if (= ctb "(khong)") (setq ctb nil))
  (setvar "BACKGROUNDPLOT" 0)
  (if (sd:v "ronl")
    (princ (strcat "\n[SD] Layer ron in: " (itoa (sd:ronl-build (sd:cfg "RONIN-LW" 0.25))) " vien (tam thoi, xoa sau khi in).")))
  (cond
    ;; ---- tat ca Layout theo page setup cua tung layout
    ((= scope "Layout")
     (setq n 0 i 0)
     (vlax-for l (vla-get-Layouts doc)
       (if (/= (vla-get-ModelType l) :vlax-true)
         (progn
           (vla-put-ActiveLayout doc l)
           (setq i (1+ i)
                 fn (if (sd:v "file") (sd:csv-name (strcat "_" (sd:ascii-name (vla-get-Name l)) (if (wcmatch (strcase dev) "*PDF*") ".pdf" ".plt")))))
           (if (= (setq r (vl-catch-all-apply '(lambda () (if fn (vla-PlotToFile (vla-get-Plot doc) fn) (vla-PlotToDevice (vla-get-Plot doc)))) nil)) :vlax-true)
             (setq n (1+ n))
             (princ (strcat "\n[SD] Loi in layout " (vla-get-Name l) (if (vl-catch-all-error-p r) (strcat ": " (vl-catch-all-error-message r)) "")))))))
     (princ (strcat "\n[SD] Da in " (itoa n) " / " (itoa i) " layout.")))
    (t
     ;; ---- khung mau neu chua co ten block / layer
     (if (= key "")
       (if (setq e (car (entsel "\nChon 1 khung ten mau (block hoac polyline): ")))
         (setq key (if (= mode "Block")
                     (cond ((sd:prop (vlax-ename->vla-object e) 'EffectiveName)) ((cdr (assoc 2 (entget e)))))
                     (cdr (assoc 8 (entget e)))))))
     (if (= scope "Chon")
       (progn (princ "\nChon cac khung can in: ")
              (setq ss (ssget (if (= mode "Block") '((0 . "INSERT")) (list '(0 . "LWPOLYLINE,POLYLINE") (cons 8 key)))))))
     (setq fr (if (and key (/= key "")) (sd:in-order (sd:in-frames mode key ss) order)))
     (if (null fr)
       (princ (strcat "\n[SD] Khong tim thay khung " (if (= mode "Block") "block " "tren layer ") (cond (key) ("")) " trong Model."))
       (progn
         ;; ---- buoc 2: kho giay cua may in da chon
         (vla-put-ConfigName lay dev)
         (setq media (sd:in-media lay))
         (if (not (sd:dlg (strcat "In hang loat (SDIN) - 2. Kho giay (" (itoa (length fr)) " khung)")
                          (list (list "paper" "Chon kho giay" 'kw
                                      (if (member (cdr (assoc "paper" old)) (mapcar 'car media))
                                        (sd:idx-of (cdr (assoc "paper" old)) (mapcar 'car media))
                                        "0")
                                      (cons '("0" . "Tu dong theo kich thuoc khung") (sd:idx-choices (mapcar 'cadr media)))))))
           (exit))
         (setq paper (sd:v "paper")
               r (if (= paper "0") "0" (car (nth (1- (atoi paper)) media)))
               cfg (list dev ctb (sd:v "sc") (sd:sc) (sd:v "center")))
         (vlax-ldata-put "SD" "INHL" (list (cons "dev" dev) (cons "ctb" (cond (ctb) ("(khong)"))) (cons "sc" (sd:v "sc"))
                                           (cons "center" (sd:v "center")) (cons "ronl" (sd:v "ronl")) (cons "file" (sd:v "file")) (cons "conf" (sd:v "conf"))
                                           (cons "mode" mode) (cons "key" key) (cons "order" order) (cons "scope" scope)
                                           (cons "paper" r)))
         (setq ext (if (wcmatch (strcase dev) "*PDF*") ".pdf" ".plt") i 0 n 0)
         (foreach f fr
           (setq i (1+ i)
                 m (if (= paper "0") (sd:in-autopaper f (mapcar '(lambda (x) (list (car x) (caddr x) (cadddr x))) media) (sd:sc))
                     (nth (1- (atoi paper)) media))
                 ok (not stop))
           (if (and ok (sd:v "conf"))
             (progn
               (sd:in-hilite f 1)
               (initget "Co Khong Huy")
               (setq kw (getkword (strcat "\nIn khung " (itoa i) "/" (itoa (length fr)) " (kho " (if m (car m) "?") ")? [Co/Khong/Huy] <Co>: ")))
               (redraw)
               (cond ((= kw "Huy") (setq stop t ok nil)) ((= kw "Khong") (setq ok nil)))))
           (if (and ok m)
             (progn
               (setq fn (if (sd:v "file") (sd:csv-name (strcat "_" (if (< i 10) "0" "") (itoa i) ext)))
                     r (sd:in-one doc lay f m cfg fn))
               (if (= r t)
                 (setq n (1+ n))
                 (princ (strcat "\n[SD] Loi in khung " (itoa i) ": " r))))))
         (princ (strcat "\n[SD] Da in " (itoa n) " khung" (if (sd:v "file") (strcat " ra file " (sd:csv-name (strcat "_01" ext)) " ...") "") "."))))))
  (if (sd:v "ronl") (sd:ronl-clear))
  (setvar "BACKGROUNDPLOT" bp)
  (sd:finish))

;;; ==========================================================================
;;;  DONG BO BAN VE (y tuong tu bo ECE Worx cho Plant 3D, chuyen sang shop drawing ket cau)
;;;    SDBONGTHEP  (~BUBBLEWorx) : danh lai so hieu thep dong bo, cung quy cach = cung so hieu, kiem tra trung / lech
;;;    SDNHANLK    (~ANNOWorx)   : nhan lien ket doi tuong bang FIELD (chieu dai / dien tich tu cap nhat)
;;;    SDTAOLAYOUT (~SHEETWorx / ISOWorx) : tao Layout hang loat tu khung ten + danh so to vao thuoc tinh
;;;    SDLIENKET   (~LINKWorx)   : kiem tra mat bang <-> khai trien (cau kien chua khai trien / khong co tren MB)
;;; ==========================================================================

;; ---- SDBONGTHEP --------------------------------------------------------------
;; Quy cach thanh thep (khong gom so hieu, so luong): (d hinh-dang (kich-thuoc) L (doan-cat)) lam tron mm
(defun sd:bt-key (xd / r)
  (setq r (sd:xd->rec xd))
  (list (sd:rtos (nth 2 r) 0) (nth 5 r) (mapcar '(lambda (x) (sd:rtos x 0)) (nth 6 r))
        (sd:rtos (nth 3 r) 0) (mapcar '(lambda (x) (sd:rtos x 0)) (nth 7 r))))
(defun sd:bt-kstr (k) (strcat "D" (car k) " " (cadr k) " L=" (nth 3 k)))

;; Ky hieu thep trong ban ve: ((ename xd cau-kien quy-cach) ...)
(defun sd:bt-tags (/ ss i e xd ck r)
  (setq i 0)
  (if (setq ss (ssget "_X" '((0 . "CIRCLE") (-3 ("SD_REBAR")))))
    (repeat (sslength ss)
      (setq e (ssname ss i) i (1+ i) xd (mapcar 'cdr (cdadr (assoc -3 (entget e '("SD_REBAR"))))))
      (if (not (sd:tm-orphan-p xd))
        (setq ck (cdr (cadr (cadr (assoc -3 (entget e '("SD_CK"))))))
              r  (cons (list e xd (cond (ck) ("")) (sd:bt-key xd)) r)))))
  (reverse r))

;; Them gia tri v vao danh sach cua khoa k trong alist (khong trung)
(defun sd:bt-add (k v al / o)
  (if (setq o (assoc k al))
    (if (member v (cdr o)) al (subst (append o (list v)) o al))
    (cons (list k v) al)))

;; Kiem tra: so hieu mang >1 quy cach / quy cach mang >1 so hieu (trong pham vi). -> (thong-bao ky-hieu-loi)
(defun sd:bt-check (tags per / m1 m2 msg bad sc)
  (foreach t1 tags
    (setq sc (if per (caddr t1) ""))
    (setq m1 (sd:bt-add (list sc (car (cadr t1))) (cadddr t1) m1)
          m2 (sd:bt-add (list sc (cadddr t1)) (car (cadr t1)) m2)))
  (foreach x m1
    (if (cddr x)
      (setq msg (cons (strcat "So hieu " (cadr (car x)) (if per (strcat " (CK " (car (car x)) ")") "")
                              " co " (itoa (length (cdr x))) " quy cach: " (sd:join (mapcar 'sd:bt-kstr (cdr x)) " / "))
                      msg)
            bad (append bad (vl-remove-if-not '(lambda (t1) (and (= (car (cadr t1)) (cadr (car x)))
                                                                 (or (not per) (= (caddr t1) (car (car x))))))
                                              tags)))))
  (foreach x m2
    (if (cddr x)
      (setq msg (cons (strcat "Cung quy cach " (sd:bt-kstr (cadr (car x))) (if per (strcat " (CK " (car (car x)) ")") "")
                              " mang " (itoa (length (cdr x))) " so hieu: " (sd:join (cdr x) ", "))
                      msg)
            bad (append bad (vl-remove-if-not '(lambda (t1) (and (equal (cadddr t1) (cadr (car x)))
                                                                 (or (not per) (= (caddr t1) (car (car x))))))
                                              tags)))))
  (list (reverse msg) bad))

;; So sanh nhom (pham vi quy-cach thu-tu-CK): pham vi, thu tu CK, D giam, L giam
(defun sd:bt< (a b / da db)
  (setq da (atof (car (cadr a))) db (atof (car (cadr b))))
  (cond ((/= (car a) (car b)) (sd:fl< (car a) (car b)))
        ((/= (caddr a) (caddr b)) (sd:fl< (caddr a) (caddr b)))
        ((/= da db) (> da db))
        ((/= (atof (nth 3 (cadr a))) (atof (nth 3 (cadr b)))) (> (atof (nth 3 (cadr a))) (atof (nth 3 (cadr b)))))
        (t (< (vl-prin1-to-string (cadr a)) (vl-prin1-to-string (cadr b))))))

;; Ke hoach danh so -> ((nhom . so-hieu-moi) ...); nhom = (pham-vi quy-cach thu-tu-ck)
(defun sd:bt-plan (tags per byck start pre / gs g o sc n cur r)
  (foreach t1 tags
    (setq sc (if per (caddr t1) "") g (list sc (cadddr t1)))
    (if (setq o (assoc g gs))
      (if (and byck (sd:fl< (caddr t1) (cadr o))) (setq gs (subst (list g (caddr t1)) o gs)))
      (setq gs (cons (list g (caddr t1)) gs))))
  (setq gs (mapcar '(lambda (x) (list (car (car x)) (cadr (car x)) (if byck (cadr x) ""))) gs))
  (setq gs (mapcar '(lambda (k) (nth k gs)) (vl-sort-i gs 'sd:bt<)))
  (setq n (1- start))
  (foreach x gs
    (if (and per (/= (car x) cur)) (setq n (1- start) cur (car x)))
    (setq n (1+ n) r (cons (cons (list (car x) (cadr x)) (strcat pre (itoa n))) r)))
  (reverse r))

;; Chu so hieu trong vong tron: TEXT can giua dat dung tam vong tron
(defun sd:bt-pkey (sp p) (strcat sp "|" (rtos (car p) 2 2) "," (rtos (cadr p) 2 2)))
(defun sd:bt-texts (/ ss i ed r)
  (setq i 0)
  (if (setq ss (ssget "_X" '((0 . "TEXT") (72 . 1) (73 . 2))))
    (repeat (sslength ss)
      (setq ed (entget (ssname ss i)) i (1+ i)
            r (cons (cons (sd:bt-pkey (cond ((cdr (assoc 410 ed))) ("Model")) (cdr (assoc 11 ed))) (cdr (assoc -1 ed))) r))))
  r)

(defun sd:bt-apply (tags plan per / tx ed x3 new te n mx)
  (setq tx (sd:bt-texts) n 0 mx 0)
  (foreach t1 tags
    (setq new (cdr (assoc (list (if per (caddr t1) "") (cadddr t1)) plan))
          ed  (entget (car t1) '("SD_REBAR")) x3 (cadr (assoc -3 ed)))
    (if (wcmatch new "*#") (setq mx (max mx (atoi (vl-string-left-trim "ABCDEFGHIJKLMNOPQRSTUVWXYZabcdefghijklmnopqrstuvwxyz-_. " new)))))
    (if (/= new (car (cadr t1)))
      (progn
        (entmod (append (vl-remove (assoc -3 ed) ed)
                        (list (list -3 (cons "SD_REBAR" (cons (cons 1000 new) (cddr x3)))))))
        (if (and (setq te (cdr (assoc (sd:bt-pkey (cond ((cdr (assoc 410 ed))) ("Model")) (cdr (assoc 10 ed))) tx)))
                 (= (cdr (assoc 1 (entget te))) (car (cadr t1))))
          (entmod (subst (cons 1 new) (assoc 1 (entget te)) (entget te))))
        (setq n (1+ n)))))
  (if (> mx 0) (setq *SD:MARK* (1+ mx)))
  n)

(defun c:SDBONGTHEP (/ tags per chk ss plan n ng)
  (sd:begin)
  (if (not (sd:dlg "Danh so hieu thep dong bo (SDBONGTHEP)"
                   (list (list "op" "Thao tac" 'kw "Danhso"
                               '(("Danhso" . "Danh lai so hieu + cap nhat ky hieu, bang") ("Kiemtra" . "Chi kiem tra trung / lech so hieu")))
                         (list "pv" "Pham vi so hieu" 'kw "Toanbo"
                               '(("Toanbo" . "Toan ban ve: cung quy cach = cung so hieu") ("Caukien" . "Theo tung cau kien (moi CK danh tu dau)")))
                         (list "sx" "Thu tu danh so" 'kw "DK"
                               '(("DK" . "Duong kinh lon -> nho, dai -> ngan") ("Caukien" . "Theo cau kien, roi duong kinh")) nil '("pv" "Toanbo"))
                         (list "start" "So bat dau" 'int 1 nil '("op" "Danhso"))
                         (list "pre" "Tien to so hieu (VD D-, de trong = khong)" 'str "" nil '("op" "Danhso")))))
    (exit))
  (sd:tag-sync-all)
  (setq per (= (sd:v "pv") "Caukien") tags (sd:bt-tags))
  (if (null tags)
    (princ "\n[SD] Khong co ky hieu thep nao (SDTHEP / SDTHEPTM / lenh khai trien).")
    (progn
      (setq chk (sd:bt-check tags per))
      (cond
        ((= (sd:v "op") "Kiemtra")
         (foreach m (car chk) (princ (strcat "\n  [!] " m)))
         (princ (strcat "\n[SD] " (itoa (length tags)) " ky hieu thep: "
                        (if (car chk) (strcat (itoa (length (car chk))) " loi trung / lech so hieu (dang chon cac ky hieu loi)."
                                              " Chay lai SDBONGTHEP -> Danhso de danh lai.")
                          "khong co so hieu trung / lech.")))
         (if (cadr chk)
           (progn (setq ss (ssadd))
                  (foreach t1 (cadr chk) (ssadd (car t1) ss))
                  (sssetfirst nil ss))))
        (t
         (setq plan (sd:bt-plan tags per (and (not per) (= (sd:v "sx") "Caukien")) (sd:v "start") (sd:v "pre"))
               n    (sd:bt-apply tags plan per)
               ng   (length plan))
         (princ (strcat "\n[SD] " (itoa (length tags)) " ky hieu -> " (itoa ng) " so hieu"
                        (if per " (theo tung cau kien)" " (cung quy cach = cung so hieu)") "; doi so " (itoa n) " ky hieu."
                        (if (car chk) (strcat " Da sua " (itoa (length (car chk))) " loi trung / lech.") "")
                        (if (vlax-ldata-get "SD" "TKAUTO") " Bang thong ke tu cap nhat se ve lai." " Ve lai bang thong ke (SDTKTHEP) neu can.")))))))
  (sd:finish))

;; ---- SDNHANLK ----------------------------------------------------------------
;; ObjectId dang chuoi cho FIELD (64-bit: GetObjectIdString)
(defun sd:objid-str (o / r)
  (setq r (vl-catch-all-apply 'vla-GetObjectIdString (list (vla-get-Utility (sd:doc)) o :vlax-false)))
  (if (vl-catch-all-error-p r) (itoa (vla-get-ObjectID o)) r))

;; Thuoc tinh dung cho FIELD: kind "Dai" / "Dientich"
(defun sd:nl-prop (o kind)
  (if (= kind "Dai")
    (cond ((vlax-property-available-p o 'Length) "Length")
          ((vlax-property-available-p o 'ArcLength) "ArcLength")
          ((vlax-property-available-p o 'Circumference) "Circumference"))
    (if (and (vlax-property-available-p o 'Area)
             (or (not (vlax-property-available-p o 'Closed)) (eq (vla-get-Closed o) :vlax-true)))
      "Area")))

;; Ma FIELD: %<\AcObjProp Object(%<\_ObjId n>%).Prop \f "dinh-dang">%
(defun sd:nl-field (o prop fmt)
  (strcat "%<\\AcObjProp Object(%<\\_ObjId " (sd:objid-str o) ">%)." prop " \\f \"" fmt "\">%"))
(defun sd:nl-fmt (kind dvm pr)
  (strcat "%lu2%pr" (itoa pr)
          (cond ((not dvm) "") ((= kind "Dai") "%ct8[0.001]") (t "%ct8[1e-006]"))))
(defun sd:nl-tpl (tpl fld / p)
  (if (setq p (vl-string-search "{}" tpl))
    (strcat (substr tpl 1 p) fld (substr tpl (+ p 3)))
    (strcat tpl fld)))

;; Diem dat + goc: giua duong cong (tiep tuyen) / tam khung bao
(defun sd:nl-place (o kind / e p d bb a)
  (setq e (vlax-vla-object->ename o))
  (if (and (= kind "Dai")
           (not (vl-catch-all-error-p (setq p (vl-catch-all-apply
                                                '(lambda ()
                                                   (setq d (/ (vlax-curve-getDistAtParam e (vlax-curve-getEndParam e)) 2.0))
                                                   (list (vlax-curve-getPointAtDist e d)
                                                         (vlax-curve-getFirstDeriv e (vlax-curve-getParamAtDist e d))))
                                                nil))))
           (car p))
    (progn
      (setq a (angle '(0 0 0) (cadr p)))
      (if (and (> a (/ pi 2)) (<= a (* 1.5 pi))) (setq a (- a pi)))
      (list (car p) a))
    (if (setq bb (sd:obj-bbox o))
      (list (mapcar '(lambda (x y) (/ (+ x y) 2.0)) (car bb) (cadr bb)) 0.0))))

(defun sd:nl-make (pt ang str h rot / doc spc mt)
  (setq doc (sd:doc)
        spc (if (and (= (getvar "TILEMODE") 0) (= (getvar "CVPORT") 1)) (vla-get-PaperSpace doc) (vla-get-ModelSpace doc))
        mt  (vla-AddMText spc (vlax-3d-point pt) 0.0 "-"))
  (vla-put-AttachmentPoint mt acAttachmentPointBottomCenter)
  (vla-put-InsertionPoint mt (vlax-3d-point pt))
  (vla-put-Height mt h)
  (vla-put-Layer mt "SD-CHU")
  (vl-catch-all-apply 'vla-put-StyleName (list mt (sd:tstyle)))
  (if rot (vla-put-Rotation mt ang))
  (vla-put-TextString mt str)
  mt)

(defun c:SDNHANLK (/ kind ss i o n sk pl tpl str h dvm pr p)
  (sd:begin)
  (if (not (sd:dlg "Nhan lien ket doi tuong (SDNHANLK)"
                   (list (list "note" "Nhan la FIELD gan voi doi tuong: keo gian / sua -> so tu cap nhat (REGEN, luu, in)" 'note nil)
                         (list "kind" "Noi dung" 'kw "Dai"
                               '(("Dai" . "Chieu dai (line, polyline, cung, tron)") ("Dientich" . "Dien tich (polyline kin, hatch, region)")
                                 ("Ca2" . "Ca chieu dai va dien tich")))
                         (list "dv" "Don vi ban ve" 'kw "mm" '(("mm" . "mm (hien thi m / m2)") ("m" . "m (giu nguyen)")))
                         (list "pr" "So chu so thap phan" 'int0 2)
                         (list "t1" "Mau chieu dai ({} = gia tri)" 'str "L = {} m" nil '("kind" "Dai" "Ca2"))
                         (list "t2" "Mau dien tich ({} = gia tri)" 'str "S = {} m\\U+00B2" nil '("kind" "Dientich" "Ca2"))
                         (list "vt" "Vi tri nhan" 'kw "Tudong" '(("Tudong" . "Tu dong giua doi tuong") ("Chon" . "Chon diem cho tung doi tuong")))
                         (list "rot" "Xoay nhan theo doi tuong (chieu dai)" 'tog t))))
    (exit))
  (setq kind (sd:v "kind") dvm (= (sd:v "dv") "mm") pr (sd:v "pr") h (* 2.5 (sd:sc)) i 0 n 0 sk 0)
  (princ "\nChon doi tuong can gan nhan: ")
  (if (setq ss (ssget '((0 . "LINE,LWPOLYLINE,POLYLINE,ARC,CIRCLE,ELLIPSE,HATCH,REGION"))))
    (progn
      (repeat (sslength ss)
        (setq o (vlax-ename->vla-object (ssname ss i)) i (1+ i) str nil)
        (foreach k (if (= kind "Ca2") '("Dai" "Dientich") (list kind))
          (if (setq p (sd:nl-prop o k))
            (setq tpl (sd:nl-tpl (if (= k "Dai") (sd:v "t1") (sd:v "t2")) (sd:nl-field o p (sd:nl-fmt k dvm pr)))
                  str (if str (strcat str "\\P" tpl) tpl))))
        (cond
          ((null str) (setq sk (1+ sk)))
          ((= (sd:v "vt") "Chon")
           (redraw (vlax-vla-object->ename o) 3)
           (setq p (sd:getpt (strcat "\nVi tri nhan " (itoa i) "/" (itoa (sslength ss)) " <bo qua>: ") nil))
           (redraw (vlax-vla-object->ename o) 4)
           (if p (progn (sd:nl-make p 0.0 str h nil) (setq n (1+ n)))))
          ((setq pl (sd:nl-place o (if (= kind "Dientich") "Dientich" "Dai")))
           (sd:nl-make (car pl) (cadr pl) str h (and (sd:v "rot") (/= kind "Dientich"))) (setq n (1+ n)))))
      (vla-Regen (sd:doc) acActiveViewport)
      (princ (strcat "\n[SD] Da gan " (itoa n) " nhan lien ket"
                     (if (> sk 0) (strcat ", bo qua " (itoa sk) " doi tuong khong co thuoc tinh phu hop (VD polyline ho khi tinh dien tich)") "")
                     ". So cap nhat khi REGEN / luu / in; xoa doi tuong -> nhan hien ####."))))
  (sd:finish))

;; ---- SDTAOLAYOUT ---------------------------------------------------------------
(defun sd:lo-safe (s)
  (foreach c '("<" ">" "/" "\\" "\"" ":" ";" "?" "*" "|" "," "=" "`")
    (while (vl-string-search c s) (setq s (vl-string-subst "-" c s))))
  s)
(defun sd:lo-pad (i w / s) (setq s (itoa i)) (while (< (strlen s) w) (setq s (strcat "0" s))) s)
;; So to theo dinh dang: So "1", So0 "01", SoN "1/12", So0N "01/12"
(defun sd:lo-num (i n fmt / w)
  (setq w (if (wcmatch fmt "So0*") (max 2 (strlen (itoa n))) 1))
  (strcat (sd:lo-pad i w) (if (wcmatch fmt "*N") (strcat "/" (sd:lo-pad n w)) "")))
;; Ghi gia tri vao cac thuoc tinh co tag khop mau (wcmatch) cua block e -> so thuoc tinh da ghi
(defun sd:lo-attr (e tags val / n)
  (setq n 0)
  (if (and e (/= tags "") (= (cdr (assoc 0 (entget e))) "INSERT") (= (cdr (assoc 66 (entget e))) 1))
    (foreach a (sd:sa->list (vla-GetAttributes (vlax-ename->vla-object e)))
      (if (wcmatch (strcase (vla-get-TagString a)) (strcase tags))
        (progn (vla-put-TextString a val) (setq n (1+ n))))))
  n)
;; Gia tri thuoc tinh dau tien khop mau
(defun sd:lo-attr-get (e tags / r)
  (if (and e (/= tags "") (= (cdr (assoc 0 (entget e))) "INSERT") (= (cdr (assoc 66 (entget e))) 1))
    (foreach a (sd:sa->list (vla-GetAttributes (vlax-ename->vla-object e)))
      (if (and (not r) (wcmatch (strcase (vla-get-TagString a)) (strcase tags)) (/= (vla-get-TextString a) ""))
        (setq r (vla-get-TextString a)))))
  r)

;; Tao 1 layout: kho giay tu dong theo khung / ty le, 1 viewport dung bang khung, ty le 1:sc, khoa. T / chuoi loi
(defun sd:lo-make (doc name f dev ctb sc / l blk m w h pw ph vp dl r o)
  (setq r (vl-catch-all-apply
            '(lambda ()
               (setq l (vla-Add (vla-get-Layouts doc) name))
               (vla-put-ConfigName l dev)
               (vla-RefreshPlotDeviceInfo l)
               (setq w (/ (- (car (cadr f)) (car (car f))) sc) h (/ (- (cadr (cadr f)) (cadr (car f))) sc)
                     m (sd:in-autopaper f (mapcar '(lambda (x) (list (car x) (caddr x) (cadddr x))) (sd:in-media l)) sc))
               (if m (vla-put-CanonicalMediaName l (car m)))
               (vla-put-PaperUnits l acMillimeters)
               (vla-GetPaperSize l 'pw 'ph)
               (vla-put-PlotRotation l (if (eq (> w h) (> pw ph)) ac0degrees ac90degrees))
               (vla-put-PlotType l acExtents)
               (vla-put-UseStandardScale l :vlax-true)
               (vla-put-StandardScale l ac1_1)
               (vla-put-CenterPlot l :vlax-true)
               (if ctb (progn (vla-put-PlotWithPlotStyles l :vlax-true) (vla-put-StyleSheet l ctb)))
               (vla-put-ActiveLayout doc l)
               (setq blk (vla-get-Block l))
               (vlax-for o blk (if (= (vla-get-ObjectName o) "AcDbViewport") (setq dl (cons o dl))))
               (foreach o dl (vl-catch-all-apply 'vla-Delete (list o)))
               (setq vp (vla-AddPViewport blk (vlax-3d-point (list (/ w 2.0) (/ h 2.0) 0.0)) w h))
               (vla-put-Layer vp "SD-VP")
               (vl-catch-all-apply 'vla-put-ViewportOn (list vp :vlax-true))
               (vla-put-CustomScale vp (/ 1.0 sc))
               (vla-put-ViewCenter vp (vlax-3d-point (mapcar '(lambda (a b) (/ (+ a b) 2.0)) (car f) (cadr f))))
               (vla-put-DisplayLocked vp :vlax-true)
               (vl-catch-all-apply 'vla-ZoomExtents (list (vlax-get-acad-object))))
            nil))
  (if (vl-catch-all-error-p r) (vl-catch-all-error-message r) t))

(defun c:SDTAOLAYOUT (/ doc old lay devs ctbs dev ctb mode key order lam fr n i e nm r los ok made skip na sc tags fmt)
  (sd:begin)
  (setq doc (sd:doc)
        old (cond ((vlax-ldata-get "SD" "TLO")) ((vlax-ldata-get "SD" "INHL")) ('())))
  (if (= (getvar "TILEMODE") 0) (setvar "TILEMODE" 1))
  (setq lay (vla-get-ActiveLayout doc))
  (vla-RefreshPlotDeviceInfo lay)
  (setq devs (vl-remove "None" (sd:sa->list (vla-GetPlotDeviceNames lay)))
        ctbs (cons "(khong)" (vl-sort (sd:sa->list (vla-GetPlotStyleTableNames lay)) '<)))
  (if (not (sd:dlg "Tao Layout hang loat + danh so to (SDTAOLAYOUT)"
                   (list (list "lam" "Thao tac" 'kw (cond ((cdr (assoc "lam" old))) ("Ca2"))
                               '(("Ca2" . "Tao Layout + danh so to") ("Layout" . "Chi tao Layout") ("Soto" . "Chi danh so to vao khung ten")))
                         (list "mode" "Khung ban ve la" 'kw (cond ((cdr (assoc "mode" old))) ("Block"))
                               '(("Block" . "Block (khung ten)") ("Layer" . "Polyline kin tren layer")))
                         (list "key" "Ten block / layer khung (trong = chon khung mau)" 'str (cond ((cdr (assoc "key" old))) ("")))
                         (list "order" "Thu tu to" 'kw (cond ((cdr (assoc "order" old))) ("Hang"))
                               '(("Hang" . "Hang: tren xuong, trai sang phai") ("Cot" . "Cot: trai sang phai, tren xuong")))
                         (list "dev" "May in cho Layout" 'kw (sd:idx-of (cond ((cdr (assoc "dev" old))) ((car (vl-member-if '(lambda (x) (wcmatch (strcase x) "*PDF*")) devs))) ("")) devs)
                               (sd:idx-choices devs) nil '("lam" "Ca2" "Layout"))
                         (list "ctb" "Net in" 'kw (sd:idx-of (cond ((cdr (assoc "ctb" old))) ("monochrome.ctb")) ctbs) (sd:idx-choices ctbs) nil '("lam" "Ca2" "Layout"))
                         (list "sc" "Ty le khung trong Model 1:" 'int (cond ((numberp (cdr (assoc "sc" old))) (cdr (assoc "sc" old))) ((fix (sd:sc)))) nil '("lam" "Ca2" "Layout"))
                         (list "pre" "Ten Layout = tien to + so to" 'str (cond ((cdr (assoc "pre" old))) ("BV-")) nil '("lam" "Ca2" "Layout"))
                         (list "trung" "Layout trung ten" 'kw (cond ((cdr (assoc "trung" old))) ("Thay")) '(("Thay" . "Xoa layout cu, tao lai") ("Bo" . "Giu layout cu, bo qua")) nil '("lam" "Ca2" "Layout"))
                         (list "tag" "Tag thuoc tinh so to (* ? = mau)" 'str (cond ((cdr (assoc "tag" old))) ("SOTO,SO_TO,SOBV,SHEET*")) nil '("lam" "Ca2" "Soto"))
                         (list "fmt" "Dinh dang so to" 'kw (cond ((cdr (assoc "fmt" old))) ("So0"))
                               '(("So" . "1, 2, 3") ("So0" . "01, 02, 03") ("SoN" . "1/12, 2/12") ("So0N" . "01/12, 02/12")) nil '("lam" "Ca2" "Soto"))
                         (list "tagn" "Tag thuoc tinh tong so to (trong = khong)" 'str (cond ((cdr (assoc "tagn" old))) ("TONGTO,TONG_TO")) nil '("lam" "Ca2" "Soto")))))
    (exit))
  (setq lam (sd:v "lam") mode (sd:v "mode") key (vl-string-trim " " (sd:v "key")) order (sd:v "order")
        dev (sd:idx-get (sd:v "dev") devs) ctb (sd:idx-get (sd:v "ctb") ctbs) sc (float (sd:v "sc"))
        tags (vl-string-trim " " (sd:v "tag")) fmt (sd:v "fmt"))
  (if (= ctb "(khong)") (setq ctb nil))
  (if (= key "")
    (if (setq e (car (entsel "\nChon 1 khung ten mau (block hoac polyline): ")))
      (setq key (if (= mode "Block")
                  (cond ((sd:prop (vlax-ename->vla-object e) 'EffectiveName)) ((cdr (assoc 2 (entget e)))))
                  (cdr (assoc 8 (entget e)))))))
  (setq fr (if (and key (/= key "")) (sd:in-order (sd:in-frames mode key nil) order)) n (length fr))
  (if (null fr)
    (princ (strcat "\n[SD] Khong tim thay khung " (if (= mode "Block") "block " "tren layer ") (cond (key) ("")) " trong Model."))
    (progn
      (vlax-ldata-put "SD" "TLO" (list (cons "lam" lam) (cons "mode" mode) (cons "key" key) (cons "order" order)
                                       (cons "dev" dev) (cons "ctb" (cond (ctb) ("(khong)"))) (cons "sc" (fix sc))
                                       (cons "pre" (sd:v "pre")) (cons "trung" (sd:v "trung"))
                                       (cons "tag" tags) (cons "fmt" fmt) (cons "tagn" (sd:v "tagn"))))
      ;; ---- danh so to vao thuoc tinh khung ten (theo thu tu to)
      (setq i 0 na 0)
      (if (/= lam "Layout")
        (foreach f fr
          (setq i (1+ i)
                na (+ na (sd:lo-attr (nth 3 f) tags (sd:lo-num i n fmt))))
          (sd:lo-attr (nth 3 f) (vl-string-trim " " (sd:v "tagn")) (if (wcmatch fmt "So0*") (sd:lo-pad n 2) (itoa n)))))
      ;; ---- tao layout: moi khung 1 layout, viewport dung khung
      (setq i 0 made 0 skip 0)
      (if (/= lam "Soto")
        (progn
          (if (null dev) (setq dev "DWG To PDF.pc3"))
          (sd:make-layer "SD-VP" 8 "Continuous" 13)
          (setq r (entget (tblobjname "LAYER" "SD-VP")))
          (if (/= (cdr (assoc 290 r)) 0) (entmod (append (vl-remove (assoc 290 r) r) '((290 . 0)))))
          (if (getvar "LAYOUTCREATEVIEWPORT")
            (setq *SD:VARS* (cons (cons "LAYOUTCREATEVIEWPORT" (getvar "LAYOUTCREATEVIEWPORT")) *SD:VARS*)))
          (if (getvar "LAYOUTCREATEVIEWPORT") (setvar "LAYOUTCREATEVIEWPORT" 0))
          (setq los (vla-get-Layouts doc))
          (foreach f fr
            (setq i (1+ i)
                  nm (sd:lo-safe (strcat (sd:v "pre") (sd:lo-pad i (max 2 (strlen (itoa n))))))
                  ok t)
            (if (not (vl-catch-all-error-p (vl-catch-all-apply 'vla-Item (list los nm))))
              (if (= (sd:v "trung") "Thay")
                (if (vl-catch-all-error-p (vl-catch-all-apply 'vla-Delete (list (vla-Item los nm))))
                  (setq ok nil))
                (setq ok nil)))
            (if (not ok)
              (setq skip (1+ skip))
              (if (= (setq r (sd:lo-make doc nm f dev ctb sc)) t)
                (setq made (1+ made))
                (princ (strcat "\n[SD] Loi tao layout " nm ": " r)))))
          (setvar "TILEMODE" 1)))
      (princ (strcat "\n[SD] " (itoa n) " khung"
                     (if (/= lam "Layout") (strcat "; ghi so to vao " (itoa na) " thuoc tinh"
                                                   (if (= na 0) " (khung khong co thuoc tinh khop tag)" "")) "")
                     (if (/= lam "Soto") (strcat "; tao " (itoa made) " layout" (if (> skip 0) (strcat ", bo qua " (itoa skip) " layout trung ten") "")
                                                 " (viewport 1:" (itoa (fix sc)) " khoa, layer SD-VP khong in). In ca bo: SDIN -> In tat ca Layout.") "")))))
  (sd:finish))

;; ---- SDLIENKET -----------------------------------------------------------------
;; Bo ma dinh dang MTEXT -> chu thuong
(defun sd:mt-plain (s / r i c n)
  (setq r "" i 1)
  (while (<= i (strlen s))
    (setq c (substr s i 1))
    (cond
      ((= c "\\")
       (setq n (substr s (1+ i) 1))
       (cond ((member n '("P" "~")) (setq r (strcat r " ") i (+ i 2)))
             ((member n '("\\" "{" "}")) (setq r (strcat r n) i (+ i 2)))
             ((member (strcase n) '("F" "H" "C" "W" "Q" "T" "A" "P" "S"))
              (setq i (1+ i))
              (while (and (<= i (strlen s)) (/= (substr s i 1) ";")) (setq i (1+ i)))
              (setq i (1+ i)))
             (t (setq i (+ i 2)))))
      ((member c '("{" "}")) (setq i (1+ i)))
      (t (setq r (strcat r c) i (1+ i)))))
  r)
;; Ten cau kien = tu dau tien cua chu
(defun sd:lk-name (s / i)
  (setq s (vl-string-trim " \t" s) i 1)
  (while (and (<= i (strlen s)) (not (member (substr s i 1) '(" " "(" "\t" ":" ";" "/" "=")))) (setq i (1+ i)))
  (substr s 1 (1- i)))

(defun sd:lk-mark (p r txt sc)
  (entmake (list '(0 . "CIRCLE") '(8 . "SD-KIEMTRA") (cons 10 p) (cons 40 r)))
  (sd:text (sd:p+ p 0 (+ r sc)) txt (* 2.5 sc) "L" "SD-KIEMTRA"))

(defun c:SDLIENKET (/ old sc ss i e ed s nm p plan det all o rows nok npl ndt bb pt tang r q)
  (sd:begin)
  (setq old (cond ((vlax-ldata-get "SD" "LKT")) ('())) sc (sd:sc))
  (if (not (sd:dlg "Kiem tra mat bang <-> khai trien (SDLIENKET)"
                   (list (list "note" "So ten cau kien ghi tren mat bang voi cau kien da khai trien (du lieu khoi luong SD_KL)" 'note nil)
                         (list "lay" "Layer chu ten cau kien tren MB (trong = chon tren man hinh)" 'str (cond ((cdr (assoc "lay" old))) ("")))
                         (list "pat" "Mau ten cau kien (@ = chu, # = so, * = bat ky)" 'str (cond ((cdr (assoc "pat" old))) ("@*#*")))
                         (list "tang" "Chi so voi cau kien cua tang (trong = tat ca)" 'str (cond ((cdr (assoc "tang" old))) ("")))
                         (list "mark" "Khoanh do cho thieu tren ban ve (layer SD-KIEMTRA)" 'tog t)
                         (list "bang" "Ve bang ket qua" 'tog t))))
    (exit))
  (vlax-ldata-put "SD" "LKT" (list (cons "lay" (sd:v "lay")) (cons "pat" (sd:v "pat")) (cons "tang" (sd:v "tang"))))
  (setq tang (strcase (vl-string-trim " " (sd:v "tang"))))
  (sd:make-layer "SD-KIEMTRA" 1 "Continuous" 35)
  ;; xoa danh dau lan truoc
  (if (setq ss (ssget "_X" '((8 . "SD-KIEMTRA"))))
    (progn (setq i 0) (repeat (sslength ss) (entdel (ssname ss i)) (setq i (1+ i)))))
  ;; ten tren mat bang: ((TEN diem...) ...)
  (setq ss (if (= (vl-string-trim " " (sd:v "lay")) "")
             (progn (princ "\nChon chu ten cau kien tren mat bang: ") (ssget '((0 . "TEXT,MTEXT"))))
             (ssget "_X" (list '(0 . "TEXT,MTEXT") (cons 8 (sd:v "lay"))))))
  (setq i 0)
  (if ss
    (repeat (sslength ss)
      (setq ed (entget (ssname ss i)) i (1+ i)
            s  (if (= (cdr (assoc 0 ed)) "MTEXT") (sd:mt-plain (vla-get-TextString (vlax-ename->vla-object (cdr (assoc -1 ed))))) (cdr (assoc 1 ed)))
            nm (strcase (sd:lk-name s)))
      (if (and (/= nm "") (wcmatch nm (strcase (sd:v "pat"))) (/= (cdr (assoc 8 ed)) "SD-KIEMTRA"))
        (setq plan (sd:bt-add nm (cdr (assoc 10 ed)) plan)))))
  ;; cau kien da khai trien: ((TEN ename...) ...)
  (setq i 0)
  (if (setq ss (ssget "_X" '((-3 ("SD_KL")))))
    (repeat (sslength ss)
      (setq e (ssname ss i) i (1+ i)
            o (mapcar 'cdr (cdadr (assoc -3 (entget e '("SD_KL"))))))
      (if (or (= tang "") (= (strcase (cond ((nth 6 o)) (""))) tang))
        (setq det (sd:bt-add (strcase (car o)) e det)))))
  (foreach x (append plan det) (if (not (member (car x) all)) (setq all (cons (car x) all))))
  (setq all (mapcar '(lambda (k) (nth k all)) (vl-sort-i all 'sd:fl<)) nok 0 npl 0 ndt 0)
  (foreach nm all
    (setq p (cdr (assoc nm plan)) o (cdr (assoc nm det)))
    (cond ((and p o) (setq nok (1+ nok)))
          (p (setq npl (1+ npl))
             (if (sd:v "mark") (foreach q p (sd:lk-mark q (* 6.0 sc) "CHUA KHAI TRIEN" sc))))
          (t (setq ndt (1+ ndt))
             (if (and (sd:v "mark") (setq bb (sd:obj-bbox (vlax-ename->vla-object (car o)))))
               (sd:lk-mark (mapcar '(lambda (a b) (/ (+ a b) 2.0)) (car bb) (cadr bb))
                           (max (* 6.0 sc) (* 0.6 (distance (car bb) (cadr bb)))) "KHONG CO TREN MAT BANG" sc))))
    (setq rows (cons (list "R" (list nm (itoa (length p)) (itoa (length o))
                                     (cond ((and p o) "OK") (p "CH\\U+01AFA KHAI TRI\\U+1EC2N") (t "KH\\U+00D4NG C\\U+00D3 TR\\U+00CAN MB")))
                           nil)
                     rows)))
  (setq rows (reverse rows))
  (princ (strcat "\n[SD] " (itoa (length all)) " cau kien: " (itoa nok) " khop, " (itoa npl) " co tren MB nhung chua khai trien, "
                 (itoa ndt) " da khai trien nhung khong thay tren MB" (if (/= tang "") (strcat " (tang " tang ")") "") "."))
  (foreach r rows (if (/= (nth 3 (cadr r)) "OK") (princ (strcat "\n  [!] " (car (cadr r)) ": " (nth 3 (cadr r))))))
  (if (and rows (sd:v "bang") (setq pt (sd:getpt "\nDiem chen bang ket qua (goc trai tren) <bo qua>: " nil)))
    (sd:table2 pt "KI\\U+1EC2M TRA M\\U+1EB6T B\\U+1EB0NG - KHAI TRI\\U+1EC2N" '(("T\\U+00CAN CK" 22) ("TR\\U+00CAN MB" 18) ("KHAI TRI\\U+1EC2N" 20) ("TR\\U+1EA0NG TH\\U+00C1I" 40)) rows -1 sc))
  (sd:finish))

;;; ==========================================================================
;;;  SDCDE - Phat hanh len CDE (Common Data Environment) theo ISO 19650
;;;    So hieu tai lieu: Du an-Don vi lap-Khu vuc-Tang-Loai-Bo mon-So (VD DA07-RPG-ZZ-02-DR-S-0101)
;;;    Trang thai: S0 (WIP) -> 01_WIP; S1..S4 (chia se) -> 02_SHARED; A1..A3 / CR (phat hanh) -> 03_PUBLISHED;
;;;    ban cu cung so hieu tu dong chuyen sang 04_ARCHIVED. Phien ban: P01.. (S0-S4), C01.. (A / CR).
;;;    Moi to (Layout hoac khung ten trong Model) -> 1 PDF ten <so hieu>_<phien ban>_<trang thai>.pdf;
;;;    ghi so hieu / phien ban / trang thai vao thuoc tinh khung ten; so dang ky CDE_Register.csv + phieu chuyen giao.
;;;  Thu muc CDE: thu muc dong bo cua ACC Docs (Desktop Connector), SharePoint / OneDrive, Trimble Connect... hoac o mang.
;;; ==========================================================================
(setq *SD:CDEST*
  '(("S0" . "S0 - Dang thuc hien (WIP)") ("S1" . "S1 - Phoi hop") ("S2" . "S2 - Tham khao thong tin")
    ("S3" . "S3 - Xem xet va gop y") ("S4" . "S4 - Trinh phe duyet") ("A1" . "A1 - Phat hanh thi cong")
    ("A2" . "A2 - Phat hanh dau thau") ("A3" . "A3 - Phat hanh thiet ke") ("CR" . "CR - Hoan cong")))

;; Thu muc trang thai theo ma
(defun sd:cde-state (st)
  (cond ((= st "S0") "01_WIP") ((wcmatch st "S#") "02_SHARED") (t "03_PUBLISHED")))

;; Kiem tra 1 truong ma: chu / so, do dai lo..hi -> nil (OK) hoac chuoi loi
(defun sd:cde-fchk (lab v lo hi dig)
  (cond ((or (< (strlen v) lo) (> (strlen v) hi)) (strcat lab " '" v "' phai dai " (itoa lo) "-" (itoa hi) " ky tu"))
        ((not (wcmatch v (if dig (sd:cde-rep "#" (strlen v)) (sd:cde-rep "[A-Z0-9]" (strlen v)))))
         (strcat lab " '" v "' chi gom " (if dig "chu so" "chu in hoa / so")))))
(defun sd:cde-rep (s n / r) (setq r "") (repeat n (setq r (strcat r s))) r)

;; Danh sach loi cua cau hinh: cfg = ((khoa . gia tri) ...)
(defun sd:cde-g (cfg k) (strcase (vl-string-trim " " (cond ((cdr (assoc k cfg))) ("")))))
(defun sd:cde-check (cfg / r st rev)
  (setq st (sd:cde-g cfg "st") rev (sd:cde-g cfg "rev"))
  (foreach x (list (sd:cde-fchk "Du an" (sd:cde-g cfg "proj") 2 6 nil) (sd:cde-fchk "Don vi lap" (sd:cde-g cfg "orig") 3 6 nil)
                   (sd:cde-fchk "Khu vuc" (sd:cde-g cfg "vol") 1 3 nil) (sd:cde-fchk "Tang" (sd:cde-g cfg "lev") 2 3 nil)
                   (sd:cde-fchk "Loai" (sd:cde-g cfg "typ") 2 2 nil) (sd:cde-fchk "Bo mon" (sd:cde-g cfg "role") 1 2 nil)
                   (sd:cde-fchk "So bat dau" (sd:cde-g cfg "num") 4 6 t)
                   (if (not (wcmatch rev "[PC]##*")) (strcat "Phien ban '" rev "' phai dang P01 / C01")
                     (if (/= (substr rev 1 1) (if (wcmatch st "S#") "P" "C"))
                       (strcat "Phien ban " rev " khong hop trang thai " st " (S0-S4 dung P.., A / CR dung C..)"))))
    (if x (setq r (cons x r))))
  (reverse r))

;; So hieu tai lieu to thu i (tu 0)
(defun sd:cde-docno (cfg i / n w s)
  (setq n (sd:cde-g cfg "num") w (strlen n) s (itoa (+ (atoi n) i)))
  (while (< (strlen s) w) (setq s (strcat "0" s)))
  (sd:join (list (sd:cde-g cfg "proj") (sd:cde-g cfg "orig") (sd:cde-g cfg "vol") (sd:cde-g cfg "lev") (sd:cde-g cfg "typ") (sd:cde-g cfg "role") s) "-"))

(defun sd:cde-mkdir (d)
  (or (vl-file-directory-p d) (vl-mkdir d) (sd:fso-do 'CreateFolder (list d)))
  d)

;; Chuyen cac ban khac phien ban cua so hieu doc trong cac thu muc chia se / phat hanh sang 04_ARCHIVED -> so file
(defun sd:cde-archive (root doc keep / n dst)
  (setq n 0)
  (foreach st '("01_WIP" "02_SHARED" "03_PUBLISHED")
    (foreach f (vl-directory-files (strcat root "\\" st) (strcat doc "_*.*") 1)
      (if (not (wcmatch (strcase f) (strcat (strcase keep) "*")))
        (progn
          (setq dst (strcat (sd:cde-mkdir (strcat root "\\04_ARCHIVED")) "\\" f))
          (if (sd:fexists dst) (sd:fso-do 'DeleteFile (list dst :vlax-true)))
          (if (sd:fso-do 'MoveFile (list (strcat root "\\" st "\\" f) dst)) (setq n (1+ n)))))))
  n)

;; Ghi thuoc tinh khung ten: so hieu / phien ban / trang thai
(defun sd:cde-attrs (e cfg doc)
  (+ (sd:lo-attr e (cdr (assoc "tdoc" cfg)) doc)
     (sd:lo-attr e (cdr (assoc "trev" cfg)) (strcase (cdr (assoc "rev" cfg))))
     (sd:lo-attr e (cdr (assoc "tst" cfg)) (strcase (cdr (assoc "st" cfg))))))

;; Ghi dong vao CSV (tao tieu de neu file moi)
(defun sd:cde-csv (fn head lines / new f)
  (setq new (not (sd:fexists fn)))
  (if (setq f (sd:open fn (if new "w" "a")))
    (progn (if new (write-line head f))
           (foreach l lines (write-line l f))
           (sd:close f))))
(defun sd:cde-trim (n l) (if (> (length l) n) (sd:head n l) l))
(defun sd:cde-q (s) (strcat "\"" (vl-string-translate "\"" "'" s) "\""))

(defun c:SDCDE (/ doc old cfg op errs root st dir dev lay devs bp i n fn docno files rows ok r ss j e lays fr
                  media m ext stamp who tr nar src title)
  (sd:begin)
  (setq doc (sd:doc)
        old (cond ((vlax-ldata-get "SD" "CDE")) ('())))
  (if (not (sd:dlg "Phat hanh len CDE - ISO 19650 (SDCDE)"
                   (list (list "op" "Thao tac" 'kw (cond ((cdr (assoc "op" old))) ("Phathanh"))
                               '(("Phathanh" . "Phat hanh: xuat PDF vao thu muc trang thai + so dang ky")
                                 ("Kiemtra" . "Kiem tra ma ISO 19650 + lich su phat hanh")))
                         (list "root" "Thu muc CDE (thu muc dong bo ACC / SharePoint / o mang)" 'str
                               (cond ((cdr (assoc "root" old))) ((strcat (getvar "DWGPREFIX") "CDE"))))
                         (list "proj" "Ma du an (2-6)" 'str (cond ((cdr (assoc "proj" old))) ("DA01")))
                         (list "orig" "Ma don vi lap (3-6)" 'str (cond ((cdr (assoc "orig" old))) ("ABC")))
                         (list "vol" "Khu vuc / hang muc (ZZ = toan bo)" 'str (cond ((cdr (assoc "vol" old))) ("ZZ")))
                         (list "lev" "Tang (00, 01, B1, ZZ...)" 'str (cond ((cdr (assoc "lev" old))) ("ZZ")))
                         (list "typ" "Loai tai lieu (DR ban ve, M3 mo hinh, SH bang...)" 'str (cond ((cdr (assoc "typ" old))) ("DR")))
                         (list "role" "Bo mon (S ket cau, A kien truc...)" 'str (cond ((cdr (assoc "role" old))) ("S")))
                         (list "num" "So to bat dau (4-6 chu so)" 'str (cond ((cdr (assoc "num" old))) ("0001")))
                         (list "st" "Trang thai (suitability)" 'kw (cond ((cdr (assoc "st" old))) ("S2")) *SD:CDEST*)
                         (list "rev" "Phien ban (P01.. chia se, C01.. phat hanh)" 'str (cond ((cdr (assoc "rev" old))) ("P01")))
                         (list "src" "To ban ve" 'kw (cond ((cdr (assoc "src" old))) ("Layout"))
                               '(("Layout" . "Moi Layout 1 to (theo thu tu tab)") ("Khung" . "Khung ten trong Model (thiet lap SDIN / SDTAOLAYOUT)"))
                               nil '("op" "Phathanh"))
                         (list "dwg" "Kem ban DWG (ban sao cung phien ban)" 'tog (if (assoc "dwg" old) (cdr (assoc "dwg" old)) t) nil '("op" "Phathanh"))
                         (list "arch" "Chuyen ban cu cung so hieu sang 04_ARCHIVED" 'tog t nil '("op" "Phathanh"))
                         (list "tdoc" "Tag thuoc tinh so hieu" 'str (cond ((cdr (assoc "tdoc" old))) ("SOHIEU*,DOCNO*,DOC_NO*,MA_BV*")) nil '("op" "Phathanh"))
                         (list "trev" "Tag thuoc tinh phien ban" 'str (cond ((cdr (assoc "trev" old))) ("REV*,PHIENBAN*,LANSUA*")) nil '("op" "Phathanh"))
                         (list "tst" "Tag thuoc tinh trang thai" 'str (cond ((cdr (assoc "tst" old))) ("TRANGTHAI*,STATUS*,SUIT*")) nil '("op" "Phathanh")))))
    (exit))
  (setq cfg (mapcar '(lambda (k) (cons k (sd:v k))) '("op" "root" "proj" "orig" "vol" "lev" "typ" "role" "num" "st" "rev" "src" "dwg" "tdoc" "trev" "tst"))
        op (sd:v "op") st (sd:v "st")
        root (vl-string-right-trim "\\/ " (sd:v "root"))
        errs (sd:cde-check cfg))
  (vlax-ldata-put "SD" "CDE" (append cfg (list (cons "hist" (cdr (assoc "hist" old))))))
  (cond
    ;; ---- kiem tra
    ((= op "Kiemtra")
     (princ (strcat "\n[SD] Mau so hieu: " (sd:cde-docno cfg 0) "_" (strcase (sd:v "rev")) "_" st
                    "  -> thu muc " root "\\" (sd:cde-state st)))
     (if errs (foreach x errs (princ (strcat "\n  [!] " x))) (princ "\n  Ma dung quy uoc ISO 19650."))
     (princ "\n[SD] Lich su phat hanh ban ve nay (moi nhat truoc):")
     (setq i 0)
     (foreach h (cdr (assoc "hist" old))
       (if (< i 20) (princ (strcat "\n  " (sd:join h "  "))))
       (setq i (1+ i)))
     (if (= i 0) (princ "\n  (chua phat hanh lan nao)")))
    (errs
     (foreach x errs (princ (strcat "\n  [!] " x)))
     (princ "\n[SD] Ma chua dung quy uoc - sua roi chay lai (khong phat hanh)."))
    ;; ---- phat hanh
    (t
     (sd:cde-mkdir root)
     (setq dir (sd:cde-mkdir (strcat root "\\" (sd:cde-state st)))
           lay (vla-get-ActiveLayout doc))
     (vla-RefreshPlotDeviceInfo lay)
     (setq devs (sd:sa->list (vla-GetPlotDeviceNames lay))
           dev  (cond ((car (vl-member-if '(lambda (x) (wcmatch (strcase x) "DWG TO PDF*")) devs)))
                      ((car (vl-member-if '(lambda (x) (wcmatch (strcase x) "*PDF*")) devs))))
           bp (getvar "BACKGROUNDPLOT")
           *SD:VARS* (cons (cons "BACKGROUNDPLOT" bp) *SD:VARS*)
           stamp (menucmd "M=$(edtime,$(getvar,date),YYYYMODD-HHMMSS)")
           who (cond ((getvar "LOGINNAME")) ("")) i 0 n 0)
     (setvar "BACKGROUNDPLOT" 0)
     (if (null dev) (princ "\n[SD] Khong tim thay may in PDF (DWG To PDF.pc3) - chi ghi thuoc tinh / DWG."))
     (cond
       ((= (sd:v "src") "Layout")
        (vlax-for l (vla-get-Layouts doc) (if (/= (vla-get-ModelType l) :vlax-true) (setq lays (cons l lays))))
        (setq lays (sd:sort lays '(lambda (a b) (< (vla-get-TabOrder a) (vla-get-TabOrder b)))))
        (foreach l lays
          (setq docno (sd:cde-docno cfg i) i (1+ i)
                fn (strcat dir "\\" docno "_" (strcase (sd:v "rev")) "_" st ".pdf")
                title (vla-get-Name l))
          (if (setq ss (ssget "_X" (list '(0 . "INSERT") '(66 . 1) (cons 410 (vla-get-Name l)))))
            (progn (setq j 0) (repeat (sslength ss) (sd:cde-attrs (ssname ss j) cfg docno) (setq j (1+ j)))))
          (vla-put-ActiveLayout doc l)
          (if (and dev (not (wcmatch (strcase (vla-get-ConfigName l)) "*PDF*")))
            (vl-catch-all-apply 'vla-put-ConfigName (list l dev)))
          (setq r (if dev (vl-catch-all-apply '(lambda () (vla-PlotToFile (vla-get-Plot doc) fn)) nil)))
          (if (and dev (not (eq r :vlax-true)))
            (princ (strcat "\n[SD] Loi in " title (if (vl-catch-all-error-p r) (strcat ": " (vl-catch-all-error-message r)) ""))))
          (setq files (cons (list docno title fn (eq r :vlax-true)) files)))
        (setvar "TILEMODE" 1))
       (t
        (setq old (cond ((vlax-ldata-get "SD" "TLO")) ((vlax-ldata-get "SD" "INHL")) ('()))
              fr (if (and (cdr (assoc "key" old)) (/= (cdr (assoc "key" old)) ""))
                   (sd:in-order (sd:in-frames (cond ((cdr (assoc "mode" old))) ("Block")) (cdr (assoc "key" old)) nil)
                                (cond ((cdr (assoc "order" old))) ("Hang")))))
        (if (null fr) (princ "\n[SD] Chua co khung ten: chay SDIN hoac SDTAOLAYOUT mot lan de khai bao block / layer khung."))
        (if (= (getvar "TILEMODE") 0) (setvar "TILEMODE" 1))
        (setq lay (vla-get-ActiveLayout doc))
        (if dev (progn (vla-put-ConfigName lay dev) (setq media (sd:in-media lay))))
        (foreach f fr
          (setq docno (sd:cde-docno cfg i) i (1+ i)
                fn (strcat dir "\\" docno "_" (strcase (sd:v "rev")) "_" st ".pdf")
                title (strcat "Khung " (itoa i)))
          (sd:cde-attrs (nth 3 f) cfg docno)
          (setq m (if dev (sd:in-autopaper f (mapcar '(lambda (x) (list (car x) (caddr x) (cadddr x))) media) (sd:sc)))
                r (if m (sd:in-one doc lay f m (list dev "monochrome.ctb" "Fit" (sd:sc) t) fn)))
          (if (and dev (/= r t)) (princ (strcat "\n[SD] Loi in " title ": " (if (= (type r) 'STR) r "khong co kho giay"))))
          (setq files (cons (list docno title fn (= r t)) files)))))
     (setq files (reverse files))
     ;; ban DWG kem theo (luu truoc)
     (if (and (sd:v "dwg") files)
       (progn
         (vl-catch-all-apply 'vla-Save (list doc))
         (setq fn (strcat dir "\\" (car (car files)) "_" (strcase (sd:v "rev")) "_" st ".dwg"))
         (if (sd:fcopy (strcat (getvar "DWGPREFIX") (getvar "DWGNAME")) fn)
           (setq files (append files (list (list (car (car files)) (strcat "DWG " (getvar "DWGNAME")) fn t))))
           (princ "\n[SD] Khong chep duoc file DWG (luu ban ve truoc)."))))
     ;; luu tru ban cu
     (setq nar 0)
     (if (sd:v "arch")
       (foreach x files
         (if (cadddr x) (setq nar (+ nar (sd:cde-archive root (car x) (strcat (car x) "_" (strcase (sd:v "rev")) "_" st)))))))
     ;; so dang ky + phieu chuyen giao
     (foreach x files
       (if (cadddr x)
         (setq n (1+ n)
               rows (cons (sd:join (list (sd:today) (car x) (sd:cde-q (cadr x)) (strcase (sd:v "rev")) st (sd:cde-state st)
                                         (sd:cde-q (vl-filename-base (caddr x))) (sd:cde-q who) (sd:cde-q (getvar "DWGNAME")))
                                   ",")
                          rows))))
     (setq rows (reverse rows)
           r "Ngay,So hieu tai lieu,Ten to,Phien ban,Trang thai,Thu muc,File,Nguoi phat hanh,Ban ve nguon")
     (if rows
       (progn
         (sd:cde-csv (strcat root "\\CDE_Register.csv") r rows)
         (setq tr (strcat root "\\Transmittal_" stamp ".csv"))
         (sd:cde-csv tr (strcat "PHIEU CHUYEN GIAO " stamp " - trang thai " (cdr (assoc st *SD:CDEST*)) "\n" r) rows)
         (vlax-ldata-put "SD" "CDE"
                         (append cfg (list (cons "hist" (sd:cde-trim 200 (append (reverse (mapcar '(lambda (x) (list (sd:today) (car x) (strcase (sd:v "rev")) st))
                                                                                                (vl-remove-if-not 'cadddr files)))
                                                                               (cdr (assoc "hist" (vlax-ldata-get "SD" "CDE")))))))))))
     (setvar "BACKGROUNDPLOT" bp)
     (princ (strcat "\n[SD] Phat hanh " (itoa n) " file vao " dir
                    (if (> nar 0) (strcat "; chuyen " (itoa nar) " ban cu sang 04_ARCHIVED") "")
                    (if rows (strcat "; so dang ky CDE_Register.csv, phieu " (vl-filename-base tr) ".csv") "")
                    ". Tang phien ban (P02, C02...) cho lan phat hanh sau."))))
  (sd:finish))

;;; ==========================================================================
;;;  AUTOCAD NANG CAO: chuan ban ve + file mau, block dong + thuoc tinh, Xref, danh muc ban ve
;;;    SDCHUAN   : kiem tra / ap dung chuan layer, linetype, text style, dimstyle; xuat file mau .dwt
;;;    SDTKBLOCK : thong ke block (ke ca block dong: visibility, tham so) + thuoc tinh -> bang + CSV;
;;;                gan hang loat gia tri thuoc tinh / tham so block dong (co {n} danh so)
;;;    SDXREF    : bao cao Xref (da nap / chua nap / khong tim thay, duong dan), doi sang duong dan tuong doi,
;;;                tim lai Xref mat duong dan, nap lai
;;;    SDDMBV    : danh muc ban ve (Sheet List) tu Layout / khung ten: so hieu, ten, ty le, phien ban -> bang + CSV
;;; ==========================================================================

;; ---- SDCHUAN -------------------------------------------------------------------
(defun sd:lay-dev (l / ed r)
  (if (setq ed (entget (tblobjname "LAYER" (car l))))
    (progn
      (if (/= (abs (cdr (assoc 62 ed))) (cadr l)) (setq r (cons (strcat "mau " (itoa (abs (cdr (assoc 62 ed)))) " -> " (itoa (cadr l))) r)))
      (if (/= (strcase (cdr (assoc 6 ed))) (strcase (sd:ltype (caddr l)))) (setq r (cons (strcat "net " (cdr (assoc 6 ed)) " -> " (sd:ltype (caddr l))) r)))
      (if (/= (cdr (assoc 370 ed)) (cadddr l)) (setq r (cons (strcat "lw " (itoa (cdr (assoc 370 ed))) " -> " (itoa (cadddr l))) r)))
      (reverse r))
    (list "chua co")))

(defun sd:lay-fix (l / ed)
  (if (not (tblsearch "LAYER" (car l)))
    (apply 'sd:make-layer l)
    (progn
      (setq ed (entget (tblobjname "LAYER" (car l))))
      (setq ed (subst (cons 62 (if (minusp (cdr (assoc 62 ed))) (- (cadr l)) (cadr l))) (assoc 62 ed) ed)
            ed (subst (cons 6 (sd:ltype (caddr l))) (assoc 6 ed) ed)
            ed (if (assoc 370 ed) (subst (cons 370 (cadddr l)) (assoc 370 ed) ed) (append ed (list (cons 370 (cadddr l))))))
      (entmod ed))))

;; Dem doi tuong trong Model theo bo loc
(defun sd:cnt (flt / ss) (if (setq ss (ssget "_X" flt)) (sslength ss) 0))

;; Xuat file mau: chep layer SD-*, text style SD-TEXT, dimstyle SD-*, block khung SD-KHUNG-* sang ban ve trong (ObjectDBX)
(defun sd:dwt-export (fn / doc dbx r objs n)
  (setq doc (sd:doc) n 0
        dbx (vl-catch-all-apply 'vla-GetInterfaceObject
                                (list (vlax-get-acad-object) (strcat "ObjectDBX.AxDbDocument." (substr (getvar "ACADVER") 1 2)))))
  (if (vl-catch-all-error-p dbx)
    (strcat "khong tao duoc ObjectDBX: " (vl-catch-all-error-message dbx))
    (progn
      (setq r (vl-catch-all-apply
                '(lambda ()
                   (foreach c (list (list (vla-get-Layers doc) "SD-*" (vla-get-Layers dbx))
                                    (list (vla-get-TextStyles doc) "SD-*" (vla-get-TextStyles dbx))
                                    (list (vla-get-DimStyles doc) "SD-*" (vla-get-DimStyles dbx))
                                    (list (vla-get-Blocks doc) "SD-KHUNG-*" (vla-get-Blocks dbx)))
                     (setq objs nil)
                     (vlax-for o (car c) (if (wcmatch (strcase (vla-get-Name o)) (cadr c)) (setq objs (cons o objs))))
                     (if objs
                       (progn
                         (vla-CopyObjects doc (vlax-make-variant (vlax-safearray-fill (vlax-make-safearray vlax-vbObject (cons 0 (1- (length objs)))) objs))
                                          (caddr c))
                         (setq n (+ n (length objs))))))
                   (vla-SaveAs dbx fn))
                nil))
      (vl-catch-all-apply 'vlax-release-object (list dbx))
      (if (vl-catch-all-error-p r) (vl-catch-all-error-message r) n))))

(defun c:SDCHUAN (/ op dev nd l n0 nt nd2 lays fn r st nc ss i e ed)
  (sd:begin)
  (if (not (sd:dlg "Chuan ban ve + file mau (SDCHUAN)"
                   (list (list "op" "Thao tac" 'kw "Kiemtra"
                               '(("Kiemtra" . "Kiem tra layer / chu / kich thuoc theo chuan SD")
                                 ("Apdung" . "Ap dung chuan: dat lai layer, text style, dimstyle")
                                 ("Xuatdwt" . "Xuat file mau .dwt (layer, style, dimstyle, khung ten)")))
                         (list "txt" "Chuyen moi chu (TEXT / MTEXT) sang style SD-TEXT" 'tog nil nil '("op" "Apdung"))
                         (list "fn" "File mau (.dwt)" 'str (strcat (getvar "DWGPREFIX") "ShopDrawing.dwt") nil '("op" "Xuatdwt")))))
    (exit))
  (setq op (sd:v "op"))
  (cond
    ((= op "Kiemtra")
     (setq nd 0)
     (foreach l *SD:LAYERS*
       (if (setq dev (sd:lay-dev l))
         (progn (setq nd (1+ nd)) (princ (strcat "\n  [!] " (car l) ": " (sd:join dev ", "))))))
     (setq n0 (sd:cnt '((8 . "0") (410 . "Model")))
           nt (- (sd:cnt '((0 . "TEXT,MTEXT"))) (sd:cnt (list '(0 . "TEXT,MTEXT") (cons 7 (sd:tstyle)))))
           nd2 (- (sd:cnt '((0 . "DIMENSION"))) (sd:cnt '((0 . "DIMENSION") (3 . "SD-*")))))
     (vlax-for y (vla-get-Layers (sd:doc))
       (if (not (wcmatch (strcase (vla-get-Name y)) "SD-*,0,DEFPOINTS,*|*")) (setq lays (cons (vla-get-Name y) lays))))
     (princ (strcat "\n[SD] Layer SD lech chuan: " (itoa nd) "; doi tuong tren layer 0 (Model): " (itoa n0)
                    "; chu khong dung SD-TEXT: " (itoa nt) "; kich thuoc khong dung dimstyle SD: " (itoa nd2)
                    "; layer ngoai chuan: " (itoa (length lays))
                    (if lays (strcat " (" (sd:join (sd:head (min 8 (length lays)) (reverse lays)) ", ") (if (> (length lays) 8) "..." "") ")") "")
                    (if (> (+ nd nt nd2) 0) ". Chay SDCHUAN -> Apdung de sua." "."))))
    ((= op "Apdung")
     (foreach l *SD:LAYERS* (sd:lay-fix l))
     (setq st (sd:tstyle) nc 0)
     (sd:use-dimstyle (sd:sc))
     (if (and (sd:v "txt") (setq ss (ssget "_X" '((0 . "TEXT,MTEXT")))))
       (progn (setq i 0)
              (repeat (sslength ss)
                (setq e (ssname ss i) ed (entget e) i (1+ i))
                (if (/= (cdr (assoc 7 ed)) st) (progn (entmod (subst (cons 7 st) (assoc 7 ed) ed)) (setq nc (1+ nc)))))))
     (princ (strcat "\n[SD] Da dat lai " (itoa (length *SD:LAYERS*)) " layer SD theo chuan, text style " st
                    ", dimstyle SD-1-" (itoa (fix (sd:sc))) (if (sd:v "txt") (strcat "; doi style " (itoa nc) " chu") "") ".")))
    (t
     (setq fn (sd:v "fn"))
     (if (not (wcmatch (strcase fn) "*.DWT")) (setq fn (strcat fn ".dwt")))
     (setq r (sd:dwt-export fn))
     (if (numberp r)
       (princ (strcat "\n[SD] Da xuat file mau " fn " (" (itoa r) " layer / style / dimstyle / khung ten). "
                      "Dung: QNEW / NEW chon file nay, hoac Options -> Files -> Template Settings."))
       (princ (strcat "\n[SD] Loi xuat file mau: " r)))))
  (sd:finish))

;; ---- SDTKBLOCK -----------------------------------------------------------------
(defun sd:bk-name (o) (cond ((sd:prop o 'EffectiveName)) ((vla-get-Name o))))
(defun sd:bk-val (v)
  (cond ((numberp v) (sd:num (/ (fix (+ (* v 100.0) (if (minusp v) -0.5 0.5))) 100.0)))
        ((= (type v) 'STR) v)
        ((= (type v) 'variant) (sd:bk-val (vlax-variant-value v)))
        (t "")))
;; Tham so block dong: (("Ten" . "gia tri") ...) bo Origin
(defun sd:bk-dyn (o / r)
  (if (and (vlax-property-available-p o 'IsDynamicBlock) (eq (vla-get-IsDynamicBlock o) :vlax-true))
    (foreach p (vlax-invoke o 'GetDynamicBlockProperties)
      (if (/= (strcase (vla-get-PropertyName p)) "ORIGIN")
        (setq r (cons (cons (vla-get-PropertyName p) (sd:bk-val (vla-get-Value p))) r)))))
  (reverse r))
;; Thuoc tinh: (("TAG" . "gia tri") ...)
(defun sd:bk-att (o / r)
  (if (eq (vla-get-HasAttributes o) :vlax-true)
    (foreach a (vlax-invoke o 'GetAttributes) (setq r (cons (cons (strcase (vla-get-TagString a)) (vla-get-TextString a)) r))))
  (reverse r))
(defun sd:kv-str (l) (sd:join (mapcar '(lambda (x) (strcat (car x) "=" (cdr x))) l) "; "))

(defun sd:bk-collect (ss grp / i o key r old dyn att)
  (setq i 0)
  (repeat (sslength ss)
    (setq o (vlax-ename->vla-object (ssname ss i)) i (1+ i)
          dyn (if (/= grp "Ten") (sd:bk-dyn o)) att (if (= grp "Day") (sd:bk-att o))
          key (list (sd:bk-name o) dyn att))
    (if (setq old (assoc key r)) (setq r (subst (cons key (1+ (cdr old))) old r)) (setq r (cons (cons key 1) r))))
  (mapcar '(lambda (k) (nth k r))
          (vl-sort-i r '(lambda (a b) (if (= (strcase (car (car a))) (strcase (car (car b))))
                                        (< (vl-prin1-to-string (cdr (car a))) (vl-prin1-to-string (cdr (car b))))
                                        (< (strcase (car (car a))) (strcase (car (car b)))))))))

(defun sd:bk-csv (rows / fn f tags line)
  (foreach r rows (foreach a (caddr (car r)) (if (not (member (car a) tags)) (setq tags (append tags (list (car a)))))))
  (setq fn (sd:csv-name "_ThongKeBlock.csv"))
  (if (setq f (sd:open fn "w"))
    (progn
      (write-line (sd:join (append '("STT" "Ten block" "Tham so dong") tags '("So luong")) ",") f)
      (setq line 0)
      (foreach r rows
        (setq line (1+ line))
        (write-line (sd:join (append (list (itoa line) (sd:cde-q (car (car r))) (sd:cde-q (sd:kv-str (cadr (car r)))))
                                     (mapcar '(lambda (tg) (sd:cde-q (cond ((cdr (assoc tg (caddr (car r))))) ("")))) tags)
                                     (list (itoa (cdr r))))
                             ",")
                    f))
      (princ (strcat "\n[SD] Da xuat: " (sd:close f))))))

;; Gan gia tri: thuoc tinh (tag mau) hoac tham so block dong (ten) -> T neu gan duoc
(defun sd:bk-set (o kind nm val / ok r)
  (if (= kind "Thuoctinh")
    (if (eq (vla-get-HasAttributes o) :vlax-true)
      (foreach a (vlax-invoke o 'GetAttributes)
        (if (wcmatch (strcase (vla-get-TagString a)) (strcase nm)) (progn (vla-put-TextString a val) (setq ok t)))))
    (if (and (vlax-property-available-p o 'IsDynamicBlock) (eq (vla-get-IsDynamicBlock o) :vlax-true))
      (foreach p (vlax-invoke o 'GetDynamicBlockProperties)
        (if (and (not ok) (= (strcase (vla-get-PropertyName p)) (strcase nm)) (eq (vla-get-ReadOnly p) :vlax-false))
          (progn
            (setq r (vl-catch-all-apply
                      '(lambda (/ cur)
                         (setq cur (vla-get-Value p))
                         (vla-put-Value p (vlax-make-variant (if (numberp (vlax-variant-value cur)) (atof val) val)
                                                             (vlax-variant-type cur))))
                      nil))
            (if (not (vl-catch-all-error-p r)) (setq ok t)))))))
  ok)

(defun c:SDTKBLOCK (/ op flt ss rows pt n i o lst ok trows val pa pb)
  (sd:begin)
  (if (not (sd:dlg "Thong ke / gan thuoc tinh block (SDTKBLOCK)"
                   (list (list "op" "Thao tac" 'kw "Thongke"
                               '(("Thongke" . "Thong ke block + thuoc tinh -> bang, CSV") ("Gan" . "Gan gia tri hang loat")))
                         (list "ten" "Ten block (* ? = mau, ca block dong)" 'str "*")
                         (list "pv" "Pham vi" 'kw "Chon" '(("Chon" . "Chon tren ban ve") ("Tatca" . "Toan bo Model")) nil '("op" "Thongke"))
                         (list "grp" "Gop theo" 'kw "Day"
                               '(("Ten" . "Ten block") ("TenTT" . "Ten + trang thai / tham so dong") ("Day" . "Ten + tham so dong + thuoc tinh"))
                               nil '("op" "Thongke"))
                         (list "bang" "Ve bang thong ke" 'tog t nil '("op" "Thongke"))
                         (list "csv" "Xuat CSV (moi thuoc tinh 1 cot)" 'tog t nil '("op" "Thongke"))
                         (list "kind" "Gan vao" 'kw "Thuoctinh" '(("Thuoctinh" . "Thuoc tinh (tag)") ("Thamso" . "Tham so block dong (VD Visibility1, Distance1)")) nil '("op" "Gan"))
                         (list "nm" "Tag / ten tham so" 'str "" nil '("op" "Gan"))
                         (list "val" "Gia tri ({n} = so thu tu trai -> phai, tren -> duoi)" 'str "" nil '("op" "Gan")))))
    (exit))
  (setq op (sd:v "op") flt '((0 . "INSERT")))
  (if (and (= op "Thongke") (= (sd:v "pv") "Tatca"))
    (setq ss (ssget "_X" '((0 . "INSERT") (410 . "Model"))))
    (progn (princ "\nChon cac block: ") (setq ss (ssget flt))))
  ;; loc theo ten hieu dung (block dong co ten an danh *U..)
  (if ss
    (progn (setq i 0 lst (ssadd))
           (repeat (sslength ss)
             (if (wcmatch (strcase (sd:bk-name (vlax-ename->vla-object (ssname ss i)))) (strcase (sd:v "ten")))
               (ssadd (ssname ss i) lst))
             (setq i (1+ i)))
           (setq ss (if (> (sslength lst) 0) lst))))
  (cond
    ((null ss) (princ "\n[SD] Khong co block nao khop."))
    ((= op "Thongke")
     (setq rows (sd:bk-collect ss (sd:v "grp")))
     (setq n 0)
     (foreach r rows
       (setq n (1+ n))
       (princ (strcat "\n  " (itoa n) ". " (car (car r)) (if (cadr (car r)) (strcat " [" (sd:kv-str (cadr (car r))) "]") "")
                      (if (caddr (car r)) (strcat " {" (sd:kv-str (caddr (car r))) "}") "") " : " (itoa (cdr r)))))
     (princ (strcat "\n[SD] " (itoa (sslength ss)) " block, " (itoa (length rows)) " nhom."))
     (if (sd:v "csv") (sd:bk-csv rows))
     (if (and (sd:v "bang") (setq pt (sd:getpt "\nDiem chen bang (goc trai tren) <bo qua>: " nil)))
       (progn
         (setq n 0 trows nil)
         (foreach r rows
           (setq n (1+ n)
                 trows (cons (list "R" (list (itoa n) (car (car r)) (sd:kv-str (cadr (car r))) (sd:kv-str (caddr (car r))) (itoa (cdr r))) nil) trows)))
         (sd:table2 pt "B\\U+1EA2NG TH\\U+1ED0NG K\\U+00CA BLOCK / THI\\U+1EBET B\\U+1ECA"
                    '(("STT" 10) ("T\\U+00CAN BLOCK" 36) ("TR\\U+1EA0NG TH\\U+00C1I / THAM S\\U+1ED0" 50) ("THU\\U+1ED8C T\\U+00CDNH" 70) ("SL" 12))
                    (reverse trows) -1 (sd:sc)))))
    ((= (vl-string-trim " " (sd:v "nm")) "") (princ "\n[SD] Chua nhap tag / ten tham so."))
    (t
     ;; thu tu: tren -> duoi, trai -> phai
     (setq i 0 lst nil)
     (repeat (sslength ss) (setq lst (cons (ssname ss i) lst) i (1+ i)))
     (setq lst (mapcar '(lambda (k) (nth k lst))
                       (vl-sort-i lst '(lambda (a b / pa pb)
                                         (setq pa (cdr (assoc 10 (entget a))) pb (cdr (assoc 10 (entget b))))
                                         (if (equal (cadr pa) (cadr pb) (* 2.0 (sd:sc))) (< (car pa) (car pb)) (> (cadr pa) (cadr pb))))))
           n 0 i 0)
     (foreach e lst
       (setq i (1+ i) val (sd:v "val"))
       (while (vl-string-search "{n}" val) (setq val (vl-string-subst (itoa i) "{n}" val)))
       (if (sd:bk-set (vlax-ename->vla-object e) (sd:v "kind") (vl-string-trim " " (sd:v "nm")) val) (setq n (1+ n))))
     (princ (strcat "\n[SD] Da gan " (itoa n) " / " (itoa (length lst)) " block"
                    (if (< n (length lst)) " (block con lai khong co tag / tham so do, hoac tham so chi doc)." ".")))))
  (sd:finish))

;; ---- SDXREF --------------------------------------------------------------------
;; Duong dan tuong doi tu thu muc base (co \ cuoi) toi file fn; nil neu khac o dia
(defun sd:relpath (base fn / a b r)
  (setq a (vl-remove "" (sd:split (strcase base) "\\")) b (sd:split fn "\\"))
  (if (and a b (= (car a) (strcase (car b))))
    (progn
      (while (and a (cdr b) (= (car a) (strcase (car b)))) (setq a (cdr a) b (cdr b)))
      (setq r "")
      (repeat (length a) (setq r (strcat r "..\\")))
      (strcat (if (= r "") ".\\" r) (sd:join b "\\")))))

;; Tim file ten nm trong thu muc d va thu muc con (sau toi da lv cap)
(defun sd:findin (d nm lv / r)
  (cond ((findfile (strcat d "\\" nm)))
        ((> lv 0)
         (foreach s (vl-remove "." (vl-remove ".." (vl-directory-files d nil -1)))
           (if (not r) (setq r (sd:findin (strcat d "\\" s) nm (1- lv)))))
         r)))

;; Trang thai Xref: (ten duong-dan file-tim-thay da-nap)
(defun sd:xr-info (b / nm p f fl)
  (setq nm (vla-get-Name b) p (vla-get-Path b)
        fl (cdr (assoc 70 (tblsearch "BLOCK" nm)))
        f (cond ((findfile p)) ((findfile (strcat (getvar "DWGPREFIX") p)))))
  (list nm p f (and fl (= 32 (logand 32 fl)))))

(defun c:SDXREF (/ doc base xs n nl nf nr nrel f rel nm trows pt)
  (sd:begin)
  (if (not (sd:dlg "Quan ly Xref (SDXREF)"
                   (list (list "note" "Xref: ban ve tham chieu ngoai (mat bang kien truc, luoi truc, ban ve bo mon khac)" 'note nil)
                         (list "rel" "Doi duong dan tuyet doi -> tuong doi (de chep ca thu muc du an)" 'tog t)
                         (list "tim" "Tim lai Xref mat duong dan trong thu muc ban ve (3 cap thu muc con)" 'tog t)
                         (list "nap" "Nap lai tat ca Xref" 'tog t)
                         (list "bang" "Ve bang bao cao" 'tog nil))))
    (exit))
  (setq doc (sd:doc) base (getvar "DWGPREFIX") n 0 nl 0 nf 0 nr 0 nrel 0)
  (vlax-for b (vla-get-Blocks doc)
    (if (eq (vla-get-IsXRef b) :vlax-true) (setq xs (cons b xs))))
  (if (null xs)
    (princ "\n[SD] Ban ve khong co Xref.")
    (progn
      (foreach b (reverse xs)
        (setq f (sd:xr-info b) nm (car f) n (1+ n))
        ;; tim lai file mat
        (if (and (not (caddr f)) (sd:v "tim")
                 (setq rel (sd:findin (vl-string-right-trim "\\" base) (strcat (vl-filename-base (cadr f)) (cond ((vl-filename-extension (cadr f))) (".dwg"))) 3)))
          (if (not (vl-catch-all-error-p (vl-catch-all-apply 'vla-put-Path (list b rel))))
            (setq nf (1+ nf) f (sd:xr-info b))))
        ;; tuong doi
        (if (and (sd:v "rel") (caddr f) (wcmatch (cadr f) "?:\\*,\\\\*")
                 (setq rel (sd:relpath base (caddr f)))
                 (not (vl-catch-all-error-p (vl-catch-all-apply 'vla-put-Path (list b rel)))))
          (setq nrel (1+ nrel) f (sd:xr-info b)))
        (if (and (sd:v "nap") (caddr f) (not (vl-catch-all-error-p (vl-catch-all-apply 'vla-Reload (list b)))))
          (setq nr (1+ nr) f (sd:xr-info b)))
        (if (cadddr f) (setq nl (1+ nl)))
        (princ (strcat "\n  " nm ": " (cond ((cadddr f) "da nap") ((caddr f) "chua nap") (t "KHONG TIM THAY")) " | " (cadr f)
                       (if (wcmatch (cadr f) "?:\\*,\\\\*") " (tuyet doi)" (if (wcmatch (cadr f) "*\\*") " (tuong doi)" " (khong duong dan)"))))
        (setq trows (cons (list "R" (list nm (cond ((cadddr f) "\\U+0110\\U+00C3 N\\U+1EA0P") ((caddr f) "CH\\U+01AFA N\\U+1EA0P") (t "KH\\U+00D4NG T\\U+00CCM TH\\U+1EA4Y")) (cadr f)) nil) trows)))
      (princ (strcat "\n[SD] " (itoa n) " Xref: " (itoa nl) " da nap, " (itoa (- n nl)) " chua nap / mat"
                     (if (> nf 0) (strcat "; tim lai " (itoa nf)) "") (if (> nrel 0) (strcat "; doi tuong doi " (itoa nrel)) "")
                     (if (> nr 0) (strcat "; nap lai " (itoa nr)) "")
                     "."))
      (if (and (sd:v "bang") (setq pt (sd:getpt "\nDiem chen bang (goc trai tren) <bo qua>: " nil)))
        (sd:table2 pt "DANH S\\U+00C1CH XREF" '(("T\\U+00CAN XREF" 40) ("TR\\U+1EA0NG TH\\U+00C1I" 28) ("\\U+0110\\U+01AF\\U+1EDCNG D\\U+1EAAN" 110)) (reverse trows) -1 (sd:sc)))))
  (sd:finish))

;; ---- SDDMBV --------------------------------------------------------------------
;; Khung ten trong 1 layout: INSERT co thuoc tinh, nhieu thuoc tinh khop mau nhat
(defun sd:dm-tb (lname pats / ss i e best bn k)
  (if (setq ss (ssget "_X" (list '(0 . "INSERT") '(66 . 1) (cons 410 lname))))
    (progn (setq i 0 bn -1)
           (repeat (sslength ss)
             (setq e (ssname ss i) i (1+ i)
                   k (length (vl-remove nil (mapcar '(lambda (p) (sd:lo-attr-get e p)) pats))))
             (if (> k bn) (setq best e bn k)))))
  best)

(defun c:SDDMBV (/ pats lays fr old sh rows i e nm tl sc rv trows pt f n)
  (sd:begin)
  (if (not (sd:dlg "Danh muc ban ve - Sheet List (SDDMBV)"
                   (list (list "src" "To ban ve" 'kw "Layout"
                               '(("Layout" . "Moi Layout 1 to (theo thu tu tab)") ("Khung" . "Khung ten trong Model (thiet lap SDIN / SDTAOLAYOUT)")))
                         (list "tsh" "Tag so hieu" 'str "SHEET*,SOHIEU*,SOBV*,SO_TO*,SOTO*,DOCNO*")
                         (list "tti" "Tag ten ban ve" 'str "TITLE*,TENBV*,TEN_BV*,TENBANVE*")
                         (list "tsc" "Tag ty le" 'str "SCALE*,TYLE*,TY_LE*")
                         (list "trv" "Tag phien ban" 'str "REV*,PHIENBAN*,LANSUA*")
                         (list "csv" "Xuat CSV" 'tog t))))
    (exit))
  (setq pats (list (sd:v "tsh") (sd:v "tti") (sd:v "tsc") (sd:v "trv")) i 0)
  (if (= (sd:v "src") "Layout")
    (progn
      (vlax-for l (vla-get-Layouts (sd:doc)) (if (/= (vla-get-ModelType l) :vlax-true) (setq lays (cons l lays))))
      (foreach l (sd:sort lays '(lambda (a b) (< (vla-get-TabOrder a) (vla-get-TabOrder b))))
        (setq nm (vla-get-Name l) e (sd:dm-tb nm pats))
        (setq rows (cons (list (cond ((sd:lo-attr-get e (car pats))) (nm)) (cond ((sd:lo-attr-get e (cadr pats))) (nm))
                               (cond ((sd:lo-attr-get e (caddr pats))) ("")) (cond ((sd:lo-attr-get e (cadddr pats))) ("")))
                         rows))))
    (progn
      (setq old (cond ((vlax-ldata-get "SD" "TLO")) ((vlax-ldata-get "SD" "INHL")) ('()))
            fr (if (and (cdr (assoc "key" old)) (/= (cdr (assoc "key" old)) ""))
                 (sd:in-order (sd:in-frames (cond ((cdr (assoc "mode" old))) ("Block")) (cdr (assoc "key" old)) nil)
                              (cond ((cdr (assoc "order" old))) ("Hang")))))
      (foreach f fr
        (setq i (1+ i) e (nth 3 f))
        (setq rows (cons (list (cond ((sd:lo-attr-get e (car pats))) ((itoa i))) (cond ((sd:lo-attr-get e (cadr pats))) ((strcat "Khung " (itoa i))))
                               (cond ((sd:lo-attr-get e (caddr pats))) ("")) (cond ((sd:lo-attr-get e (cadddr pats))) ("")))
                         rows)))))
  (setq rows (reverse rows))
  (if (null rows)
    (princ (if (= (sd:v "src") "Layout") "\n[SD] Ban ve chua co Layout." "\n[SD] Chua co khung ten: chay SDIN hoac SDTAOLAYOUT de khai bao khung."))
    (progn
      (setq n 0)
      (foreach r rows
        (setq n (1+ n) trows (cons (list "R" (cons (itoa n) r) nil) trows)))
      (princ (strcat "\n[SD] Danh muc " (itoa n) " to ban ve."))
      (if (and (sd:v "csv") (setq f (sd:open (setq nm (sd:csv-name "_DanhMucBanVe.csv")) "w")))
        (progn
          (write-line "STT,So hieu,Ten ban ve,Ty le,Phien ban" f)
          (setq n 0)
          (foreach r rows (setq n (1+ n)) (write-line (sd:join (cons (itoa n) (mapcar 'sd:cde-q r)) ",") f))
          (princ (strcat "\n[SD] Da xuat: " (sd:close f)))))
      (if (setq pt (sd:getpt "\nDiem chen bang danh muc (goc trai tren) <bo qua>: " nil))
        (sd:table2 pt "DANH M\\U+1EE4C B\\U+1EA2N V\\U+1EBC" '(("STT" 12) ("S\\U+1ED0 HI\\U+1EC6U" 50) ("T\\U+00CAN B\\U+1EA2N V\\U+1EBC" 90) ("T\\U+1EF6 L\\U+1EC6" 20) ("PHI\\U+00CAN B\\U+1EA2N" 22))
                   (reverse trows) -1 (sd:sc)))))
  (sd:finish))

;;; ==========================================================================
;;;  SDLOC - Loc / tim nhanh doi tuong theo bieu thuc dieu kien (y tuong OneFilter cua DiRoots)
;;;    Bieu thuc: dieu kien noi bang & (VA), | (HOAC; & uu tien hon |)
;;;    Dieu kien: <truong><phep so sanh><gia tri>
;;;      truong : loai layer mau net block chu dai dientich bankinh cao (do cao Z) kg (khong gian / layout)
;;;               att:TAG (thuoc tinh block) dyn:TEN (tham so block dong)
;;;               ck (cau kien SD) d (duong kinh thep) sh (so hieu thep) sl (so thanh) tang (tang cau kien)
;;;      phep   : = <> > < >= <= ~ (chua, khong phan biet hoa thuong); = <> dung mau * ? # , cho chu
;;;    VD: loai=INSERT & block=VAN* & att:CONGSUAT>=5 | layer=SD-THEP* & d>=20
;;;    Truong khong co (VD ck cua doi tuong thuong) duoc coi la chuoi rong: ck= tim doi tuong chua gan cau kien
;;;  Ket qua: chon (grip), dem theo layer / loai, co lap (ISOLATEOBJECTS), doi layer, xuat CSV
;;; ==========================================================================
(setq *SD:LOCOPS* '(">=" "<=" "<>" "=" ">" "<" "~"))
(setq *SD:LOCF* '("loai" "layer" "mau" "net" "block" "chu" "dai" "dientich" "bankinh" "cao" "kg" "ck" "d" "sh" "sl" "tang"))

;; Phan tich 1 dieu kien -> (truong phep gia-tri) hoac chuoi loi
(defun sd:loc-cond (s / i best p op f)
  (setq s (vl-string-trim " \t" s))
  (foreach o *SD:LOCOPS*
    (if (and (setq p (vl-string-search o s)) (or (null best) (< p (car best)) (and (= p (car best)) (> (strlen o) (strlen (cadr best))))))
      (setq best (list p o))))
  (if (null best)
    (strcat "thieu phep so sanh trong '" s "'")
    (progn
      (setq p (car best) op (cadr best)
            f (strcase (vl-string-trim " " (substr s 1 p)) t))
      (if (or (member f *SD:LOCF*) (wcmatch f "att:?*,dyn:?*"))
        (list f op (vl-string-trim " " (substr s (+ p (strlen op) 1))))
        (strcat "truong '" f "' khong co (dung: " (sd:join *SD:LOCF*  " ") " att:TAG dyn:TEN)")))))

;; Bieu thuc -> ((dk dk ...) ...) nhom HOAC cua cac nhom VA; hoac chuoi loi
(defun sd:loc-parse (s / r g c err)
  (foreach og (sd:split s "|")
    (setq g nil)
    (foreach a (sd:split og "&")
      (if (/= (vl-string-trim " \t" a) "")
        (if (= (type (setq c (sd:loc-cond a))) 'STR) (if (not err) (setq err c)) (setq g (cons c g)))))
    (if g (setq r (cons (reverse g) r))))
  (cond (err) ((null r) "bieu thuc rong") (t (reverse r))))

;; Gia tri truong cua doi tuong (nil = khong co)
(defun sd:loc-get (e ed f / o x tg)
  (cond
    ((= f "loai") (cdr (assoc 0 ed)))
    ((= f "layer") (cdr (assoc 8 ed)))
    ((= f "mau") (cond ((cdr (assoc 62 ed))) (256)))
    ((= f "net") (cond ((cdr (assoc 6 ed))) ("BYLAYER")))
    ((= f "kg") (cond ((cdr (assoc 410 ed))) ("Model")))
    ((= f "chu") (cond ((= (cdr (assoc 0 ed)) "MTEXT") (sd:mt-plain (vla-get-TextString (vlax-ename->vla-object e))))
                       ((member (cdr (assoc 0 ed)) '("TEXT" "ATTRIB" "ATTDEF")) (cdr (assoc 1 ed)))))
    ((= f "cao") (caddr (cdr (assoc 10 ed))))
    ((= f "bankinh") (cdr (assoc 40 (if (member (cdr (assoc 0 ed)) '("CIRCLE" "ARC")) ed))))
    ((= f "dai")
     (if (not (vl-catch-all-error-p (setq x (vl-catch-all-apply '(lambda () (vlax-curve-getDistAtParam e (vlax-curve-getEndParam e))) nil))))
       x))
    ((= f "dientich") (if (vlax-property-available-p (setq o (vlax-ename->vla-object e)) 'Area) (sd:prop o 'Area)))
    ((= f "block") (if (= (cdr (assoc 0 ed)) "INSERT") (sd:bk-name (vlax-ename->vla-object e))))
    ((wcmatch f "att:*")
     (if (= (cdr (assoc 0 ed)) "INSERT")
       (progn (setq tg (strcase (substr f 5)))
              (cdr (assoc tg (sd:bk-att (vlax-ename->vla-object e)))))))
    ((wcmatch f "dyn:*")
     (if (= (cdr (assoc 0 ed)) "INSERT")
       (progn (setq tg (strcase (substr f 5)))
              (cdr (car (vl-member-if '(lambda (a) (= (strcase (car a)) tg)) (sd:bk-dyn (vlax-ename->vla-object e))))))))
    ((= f "ck") (cond ((setq x (cadr (assoc -3 (entget e '("SD_CK"))))) (cdr (cadr x)))
                      ((setq x (cadr (assoc -3 (entget e '("SD_KL"))))) (cdr (cadr x)))))
    ((= f "tang") (if (setq x (cadr (assoc -3 (entget e '("SD_KL"))))) (cdr (nth 7 x))))
    ((member f '("d" "sh" "sl"))
     (if (setq x (cadr (assoc -3 (entget e '("SD_REBAR")))))
       (cdr (nth (cdr (assoc f '(("sh" . 1) ("sl" . 2) ("d" . 3)))) x))))))

;; So sanh gia tri v voi dieu kien (op, t)
(defun sd:loc-cmp (v op tv / a b)
  (cond
    ((and (null v) (setq v "") nil))
    ((and (setq b (distof tv 2)) (setq a (if (numberp v) v (distof v 2))))
     (cond ((= op "=") (equal a b 1e-6)) ((= op "<>") (not (equal a b 1e-6)))
           ((= op ">") (> a b)) ((= op "<") (< a b)) ((= op ">=") (>= a b)) ((= op "<=") (<= a b))
           (t (vl-string-search (strcase tv) (strcase (if (numberp v) (sd:num v) v))))))
    (t
     (setq a (strcase (if (numberp v) (sd:num v) v)) b (strcase tv))
     (cond ((= op "=") (wcmatch a b)) ((= op "<>") (not (wcmatch a b)))
           ((= op "~") (vl-string-search b a))
           ((= op ">") (> a b)) ((= op "<") (< a b)) ((= op ">=") (>= a b)) ((= op "<=") (<= a b))))))

;; Doi tuong khop bieu thuc?
(defun sd:loc-match (e ed groups)
  (vl-some '(lambda (g) (vl-every '(lambda (c) (sd:loc-cmp (sd:loc-get e ed (car c)) (cadr c) (caddr c))) g)) groups))

;; Bieu thuc da dung (nho giua cac ban ve, toi da 10)
(defun sd:loc-hist (/ s) (if (setq s (getenv "ShopDrawingLoc")) (vl-remove "" (sd:split s "^^"))))
(defun sd:loc-save (x / h)
  (setq h (cons x (vl-remove x (sd:loc-hist))))
  (setenv "ShopDrawingLoc" (sd:join (if (> (length h) 10) (sd:head 10 h) h) "^^")))

(setq *SD:LOCMAU*
  '(("Tunhap" . "(tu nhap bieu thuc ben duoi)")
    ("Ganday" . "Bieu thuc dung gan nhat")
    ("Thep20" . "Ky hieu thep duong kinh >= 20: d>=20")
    ("Lay0" . "Doi tuong tren layer 0: layer=0")
    ("Churong" . "Chu rong: loai=TEXT,MTEXT & chu=")
    ("Ngan" . "Doan rat ngan < 1: loai=LINE,LWPOLYLINE,ARC & dai<1")
    ("Mauroi" . "Mau gan cung (khong ByLayer): mau<>256 & mau<>0")
    ("Chuack" . "Ky hieu thep chua gan cau kien: d>0 & ck=")))
(setq *SD:LOCEXP*
  '(("Thep20" . "d>=20") ("Lay0" . "layer=0") ("Churong" . "loai=TEXT,MTEXT & chu=")
    ("Ngan" . "loai=LINE,LWPOLYLINE,ARC & dai<1") ("Mauroi" . "mau<>256 & mau<>0")
    ("Chuack" . "d>0 & ck=")))

(defun c:SDLOC (/ imp mau ex gr ss i e ed res n byl lay f cols line keys v)
  (setq imp (ssget "_I"))
  (sd:begin)
  (if (not (sd:dlg "Loc doi tuong theo dieu kien (SDLOC)"
                   (list (list "note" "Truong: loai layer mau net block chu dai dientich bankinh cao kg att:TAG dyn:TEN ck d sh sl tang" 'note nil)
                         (list "note" "Phep: = <> > < >= <= ~(chua); & = VA, | = HOAC. VD: block=VAN* & att:CS>=5 | d>=20" 'note nil)
                         (list "mau" "Bo loc" 'kw "Tunhap" *SD:LOCMAU*)
                         (list "ex" "Bieu thuc" 'str (cond ((car (sd:loc-hist))) ("layer=SD-THEP* & dai>=1000")) nil '("mau" "Tunhap"))
                         (list "pv" "Pham vi" 'kw (if imp "Hientai" "Tatca")
                               '(("Tatca" . "Toan bo khong gian hien hanh") ("Chon" . "Chon vung tren ban ve") ("Hientai" . "Trong cac doi tuong dang chon (loc tiep)")))
                         (list "lam" "Ket qua" 'kw "Chon"
                               '(("Chon" . "Chon (hien grip) de sua / xoa / copy") ("Dem" . "Chi dem theo layer + loai")
                                 ("Coplap" . "Co lap (an doi tuong khac)") ("Doilayer" . "Chuyen sang layer") ("CSV" . "Xuat danh sach CSV")))
                         (list "lay" "Layer dich" 'str (getvar "CLAYER") nil '("lam" "Doilayer")))))
    (exit))
  (setq mau (sd:v "mau")
        ex  (cond ((= mau "Tunhap") (sd:v "ex")) ((= mau "Ganday") (car (sd:loc-hist))) ((cdr (assoc mau *SD:LOCEXP*)))))
  (setq gr (if ex (sd:loc-parse ex) "chua co bieu thuc"))
  (cond
    ((= (type gr) 'STR) (princ (strcat "\n[SD] Loi bieu thuc: " gr)))
    (t
     (if (= mau "Tunhap") (sd:loc-save ex))
     (setq ss (cond ((= (sd:v "pv") "Hientai") imp)
                    ((= (sd:v "pv") "Chon") (princ "\nChon vung can loc: ") (ssget))
                    (t (ssget "_X" (list (cons 410 (if (= (getvar "CVPORT") 1) (getvar "CTAB") "Model")))))))
     (setq res (ssadd) i 0)
     (if ss
       (repeat (sslength ss)
         (setq e (ssname ss i) ed (entget e) i (1+ i))
         (if (sd:loc-match e ed gr) (ssadd e res))))
     (setq n (sslength res))
     ;; dem theo layer + loai
     (setq i 0)
     (repeat n
       (setq ed (entget (ssname res i)) i (1+ i)
             lay (strcat (cdr (assoc 8 ed)) " | " (cdr (assoc 0 ed))))
       (if (setq f (assoc lay byl)) (setq byl (subst (cons lay (1+ (cdr f))) f byl)) (setq byl (cons (cons lay 1) byl))))
     (setq byl (sd:sort byl '(lambda (a b) (> (cdr a) (cdr b)))))
     (princ (strcat "\n[SD] Bieu thuc: " ex))
     (princ (strcat "\n[SD] Tim thay " (itoa n) " / " (itoa (if ss (sslength ss) 0)) " doi tuong."))
     (setq i 0)
     (foreach x byl (if (< i 15) (princ (strcat "\n  " (car x) " : " (itoa (cdr x))))) (setq i (1+ i)))
     (if (> i 15) (princ (strcat "\n  ... va " (itoa (- i 15)) " nhom khac")))
     (if (> n 0)
       (cond
         ((= (sd:v "lam") "Chon") (setq *SD:LOCSS* res))
         ((= (sd:v "lam") "Coplap") (command "_.ISOLATEOBJECTS" res "") (princ "\n[SD] Bo co lap: UNISOLATEOBJECTS."))
         ((= (sd:v "lam") "Doilayer")
          (setq lay (vl-string-trim " " (sd:v "lay")))
          (if (not (tblsearch "LAYER" lay)) (sd:make-layer lay 7 "Continuous" -3))
          (setq i 0)
          (repeat n (setq ed (entget (ssname res i)) i (1+ i)) (entmod (subst (cons 8 lay) (assoc 8 ed) ed)))
          (princ (strcat "\n[SD] Da chuyen " (itoa n) " doi tuong sang layer " lay ".")))
         ((= (sd:v "lam") "CSV")
          (setq keys (vl-remove-if '(lambda (k) (member k '("loai" "layer"))) (mapcar 'car (apply 'append gr))))
          (setq cols nil) (foreach k keys (if (not (member k cols)) (setq cols (append cols (list k)))))
          (if (setq f (sd:open (setq line (sd:csv-name "_Loc.csv")) "w"))
            (progn
              (write-line (sd:join (append '("Handle" "Loai" "Layer") cols) ",") f)
              (setq i 0)
              (repeat n
                (setq e (ssname res i) ed (entget e) i (1+ i))
                (write-line (sd:join (append (list (cdr (assoc 5 ed)) (cdr (assoc 0 ed)) (sd:cde-q (cdr (assoc 8 ed))))
                                             (mapcar '(lambda (k / v) (setq v (sd:loc-get e ed k))
                                                        (sd:cde-q (cond ((numberp v) (sd:num v)) (v) (""))))
                                                     cols))
                                     ",")
                            f))
              (princ (strcat "\n[SD] Da xuat: " (sd:close f))))))))))
  (sd:finish)
  ;; chon sau khi ket thuc lenh de grip con hien
  (if *SD:LOCSS* (progn (sssetfirst nil *SD:LOCSS*) (setq *SD:LOCSS* nil)))
  (princ))

;;; ==========================================================================
;;;  TIEN ICH VE: tong dien tich, chu giua 2 diem, quan ly layout, kich thuoc ghi tay, thu tu ve theo layer
;;; ==========================================================================

;; ---- SDDIENTICH - dem + tong dien tich theo layer ---------------------------------
(defun c:SDDIENTICH (/ ss i e o a lay rec res tot sk dvm k pt n)
  (sd:begin)
  (if (not (sd:dlg "Tong dien tich (SDDIENTICH)"
                   (list (list "note" "Polyline kin, tron, elip, spline kin, hatch (da tru dao), region; doi tuong ho bi bo qua" 'note nil)
                         (list "dv" "Don vi ban ve" 'kw "mm" '(("mm" . "mm (hien thi m2)") ("m" . "m (giu nguyen)")))
                         (list "nhan" "Gan nhan dien tich tu cap nhat (FIELD) len tung doi tuong" 'tog nil)
                         (list "ghi" "Ghi tong dien tich len ban ve" 'tog t))))
    (exit))
  (setq dvm (= (sd:v "dv") "mm") k (if dvm 1e-6 1.0))
  (princ "\nChon doi tuong can tinh dien tich: ")
  (if (setq ss (ssget '((0 . "LWPOLYLINE,POLYLINE,CIRCLE,ELLIPSE,SPLINE,HATCH,REGION"))))
    (progn
      (setq i 0 tot 0.0 sk 0 n 0)
      (repeat (sslength ss)
        (setq e (ssname ss i) i (1+ i) o (vlax-ename->vla-object e)
              a (if (sd:nl-prop o "Dientich") (sd:prop o 'Area)))
        (if (numberp a)
          (progn
            (setq tot (+ tot a) n (1+ n) lay (cdr (assoc 8 (entget e))))
            (if (setq rec (assoc lay res))
              (setq res (subst (list lay (1+ (cadr rec)) (+ (caddr rec) a)) rec res))
              (setq res (cons (list lay 1 a) res)))
            (if (and (sd:v "nhan") (setq pt (sd:nl-place o "Dientich")))
              (sd:nl-make (car pt) 0.0 (sd:nl-tpl "S = {} m\\U+00B2" (sd:nl-field o "Area" (sd:nl-fmt "Dientich" dvm 2))) (* 2.5 (sd:sc)) nil)))
          (setq sk (1+ sk))))
      (princ "\n----------------------------------------------")
      (foreach r (sd:sort res '(lambda (a b) (< (car a) (car b))))
        (princ (strcat "\n" (car r) ": " (itoa (cadr r)) " doi tuong, S = " (sd:rtos (* k (caddr r)) 3) (if dvm " m2" ""))))
      (princ (strcat "\nTONG: " (itoa n) " doi tuong, S = " (sd:rtos (* k tot) 3) (if dvm " m2" "")
                     (if (> sk 0) (strcat "  (bo qua " (itoa sk) " doi tuong ho / loi)") "")))
      (princ "\n----------------------------------------------")
      (if (sd:v "nhan") (vla-Regen (sd:doc) acActiveViewport))
      (if (and (sd:v "ghi") (setq pt (sd:getpt "\nDiem ghi tong dien tich <Enter bo qua>: " nil)))
        (sd:text pt (strcat "S = " (sd:rtos (* k tot) 2) (if dvm " m\\U+00B2" "")) (* 2.5 (sd:sc)) "L" "SD-CHU"))))
  (sd:finish))

;; ---- SDCHUGIUA - tao / can chu 1 dong giua 2 diem, xoay theo 2 diem -------------
;; Goc doc duoc (chu khong lon nguoc)
(defun sd:read-ang (a)
  (setq a (rem (+ a (* 2 pi)) (* 2 pi)))
  (if (and (> a (+ (/ pi 2) 1e-9)) (<= a (+ (* 1.5 pi) 1e-9))) (- a pi) a))
;; Diem dat chu: trung diem p1 p2, lech vuong goc dz
(defun sd:mid-off (p1 p2 dz / a m)
  (setq a (sd:read-ang (angle p1 p2)) m (mapcar '(lambda (x y) (/ (+ x y) 2.0)) p1 p2))
  (list (polar (list (car m) (cadr m) 0.0) (+ a (/ pi 2)) dz) a))

(defun c:SDCHUGIUA (/ op h dz p1 p2 pm e ed s n)
  (sd:begin)
  (if (not (sd:dlg "Chu giua 2 diem (SDCHUGIUA)"
                   (list (list "op" "Thao tac" 'kw "Tao" '(("Tao" . "Tao chu moi giua 2 diem") ("Canh" . "Can chu co san vao giua 2 diem")))
                         (list "s" "Noi dung chu" 'str (cond (*SD:CGS*) ("TEXT")) nil '("op" "Tao"))
                         (list "h" "Chieu cao chu (mm tren giay)" 'real 2.5)
                         (list "vt" "Vi tri" 'kw "Tren" '(("Tren" . "Phia tren duong noi 2 diem") ("Giua" . "Dung tren duong noi"))))))
    (exit))
  (setq op (sd:v "op") h (* (sd:v "h") (sd:sc)) dz (if (= (sd:v "vt") "Tren") (* 0.9 h) 0.0) n 0 *SD:CGS* (sd:v "s"))
  (while (and (or (= op "Tao")
                  (setq e (car (entsel (strcat "\nChon chu (TEXT) can can <ket thuc>: ")))))
              (or (= op "Tao") (= (cdr (assoc 0 (entget e))) "TEXT")
                  (progn (princ "\n[SD] Chi can duoc TEXT 1 dong.") nil))
              (setq p1 (sd:getpt (if (= op "Tao") "\nDiem thu nhat <ket thuc>: " "\nDiem thu nhat: ") nil))
              (setq p2 (sd:getpt "\nDiem thu hai: " p1)))
    (setq pm (sd:mid-off p1 p2 dz))
    (if (= op "Tao")
      (progn
        (entmake (list '(0 . "TEXT") '(8 . "SD-CHU") (cons 7 (sd:tstyle)) (cons 10 (car pm)) (cons 11 (car pm))
                       (cons 40 h) (cons 1 (sd:v "s")) (cons 50 (cadr pm)) '(72 . 1) '(73 . 2)))
        (setq n (1+ n)))
      (progn
        (setq ed (entget e))
        (foreach g (list (cons 10 (car pm)) (cons 11 (car pm)) (cons 50 (cadr pm)) '(72 . 1) '(73 . 2))
          (setq ed (if (assoc (car g) ed) (subst g (assoc (car g) ed) ed) (append ed (list g)))))
        (entmod ed)
        (setq n (1+ n)))))
  (princ (strcat "\n[SD] " (if (= op "Tao") "Da tao " "Da can ") (itoa n) " chu."))
  (sd:finish))

;; ---- SDLAYOUT - quan ly Layout (hop thoai): mo, len / xuong, sap xep, them, chep, doi ten, doi ten hang loat, xoa
(defun sd:lays (/ r)
  (vlax-for l (vla-get-Layouts (sd:doc)) (if (/= (vla-get-ModelType l) :vlax-true) (setq r (cons l r))))
  (sd:sort r '(lambda (a b) (< (vla-get-TabOrder a) (vla-get-TabOrder b)))))
(defun sd:lay-exists (nm) (not (vl-catch-all-error-p (vl-catch-all-apply 'vla-Item (list (vla-get-Layouts (sd:doc)) nm)))))
(defun sd:lay-order (lst / i) (setq i 0) (foreach l lst (vla-put-TabOrder l (setq i (1+ i)))))

(defun sd:lay-dcl (/ fn f)
  (setq fn (vl-filename-mktemp "sdlay" nil ".dcl"))
  (if (setq f (open fn "w"))
    (progn
      (foreach l '("sdlay : dialog { label = \"Quan ly Layout (SDLAYOUT)\";"
                   "  : row {"
                   "    : list_box { key = \"lst\"; width = 44; height = 20; }"
                   "    : column { fixed_height = true;"
                   "      : button { key = \"mo\"; label = \"Mo layout\"; }"
                   "      : button { key = \"len\"; label = \"Len\"; }"
                   "      : button { key = \"xuong\"; label = \"Xuong\"; }"
                   "      : button { key = \"az\"; label = \"Sap xep A-Z\"; }"
                   "      : button { key = \"moi\"; label = \"Them moi\"; }"
                   "      : button { key = \"chep\"; label = \"Sao chep\"; }"
                   "      : button { key = \"ten\"; label = \"Doi ten\"; }"
                   "      : button { key = \"hl\"; label = \"Doi ten hang loat\"; }"
                   "      : button { key = \"xoa\"; label = \"Xoa\"; }"
                   "    }"
                   "  }"
                   "  : edit_box { key = \"nm\"; label = \"Ten moi / tien to (hang loat):\"; edit_width = 32; }"
                   "  : text { key = \"msg\"; width = 64; }"
                   "  : button { key = \"cancel\"; label = \"Dong\"; is_cancel = true; fixed_width = true; alignment = centered; }"
                   "}")
        (write-line l f))
      (close f)
      fn)))

(defun c:SDLAYOUT (/ doc fn id res lays l nm i act msg tmp)
  (sd:begin)
  (setq doc (sd:doc) fn (sd:lay-dcl) i 0 msg "Chon layout roi bam lenh; nhap dup = mo layout." act t)
  (while act
    (setq lays (sd:lays) i (min i (max 0 (1- (length lays)))) res 0)
    (if (and fn (setq id (load_dialog fn)) (> id 0) (new_dialog "sdlay" id))
      (progn
        (start_list "lst")
        (mapcar 'add_list (mapcar '(lambda (x) (strcat (if (< (vla-get-TabOrder x) 10) "0" "") (itoa (vla-get-TabOrder x)) "   " (vla-get-Name x)
                                                         (if (= (vla-get-Name x) (getvar "CTAB")) "   (dang mo)" "")))
                                  lays))
        (end_list)
        (set_tile "lst" (itoa i))
        (set_tile "nm" (if (nth i lays) (vla-get-Name (nth i lays)) ""))
        (set_tile "msg" msg)
        (action_tile "lst" "(setq *SD:LI* (atoi $value)) (set_tile \"nm\" (vla-get-Name (nth *SD:LI* (sd:lays)))) (if (= $reason 4) (progn (setq *SD:LN* (get_tile \"nm\")) (done_dialog 2)))")
        (foreach b '(("mo" . 2) ("len" . 3) ("xuong" . 4) ("az" . 5) ("moi" . 6) ("chep" . 7) ("ten" . 8) ("hl" . 9) ("xoa" . 10))
          (action_tile (car b) (strcat "(setq *SD:LI* (atoi (get_tile \"lst\")) *SD:LN* (get_tile \"nm\")) (done_dialog " (itoa (cdr b)) ")")))
        (setq res (start_dialog))
        (unload_dialog id))
      (princ "\n[SD] Khong mo duoc hop thoai."))
    (setq i (cond (*SD:LI*) (0)) l (nth i lays) nm (vl-string-trim " " (cond (*SD:LN*) (""))) *SD:LI* nil *SD:LN* nil)
    (cond
      ((< res 2) (setq act nil))
      ((and (null l) (/= res 6)) (setq msg "Ban ve chua co layout: dung Them moi."))
      ((= res 2) (setvar "CTAB" (vla-get-Name l)) (setq act nil))
      ((= res 3) (if (> i 0) (progn (sd:lay-order (append (sd:head (1- i) lays) (list l (nth (1- i) lays)) (cddr (member (nth (1- i) lays) lays))))
                                    (setq i (1- i) msg "Da chuyen len."))))
      ((= res 4) (if (< i (1- (length lays)))
                   (progn (sd:lay-order (append (sd:head i lays) (list (nth (1+ i) lays) l) (cddr (member l lays))))
                          (setq i (1+ i) msg "Da chuyen xuong."))))
      ((= res 5) (sd:lay-order (mapcar '(lambda (k) (nth k lays)) (vl-sort-i (mapcar 'vla-get-Name lays) 'sd:fl<)))
                 (setq msg "Da sap xep theo ten (tu nhien: BV-2 truoc BV-10)."))
      ((= res 6) (setq nm (sd:lo-safe (if (or (= nm "") (sd:lay-exists nm)) (strcat "Layout" (itoa (1+ (length lays)))) nm)))
                 (if (vl-catch-all-error-p (vl-catch-all-apply 'vla-Add (list (vla-get-Layouts doc) nm)))
                   (setq msg (strcat "Khong tao duoc " nm))
                   (setq msg (strcat "Da them " nm) i (length lays))))
      ((= res 7) (setq nm (sd:lo-safe (if (or (= nm "") (sd:lay-exists nm)) (strcat (vla-get-Name l) " (2)") nm)))
                 (command "_.LAYOUT" "_C" (vla-get-Name l) nm)
                 (setq msg (if (sd:lay-exists nm) (strcat "Da sao chep thanh " nm) "Khong sao chep duoc.") i (1- (length (sd:lays)))))
      ((= res 8) (cond ((or (= nm "") (= nm (vla-get-Name l))) (setq msg "Nhap ten moi vao o ben duoi."))
                       ((sd:lay-exists nm) (setq msg (strcat "Da co layout " nm)))
                       ((vl-catch-all-error-p (vl-catch-all-apply 'vla-put-Name (list l (sd:lo-safe nm)))) (setq msg "Ten khong hop le."))
                       (t (setq msg (strcat "Da doi ten thanh " (sd:lo-safe nm))))))
      ((= res 9) (setq tmp 0)
                 (foreach x lays (vl-catch-all-apply 'vla-put-Name (list x (strcat "~sdtmp" (itoa (setq tmp (1+ tmp)))))))
                 (setq tmp 0)
                 (foreach x lays (vla-put-Name x (sd:lo-safe (strcat (if (= nm "") "BV-" nm) (sd:lo-pad (setq tmp (1+ tmp)) (max 2 (strlen (itoa (length lays)))))))))
                 (setq msg (strcat "Da doi ten " (itoa tmp) " layout theo thu tu tab.")))
      ((= res 10) (if (= (vla-get-Name l) (getvar "CTAB")) (setvar "CTAB" "Model"))
                  (setq nm (vla-get-Name l))
                  (setq msg (if (vl-catch-all-error-p (vl-catch-all-apply 'vla-Delete (list l))) (strcat "Khong xoa duoc " nm) (strcat "Da xoa " nm " (U de hoan tac sau khi dong)."))))))
  (if fn (vl-file-delete fn))
  (sd:finish))

;; ---- SDDIMTAY - kich thuoc ghi tay (text override) --------------------------------
;; Kich thuoc ghi de: chu khac rong va khong chua <> (gia tri do)
(defun sd:dim-hand-p (ed / s) (setq s (cdr (assoc 1 ed))) (and s (/= s "") (not (vl-string-search "<>" s))))
;; So trong chu ghi de (bo %%c, tien to chu) -> so hoac nil
(defun sd:dim-num (s / i c r)
  (setq r "" i 1)
  (while (<= i (strlen s))
    (setq c (substr s i 1) i (1+ i))
    (if (or (wcmatch c "#") (and (= c ".") (/= r ""))) (setq r (strcat r c))))
  (if (/= r "") (atof r)))

(defun c:SDDIMTAY (/ op ss i e ed s m v tol sel n nl res xd col)
  (sd:begin)
  (regapp "SD_DIMTAY")
  (if (not (sd:dlg "Kich thuoc ghi tay (SDDIMTAY)"
                   (list (list "note" "Kich thuoc co gia tri go tay (text override) thay cho gia tri do that" 'note nil)
                         (list "op" "Thao tac" 'kw "Danhdau"
                               '(("Danhdau" . "To mau do de nhan biet") ("Bodanhdau" . "Bo to mau (tra mau cu)")
                                 ("Khoiphuc" . "Khoi phuc gia tri do that (xoa ghi de)") ("Chon" . "Chon de xem / sua") ("Xoa" . "Xoa kich thuoc ghi tay")))
                         (list "loc" "Pham vi kich thuoc ghi tay" 'kw "Tatca" '(("Tatca" . "Moi kich thuoc ghi tay") ("Lech" . "Chi khi so ghi lech so do > dung sai")))
                         (list "tol" "Dung sai (don vi ve)" 'real 1.0 nil '("loc" "Lech"))
                         (list "pv" "Pham vi" 'kw "Tatca" '(("Tatca" . "Khong gian hien hanh") ("Chon" . "Chon tren ban ve"))))))
    (exit))
  (setq op (sd:v "op") tol (sd:v "tol") n 0 nl 0)
  (setq ss (if (= (sd:v "pv") "Chon")
             (progn (princ "\nChon kich thuoc: ") (ssget '((0 . "DIMENSION"))))
             (ssget "_X" (list '(0 . "DIMENSION") (cons 410 (if (= (getvar "CVPORT") 1) (getvar "CTAB") "Model")))))
        sel (ssadd) i 0)
  (if ss
    (repeat (sslength ss)
      (setq e (ssname ss i) ed (entget e '("SD_DIMTAY")) i (1+ i))
      (cond
        ((= op "Bodanhdau")
         (if (setq xd (cadr (assoc -3 ed)))
           (progn (setq col (cdr (cadr xd)))
                  (entmod (append (vl-remove (assoc -3 ed) (if (assoc 62 ed) (subst (cons 62 col) (assoc 62 ed) ed) (append ed (list (cons 62 col)))))
                                  (list (list -3 (list "SD_DIMTAY")))))
                  (setq n (1+ n)))))
        ((sd:dim-hand-p ed)
         (setq s (cdr (assoc 1 ed)) m (cdr (assoc 42 ed)) v (sd:dim-num s))
         (if (and v m (> (abs (- v m)) tol)) (setq nl (1+ nl)))
         (if (or (= (sd:v "loc") "Tatca") (null v) (null m) (> (abs (- v m)) tol))
           (progn
             (setq n (1+ n) res (cons (list s m) res))
             (cond
               ((= op "Danhdau")
                (if (not (assoc -3 ed))
                  (entmod (append (if (assoc 62 ed) (subst '(62 . 1) (assoc 62 ed) ed) (append ed '((62 . 1))))
                                  (list (list -3 (list "SD_DIMTAY" (cons 1070 (cond ((cdr (assoc 62 ed))) (256))))))))))
               ((= op "Khoiphuc")
                (setq ed (subst '(1 . "") (assoc 1 ed) ed))
                (if (setq xd (cadr (assoc -3 ed)))
                  (setq ed (append (vl-remove (assoc -3 ed) (if (assoc 62 ed) (subst (cons 62 (cdr (cadr xd))) (assoc 62 ed) ed) ed))
                                   (list (list -3 (list "SD_DIMTAY"))))))
                (entmod ed))
               ((= op "Xoa") (entdel e))
               (t (ssadd e sel)))))))))
  (princ (strcat "\n[SD] " (if ss (itoa (sslength ss)) "0") " kich thuoc; "
                 (cond ((= op "Bodanhdau") (strcat "bo to mau " (itoa n)))
                       (t (strcat (itoa n) " ghi tay" (if (> nl 0) (strcat " (" (itoa nl) " lech so do > " (sd:num tol) ")") "")
                                  (cond ((= op "Danhdau") " -> to do. Bo to: SDDIMTAY -> Bodanhdau.")
                                        ((= op "Khoiphuc") " -> da tra ve gia tri do.")
                                        ((= op "Xoa") " -> da xoa.") (t " -> dang chon.")))))))
  (setq i 0)
  (foreach r (reverse res) (if (< i 10) (princ (strcat "\n  ghi \"" (car r) "\"  do " (if (cadr r) (sd:rtos (cadr r) 1) "?")))) (setq i (1+ i)))
  (sd:finish)
  (if (> (sslength sel) 0) (sssetfirst nil sel))
  (princ))

;; ---- SDTHUTU - thu tu ve theo layer (duoi -> tren) ----------------------------------
(defun c:SDTHUTU (/ lst ss n sp)
  (sd:begin)
  (if (not (sd:dlg "Thu tu ve theo layer (SDTHUTU)"
                   (list (list "note" "Danh sach layer tu DUOI len TREN, cach nhau dau ; (moi muc dung mau * ? ,)" 'note nil)
                         (list "ds" "Thu tu layer" 'str (cond ((getenv "ShopDrawingThuTu"))
                                                               ("SD-HATCH;SD-GACH*;SD-OSAN;SD-BETONG;SD-CF-*;SD-GIAO;SD-KHUAT;SD-THEP*;SD-KICHTHUOC;SD-KYHIEU;SD-CHU")))
                         (list "hatch" "Sau do dua moi hatch xuong duoi cung (HATCHTOBACK)" 'tog nil)
                         (list "chu" "Sau cung dua chu + kich thuoc len tren cung (TEXTTOFRONT)" 'tog t))))
    (exit))
  (setenv "ShopDrawingThuTu" (sd:v "ds"))
  (setq lst (vl-remove "" (mapcar '(lambda (x) (vl-string-trim " " x)) (sd:split (sd:v "ds") ";")))
        sp (if (= (getvar "CVPORT") 1) (getvar "CTAB") "Model") n 0)
  (foreach p lst
    (if (setq ss (ssget "_X" (list (cons 8 p) (cons 410 sp))))
      (progn (command "_.DRAWORDER" ss "" "_F") (setq n (+ n (sslength ss))))))
  (if (sd:v "hatch") (vl-catch-all-apply 'vl-cmdf '("_.HATCHTOBACK")))
  (if (sd:v "chu") (vl-catch-all-apply 'vl-cmdf '("_.TEXTTOFRONT" "_A")))
  (princ (strcat "\n[SD] Da sap thu tu ve " (itoa n) " doi tuong theo " (itoa (length lst)) " muc layer (muc sau nam tren muc truoc)."))
  (sd:finish))

;;; ==========================================================================
;;;  COFFA NHOM (he tam nhom): vach / cot / loi, san, dam + kiem tra + kho
;;;    SDNHOMSET  : chon he (Module 50 kieu Mivan / Kumkang, MEVA AluFix) hoac tu chinh catalogue: tam vach, goc IC / EC / SC,
;;;                 tam san, dam do, dau chong; quy tac ty (theo buoc / theo bang chieu cao tam); ap luc, ty, cay chong cho phep
;;;    SDNHOMVACH : vach / cot / loi tu polyline kin mat be tong (hoac cot b x h, vach L x t): chia tam it nhat, IC / EC,
;;;                 ty, mat dung tung mat to mau theo be rong + so hieu tam (thu tu lap), chu giai, kiem tra ap luc + tai ty
;;;    SDNHOMSAN  : o san: SC chu vi, dam do + dau chong (thao som drophead) + cay chong, tam san; kiem tra tai cay chong
;;;    SDNHOMDAM  : dam: thanh trong / ngoai, day, goc ngoai, cay chong
;;;    SDNHOMKHO  : cong don bang tam moi lan chay (theo ten cau kien) -> tong hop cong trinh; doi chieu kho (CSV ma,SL) -> thieu
;;;  Tam ngoai catalogue danh dau * / -BU (tam bu, gia cong) va to do.
;;; ==========================================================================
(setq *SD:ALDEF*
  '(("MOD" . 50.0) ("WW" . "600,500,450,400,350,300,250,200,150,100") ("WH" . "2400,1800,1500,1200,900,600,300")
    ("IC" . 100.0) ("EC" . 65.0) ("SC" . 100.0) ("SCL" . "1500,1200,900,600,300,200,100")
    ("DW" . "600,500,400,300,200,100") ("DL" . "1200,1100,1000,900,800,700,600") ("BW" . 100.0) ("PHL" . 200.0)
    ("PS" . 1200.0) ("TIEM" . "Buoc") ("TIEB" . "2400:3,1800:2,1500:2,1200:2,900:1,600:1,300:0")
    ("TH" . 600.0) ("TV" . 800.0) ("T0" . 300.0) ("PIN" . 300.0)
    ("PMAX" . 60.0) ("TIECAP" . 40.0) ("PROPCAP" . 15.0) ("LIVE" . 2.5)))
;; He mau: gia tri ghi de len catalogue
(setq *SD:ALPROF*
  '(("Module50" . (("MOD" . 50.0) ("WW" . "600,500,450,400,350,300,250,200,150,100") ("WH" . "2400,1800,1500,1200,900,600,300")
                   ("IC" . 100.0) ("EC" . 65.0) ("SC" . 100.0) ("TIEM" . "Buoc") ("TH" . 600.0) ("TV" . 800.0) ("PMAX" . 60.0)))
    ("AluFix" . (("MOD" . 50.0) ("WW" . "900,750,550,450,400,250") ("WH" . "3500,3000,2700,2500,1500,1350")
                 ("IC" . 200.0) ("EC" . 0.0) ("SC" . 0.0) ("TIEM" . "Bang")
                 ("TIEB" . "3500:4,3000:3,2700:3,2500:3,1500:2,1350:2") ("PMAX" . 50.0)))))
(defun sd:al (k) (sd:cfg (strcat "AL-" k) (cdr (assoc k *SD:ALDEF*))))
(defun sd:al-list (k) (vl-sort (vl-remove 0.0 (mapcar 'atof (sd:split (sd:al k) ","))) '>))
;; So hang ty cua tam cao h theo bang "h:n,..." (gan nhat khong vuot)
(defun sd:al-tierows (h / best)
  (foreach x (sd:split (sd:al "TIEB") ",")
    (setq x (sd:split x ":"))
    (if (and (cadr x) (<= (atof (car x)) (+ h 1.0)) (or (null best) (> (atof (car x)) (car best))))
      (setq best (list (atof (car x)) (atoi (cadr x))))))
  (if best (cadr best) (if (>= h 600.0) 1 0)))

;; Chia doan L bang kich thuoc chuan ws (giam dan, boi so MOD): it tam nhat, uu tien tam lon -> (tam... phan-bu)
(defun sd:al-fill (L ws / u n best rb i k c r w pcs)
  (setq u (sd:al "MOD") n (fix (+ (/ L u) 1e-6)) ws (mapcar '(lambda (x) (fix (+ (/ x u) 0.5))) ws) rb (list (cons 0 nil)) i 0)
  (repeat n
    (setq i (1+ i) best nil)
    (foreach w ws
      (if (and (<= w i) (setq c (nth (1- w) rb)) (or (null best) (< (1+ (car c)) (car best))))
        (setq best (cons (1+ (car c)) w))))
    (setq rb (cons best rb)))
  (setq k 0)
  (while (and (< k n) (null (nth k rb))) (setq k (1+ k)))
  (setq r (- L (* (- n k) u)) i (- n k))
  (while (> i 0)
    (setq c (nth (- n i) rb) w (cdr c) pcs (cons (* w u) pcs) i (- i w)))
  (list (sd:al-sortd pcs) (if (< r 0.5) 0.0 r)))
(defun sd:al-sortd (l) (mapcar '(lambda (k) (nth k l)) (vl-sort-i l '>)))

;; Bang ma tam
(defun sd:al-add (bom code n / o)
  (if (setq o (assoc code bom)) (subst (cons code (+ (cdr o) n)) o bom) (cons (cons code n) bom)))
(defun sd:al-desc (code)
  (cond ((wcmatch code "*-BU*,*`*") "Tam bu / gia cong (ngoai catalogue)")
        ((wcmatch code "W#*") "Tam vach / cot") ((wcmatch code "IC*") "Goc trong") ((wcmatch code "EC*") "Goc ngoai")
        ((wcmatch code "SC*") "Goc san (vach - san)") ((wcmatch code "D#*") "Tam san") ((wcmatch code "MB*") "Dam do san")
        ((wcmatch code "PH*") "Dau chong (thao som)") ((wcmatch code "BS*") "Tam thanh dam") ((wcmatch code "BB*") "Tam day dam")
        ((wcmatch code "PROP*") "Cay chong") ((wcmatch code "TY*") "Ty + ong nhua + bat") ((wcmatch code "PIN*") "Chot + nem")
        (t "")))
(defun sd:al-code (pre a b) (strcat pre (sd:num a) "x" (sd:num b)))
(defun sd:al-sorted (bom) (mapcar '(lambda (k) (nth k bom)) (vl-sort-i (mapcar 'car bom) 'sd:fl<)))

;; Mau theo be rong tam (de nhin luoi tam); tam bu = do
(defun sd:al-color (w / ws i)
  (setq ws (sd:al-list "WW") i (vl-position w ws))
  (if i (nth (rem i 10) '(3 4 5 6 30 140 200 42 92 172)) 1))
(defun sd:col-last (c) (entmod (append (entget (entlast)) (list (cons 62 c)))))

;; Chu giai mau tam tai pt
(defun sd:al-legend (pt sc / y)
  (setq y 0.0)
  (sd:text pt "CH\\U+00DA GI\\U+1EA2I M\\U+00C0U T\\U+1EA4M" (* 2.5 sc) "L" "SD-CHU")
  (foreach w (append (sd:al-list "WW") (list "BU"))
    (setq y (- y (* 6 sc)))
    (sd:rect (sd:p+ pt 0 y) (* 8 sc) (* 4 sc) "SD-CF-VAN")
    (sd:col-last (if (= w "BU") 1 (sd:al-color w)))
    (sd:text (sd:p+ pt (* 10 sc) (+ y (* 2 sc))) (if (= w "BU") "T\\U+1EA5m b\\U+00F9 / gia c\\U+00F4ng (*, -BU)" (strcat "W" (sd:num w))) (* 2.0 sc) "ML" "SD-CHU")))

;; Bang + CSV + luu cong don (ldata "SD" "ALBOM": ((ten . bom) ...))
(defun sd:al-table (pt title bom sc name / rows n fn f all)
  (setq bom (sd:al-sorted bom) n 0)
  (foreach b bom
    (setq n (1+ n) rows (cons (list "R" (list (itoa n) (car b) (sd:al-desc (car b)) (itoa (fix (+ (cdr b) 0.5)))) nil) rows)))
  (sd:table2 pt title '(("STT" 10) ("M\\U+00C3 T\\U+1EA4M" 34) ("LO\\U+1EA0I" 52) ("SL" 14)) (reverse rows) -1 sc)
  (if name
    (progn (setq all (vlax-ldata-get "SD" "ALBOM"))
           (vlax-ldata-put "SD" "ALBOM" (cons (cons name bom) (vl-remove (assoc name all) all)))))
  (if (setq f (sd:open (setq fn (sd:csv-name "_CoffaNhom.csv")) "w"))
    (progn (write-line "STT,Ma tam,Loai,So luong" f)
           (setq n 0)
           (foreach b bom (setq n (1+ n)) (write-line (sd:join (list (itoa n) (car b) (sd:al-desc (car b)) (itoa (fix (+ (cdr b) 0.5)))) ",") f))
           (princ (strcat "\n[SD] Da xuat: " (sd:close f))))))

;; Mat dung 1 mat: luoi tam to mau, so hieu tam (id = tien to, nil = khong), ty theo buoc / bang. Tra ve bom
(defun sd:al-face (o L H pre sc title bom id / fw fh x y ys xs xl p k hs nr)
  (setq fw (sd:al-fill L (sd:al-list "WW")) fh (sd:al-fill H (sd:al-list "WH")) k 0
        hs (append (car fh) (if (> (cadr fh) 0) (list (cadr fh)))))
  (sd:text (sd:p+ o (/ L 2.0) (+ H (* 5 sc))) title (* 2.5 sc) "MC" "SD-CHU")
  (sd:rect o L H "SD-CF-VAN")
  (setq x 0.0)
  (foreach w (append (car fw) (if (> (cadr fw) 0) (list (cadr fw))))
    (setq y 0.0)
    (foreach hh hs
      (setq k (1+ k))
      (sd:rect (sd:p+ o x y) w hh "SD-CF-VAN")
      (sd:col-last (if (and (member w (car fw)) (member hh (car fh))) (sd:al-color w) 1))
      (sd:text (sd:p+ o (+ x (/ w 2.0)) (+ y (/ hh 2.0))) (sd:num w) (* (min 1.8 (/ w sc 12.0)) sc) "MC" "SD-CHU")
      (if id (sd:text (sd:p+ o (+ x (* 0.8 sc)) (+ y (* 1.2 sc))) (strcat id "." (if (< k 10) "0" "") (itoa k)) (* (min 1.2 (/ w sc 16.0)) sc) "L" "SD-CHU"))
      (setq bom (sd:al-add bom (if (member w (car fw)) (strcat (sd:al-code pre w hh) (if (member hh (car fh)) "" "*"))
                                 (sd:al-code (strcat pre "-BU") w hh))
                           1)
            *SD:ALPIN* (+ *SD:ALPIN* (/ (+ w hh) (sd:al "PIN")))
            y (+ y hh)))
    (setq x (+ x w) xs (cons x xs)))
  ;; ty tai khe noi tam doc
  (if (= (sd:al "TIEM") "Bang")
    ;; theo bang: moi khe noi, moi tam trong chong co n hang ty chia deu
    (progn
      (setq y 0.0 ys nil)
      (foreach hh hs
        (setq nr (sd:al-tierows hh) k 0)
        (repeat nr (setq k (1+ k) ys (cons (+ y (* hh (/ (- k 0.5) nr))) ys)))
        (setq y (+ y hh)))
      (foreach x (cdr xs) (foreach y ys (sd:circle (sd:p+ o x y) (* 0.8 sc) "SD-CF-TY") (setq *SD:ALTIE* (1+ *SD:ALTIE*)))))
    (progn
      (setq ys (list (sd:al "T0")))
      (while (<= (+ (car ys) (sd:al "TV")) (- H (sd:al "T0") -1)) (setq ys (cons (+ (car ys) (sd:al "TV")) ys)))
      (setq xl 0.0)
      (foreach x (reverse (cdr xs))
        (if (>= (- x xl) (- (sd:al "TH") 1))
          (progn (setq xl x)
                 (foreach y ys
                   (setq p (sd:p+ o x y))
                   (sd:circle p (* 0.8 sc) "SD-CF-TY")
                   (setq *SD:ALTIE* (1+ *SD:ALTIE*))))))))
  bom)

;; Kiem tra ap luc + tai ty -> danh sach dong ghi chu
(defun sd:al-check-wall (H / p th tv q r)
  (setq p (sd:fw-pressure H t)
        th (if (= (sd:al "TIEM") "Bang") (car (sd:al-list "WW")) (sd:al "TH"))
        tv (if (= (sd:al "TIEM") "Bang") (/ (car (sd:al-list "WH")) (max 1 (sd:al-tierows (car (sd:al-list "WH"))))) (sd:al "TV"))
        q (/ (* p th tv) 1e6))
  (setq r (list (strcat "\\U+00C1p l\\U+1EF1c BT t\\U+01B0\\U+01A1i p = " (sd:rtos p 1) " kN/m\\U+00B2 " (if (<= p (sd:al "PMAX")) "\\U+2264 " "> ") (sd:num (sd:al "PMAX"))
                        " cho ph\\U+00E9p" (if (<= p (sd:al "PMAX")) " - OK" " - V\\U+01AF\\U+1EE2T: gi\\U+1EA3m t\\U+1ED1c \\U+0111\\U+1ED9 \\U+0111\\U+1ED5 / \\U+0111\\U+1ED5 2 \\U+0111\\U+1EE3t"))
                (strcat "T\\U+1EA3i 1 ty \\U+2248 p x " (sd:num th) " x " (sd:rtos tv 0) " = " (sd:rtos q 1) " kN " (if (<= q (sd:al "TIECAP")) "\\U+2264 " "> ")
                        (sd:num (sd:al "TIECAP")) " kN" (if (<= q (sd:al "TIECAP")) " - OK" " - V\\U+01AF\\U+1EE2T: t\\U+0103ng s\\U+1ED1 ty"))))
  (foreach s r (princ (strcat "\n[SD] " s)))
  r)

;; ---- SDNHOMSET
(defun c:SDNHOMSET (/ pr)
  (sd:begin)
  (if (not (sd:dlg "Catalogue coffa nhom (SDNHOMSET)"
                   (append
                     (list (list "prof" "He coffa nhom" 'kw "Giu"
                                 '(("Giu" . "Giu / tu chinh catalogue ben duoi") ("Module50" . "Module 50 (kieu Mivan / Kumkang): W 100-600 x 300-2400")
                                   ("AluFix" . "MEVA AluFix: W 250-900 x 1350-3500, IC 200, ty theo bang, 50 kN/m2"))))
                     (mapcar '(lambda (f) (append (list (car f) (cadr f) (caddr f) (sd:al (car f))) (cdddr f)))
                             '(("MOD" "Module kich thuoc (mm)" real)
                               ("WW" "Tam vach / cot - cac be rong (mm)" str) ("WH" "Tam vach - cac chieu cao (mm)" str)
                               ("IC" "Goc trong IC - canh (mm)" real) ("EC" "Goc ngoai EC - canh (mm, 0 = ghep kep)" real0)
                               ("SC" "Goc san SC - canh (mm, 0 = khong)" real0) ("SCL" "Goc san - cac chieu dai (mm)" str)
                               ("DW" "Tam san - cac be rong (mm)" str) ("DL" "Tam san - cac chieu dai (mm)" str)
                               ("BW" "Dam do san - be rong (mm)" real) ("PHL" "Dau chong - chieu dai (mm)" real)
                               ("PS" "Khoang cach cay chong (mm)" real)
                               ("TIEM" "Bo tri ty" kw (("Buoc" . "Theo buoc ngang / dung") ("Bang" . "Theo bang so hang ty / chieu cao tam")))
                               ("TIEB" "Bang ty: chieu cao tam:so hang, ..." str)
                               ("TH" "Ty - buoc ngang (mm)" real) ("TV" "Ty - buoc dung (mm)" real) ("T0" "Ty - hang dau cach chan (mm)" real)
                               ("PIN" "Chot nem - khoang cach (mm)" real)
                               ("PMAX" "Ap luc be tong cho phep cua tam (kN/m2)" real) ("TIECAP" "Ty - tai cho phep (kN)" real)
                               ("PROPCAP" "Cay chong - tai cho phep (kN)" real) ("LIVE" "Hoat tai thi cong san (kN/m2)" real))))))
    (exit))
  (foreach f *SD:FV* (if (/= (car f) "prof") (sd:cfg-put (strcat "AL-" (car f)) (cdr f))))
  (if (setq pr (cdr (assoc (sd:v "prof") *SD:ALPROF*)))
    (foreach f pr (sd:cfg-put (strcat "AL-" (car f)) (cdr f))))
  (princ (strcat "\n[SD] Da luu catalogue coffa nhom" (if pr (strcat " theo he " (sd:v "prof")) "")
                 ": W " (sd:al "WW") " x " (sd:al "WH") "; IC " (sd:num (sd:al "IC")) ", EC " (sd:num (sd:al "EC"))
                 "; ty " (if (= (sd:al "TIEM") "Bang") (strcat "theo bang " (sd:al "TIEB")) "theo buoc") ". Doi chieu catalogue nha cung cap truoc khi dat hang."))
  (sd:finish))

;; ---- SDNHOMVACH
(defun sd:al-rectpts (o a b) (list (list (car o) (cadr o)) (list (+ (car o) a) (cadr o)) (list (+ (car o) a) (+ (cadr o) b)) (list (car o) (+ (cadr o) b))))

(defun c:SDNHOMVACH (/ nguon name H Hp sc polys ss i o pts n p cv bom x0 y0 bb k a b L r0 r1 fh ic ec ck)
  (sd:begin)
  (if (not (sd:dlg "Coffa nhom vach / cot / loi (SDNHOMVACH)"
                   (list (list "nguon" "Cau kien" 'kw (cond (*SD:ALN*) ("Chon"))
                               '(("Chon" . "Chon polyline kin mat be tong (vach, cot, loi - hinh bat ky)") ("Cot" . "Cot chu nhat b x h") ("Vach" . "Vach thang L x t")))
                         (list "name" "Ten" 'str (cond (*SD:ALNM*) ("V1")))
                         (list "a" "b cot / L vach (mm)" 'real 600.0 nil '("nguon" "Cot" "Vach"))
                         (list "b" "h cot / t vach (mm)" 'real 600.0 nil '("nguon" "Cot" "Vach"))
                         (list "H" "Chieu cao do (san -> day san tren, mm)" 'real (cond (*SD:ALH*) (2900.0)))
                         (list "dinh" "Dinh vach" 'kw "SC" '(("SC" . "Co san phia tren: tru goc san SC") ("Het" . "Do het chieu cao (khong goc san)")))
                         (list "id" "Danh so hieu tam (M1.01...) cho thu tu lap dung" 'tog t)
                         (list "sc" "Ty le ve 1/" 'int 25))))
    (exit))
  (setq nguon (sd:v "nguon") name (sd:v "name") H (sd:v "H") sc (float (sd:v "sc"))
        Hp (- H (if (= (sd:v "dinh") "SC") (sd:al "SC") 0.0)) ic (sd:al "IC") ec (sd:al "EC")
        *SD:ALN* nguon *SD:ALNM* name *SD:ALH* H *SD:ALTIE* 0 *SD:ALPIN* 0.0)
  (cond
    ((= nguon "Chon")
     (princ "\nChon polyline kin mat be tong (vach / cot / loi): ")
     (if (setq ss (ssget '((0 . "LWPOLYLINE") (-4 . "&") (70 . 1))))
       (progn (setq i 0) (repeat (sslength ss) (setq polys (cons (sd:poly-ccw (ssname ss i)) polys) i (1+ i))))))
    ((setq o (sd:getpt "\nDiem chen mat bang (goc trai duoi): " nil))
     (setq pts (sd:al-rectpts o (sd:v "a") (sd:v "b")) polys (list pts))
     (sd:pline (mapcar '(lambda (q) (append q '(0.0))) pts) t "SD-BETONG")))
  (if polys
    (progn
      (setq polys (reverse polys) k 0
            bb (list (apply 'min (mapcar 'car (apply 'append polys))) (apply 'min (mapcar 'cadr (apply 'append polys)))
                     (apply 'max (mapcar 'car (apply 'append polys))) (apply 'max (mapcar 'cadr (apply 'append polys))))
            x0 (+ (caddr bb) (* 40 sc)) y0 (cadr bb))
      (sd:use-dimstyle sc)
      (foreach pts polys
        ;; dinh loi (CCW) = goc ngoai EC; dinh lom = goc trong IC
        (setq cv (mapcar '(lambda (u0 u1 u2) (> (sd:turn u0 u1 u2) 0)) (cons (last pts) pts) pts (append (cdr pts) (list (car pts))))
              n (length pts) i 0)
        (foreach c cv
          (setq fh (sd:al-fill Hp (sd:al-list "WH")))
          (if (or (not c) (> ec 0))
            (foreach hh (append (car fh) (if (> (cadr fh) 0) (list (cadr fh))))
              (setq bom (sd:al-add bom (if c (sd:al-code "EC" ec hh) (sd:al-code "IC" ic hh)) 1))))
          (setq p (nth i pts) i (1+ i))
          (sd:text (append p '(0.0)) (if c "EC" "IC") (* 1.8 sc) "MC" (if c "SD-CF-GONG" "SD-CF-TY")))
        (setq i 0)
        (foreach w (sd:poly-walls pts nil)
          (setq a (car w) b (cadr w) k (1+ k)
                r0 (if (nth i cv) 0.0 ic) r1 (if (nth (rem (1+ i) n) cv) 0.0 ic)
                L (- (cadddr w) r0 r1) i (1+ i))
          ;; mat bang: dai tam ngoai mat be tong + vach chia tam
          (sd:pline (list (polar a (angle a b) r0) (polar b (angle b a) r1) (polar (polar b (angle b a) r1) (caddr w) 65.0) (polar (polar a (angle a b) r0) (caddr w) 65.0)) t "SD-CF-VAN")
          (setq fh (car (sd:al-fill L (sd:al-list "WW"))) p r0)
          (foreach ww fh
            (setq p (+ p ww))
            (if (< p (- (cadddr w) r1 1.0))
              (sd:line (polar a (angle a b) p) (polar (polar a (angle a b) p) (caddr w) 65.0) "SD-CF-VAN")))
          (sd:text (polar (mapcar '(lambda (u v) (/ (+ u v) 2.0)) a b) (caddr w) (+ 65.0 (* 4 sc))) (strcat "M" (itoa k)) (* 2.2 sc) "MC" "SD-CHU")
          (if (> L 1.0)
            (setq bom (sd:al-face (list x0 y0 0.0) L Hp "W" sc (strcat "M\\U+1EB6T M" (itoa k) " - L=" (sd:num L) ", H=" (sd:num Hp)) bom
                                  (if (sd:v "id") (strcat "M" (itoa k))))
                  x0 (+ x0 L (* 25 sc))))))
      (setq bom (sd:al-add bom "TY" (fix (+ (/ *SD:ALTIE* 2.0) 0.5)))
            bom (sd:al-add bom "PIN" (fix (+ (/ *SD:ALPIN* 2.0) 0.5))))
      (sd:text (sd:p+ (list (car bb) (cadr bb) 0.0) 0 (* -14 sc)) (strcat "M\\U+1EB6T B\\U+1EB0NG COFFA NH\\U+00D4M " name) (* 3.0 sc) "L" "SD-CHU")
      ;; kiem tra ap luc + tai ty, ghi duoi mat bang
      (setq ck (sd:al-check-wall H) i 0)
      (foreach s ck (setq i (1+ i)) (sd:text (sd:p+ (list (car bb) (cadr bb) 0.0) 0 (- (* -14 sc) (* 4.5 sc i))) s (* 2.0 sc) "L" "SD-CHU"))
      (sd:al-legend (list x0 (+ y0 Hp (* 6 sc)) 0.0) sc)
      (sd:al-table (list (+ x0 (* 70 sc)) (+ y0 Hp) 0.0) (strcat "B\\U+1EA2NG T\\U+1EA4M COFFA NH\\U+00D4M " name) bom sc name)
      (sd:use-dimstyle *SD:SCALE*)
      (princ (strcat "\n[SD] " name ": " (itoa k) " mat, cao tam " (sd:num Hp) " mm; ty ~" (itoa (fix (+ (/ *SD:ALTIE* 2.0) 0.5)))
                     " bo (xuyen 2 mat); tam do / * / BU = ngoai catalogue. Tong hop + doi chieu kho: SDNHOMKHO.")))
    (princ "\n[SD] Chua co cau kien."))
  (sd:finish))

;; ---- SDNHOMSAN
(defun c:SDNHOMSAN (/ name sc polys ss i pts x1 y1 x2 y2 Lx Ly sch nx ny bw nb bays dlen dl fy x y bom e nph phl seg o k ts q pl)
  (sd:begin)
  (if (not (sd:dlg "Coffa nhom san (SDNHOMSAN)"
                   (list (list "nguon" "O san" 'kw "Chon" '(("Chon" . "Chon polyline kin mep o san (giap dam / vach)") ("Nhap" . "Nhap Lx x Ly")))
                         (list "name" "Ten" 'str "S1")
                         (list "lx" "Lx (mm)" 'real 4200.0 nil '("nguon" "Nhap"))
                         (list "ly" "Ly (mm)" 'real 3600.0 nil '("nguon" "Nhap"))
                         (list "ts" "Day san (mm)" 'real 120.0)
                         (list "sc" "Ty le ve 1/" 'int 50))))
    (exit))
  (setq name (sd:v "name") sc (float (sd:v "sc")) sch (sd:al "SC") bw (sd:al "BW") phl (sd:al "PHL") ts (sd:v "ts"))
  (if (= (sd:v "nguon") "Chon")
    (progn (princ "\nChon polyline kin mep o san: ")
           (if (setq ss (ssget '((0 . "LWPOLYLINE") (-4 . "&") (70 . 1))))
             (progn (setq i 0) (repeat (sslength ss) (setq polys (cons (sd:poly-ccw (ssname ss i)) polys) i (1+ i))))))
    (if (setq o (sd:getpt "\nGoc trai duoi o san: " nil))
      (progn (setq polys (list (sd:al-rectpts o (sd:v "lx") (sd:v "ly"))))
             (sd:pline (mapcar '(lambda (q) (append q '(0.0))) (car polys)) t "SD-BETONG"))))
  (setq k 0)
  (foreach pts polys
    (setq k (1+ k)
          x1 (apply 'min (mapcar 'car pts)) y1 (apply 'min (mapcar 'cadr pts))
          x2 (apply 'max (mapcar 'car pts)) y2 (apply 'max (mapcar 'cadr pts))
          Lx (- x2 x1) Ly (- y2 y1))
    (if (or (/= (length pts) 4) (> (abs (- (abs (sd:parea pts)) (* Lx Ly))) 1.0))
      (princ (strcat "\n[SD] O " (itoa k) " khong phai chu nhat: bo tri theo khung bao " (sd:num Lx) "x" (sd:num Ly) " (kiem tra phan khuyet).")))
    ;; goc san SC theo chu vi
    (if (> sch 0)
      (foreach s (list Lx Lx Ly Ly)
        (setq e (sd:al-fill s (sd:al-list "SCL")))
        (foreach l (car e) (setq bom (sd:al-add bom (sd:al-code "SC" sch l) 1)))
        (if (> (cadr e) 0) (setq bom (sd:al-add bom (sd:al-code "SC-BU" sch (cadr e)) 1)))))
    (if (> sch 0) (progn (sd:rect (list (+ x1 sch) (+ y1 sch) 0.0) (- Lx sch sch) (- Ly sch sch) "SD-CF-GONG") (sd:col-last 2)))
    (setq nx (- Lx sch sch) ny (- Ly sch sch) dl (car (sd:al-list "DL"))
          nb (max 0 (1- (fix (+ (/ (+ nx bw) (+ dl bw)) 0.999999))))
          bays (1+ nb) dlen (/ (- nx (* nb bw)) bays)
          fy (sd:al-fill ny (sd:al-list "DW"))
          nph (1+ (fix (+ (/ (- ny phl) (sd:al "PS")) 0.999999))) seg (/ (- ny (* nph phl)) (max 1 (1- nph))))
    (setq x (+ x1 sch) i 0)
    (repeat bays
      (setq y (+ y1 sch))
      (foreach w (append (car fy) (if (> (cadr fy) 0) (list (cadr fy))))
        (sd:rect (list x y 0.0) dlen w "SD-CF-VAN")
        (sd:col-last (if (and (member w (car fy)) (member (float (fix (+ dlen 0.5))) (sd:al-list "DL"))) (sd:al-color w) 1))
        (sd:text (list (+ x (/ dlen 2.0)) (+ y (/ w 2.0)) 0.0) (strcat (sd:num w) "x" (sd:num (fix (+ dlen 0.5)))) (* (min 1.8 (/ w sc 8.0)) sc) "MC" "SD-CHU")
        (setq bom (sd:al-add bom (if (and (member w (car fy)) (member (float (fix (+ dlen 0.5))) (sd:al-list "DL")))
                                   (sd:al-code "D" w (fix (+ dlen 0.5)))
                                   (strcat (sd:al-code "D" w (fix (+ dlen 0.5))) "*"))
                             1)
              y (+ y w)))
      (setq x (+ x dlen) i (1+ i))
      (if (<= i nb)
        (progn
          (sd:rect (list x (+ y1 sch) 0.0) bw ny "SD-CF-GONG")
          (setq y (+ y1 sch))
          (repeat nph
            (sd:rect (list x y 0.0) bw phl "SD-CF-CHONG")
            (sd:circle (list (+ x (/ bw 2.0)) (+ y (/ phl 2.0)) 0.0) (* 0.8 sc) "SD-CF-CHONG")
            (setq y (+ y phl seg)))
          (setq bom (sd:al-add bom "PH" nph) bom (sd:al-add bom "PROP" nph)
                bom (sd:al-add bom (sd:al-code "MB" bw (fix (+ seg 0.5))) (1- nph))
                x (+ x bw)))))
    ;; kiem tra tai cay chong: (25.t + 0.5 coffa + hoat tai) x dien tich chiu tai 1 cay chong
    (setq q (+ (* 25.0 (/ ts 1000.0)) 0.5 (sd:al "LIVE"))
          pl (* q (/ (* (+ dlen bw) (+ seg phl)) 1e6)))
    (sd:text (list x1 (- y1 (* 10 sc)) 0.0) (strcat "COFFA NH\\U+00D4M S\\U+00C0N " name (if (> (length polys) 1) (strcat "-" (itoa k)) "") " - " (sd:num Lx) "x" (sd:num Ly)
                                                ": " (itoa bays) " kho\\U+1EA3ng t\\U+1EA5m d\\U+00E0i " (sd:num (fix (+ dlen 0.5))) ", " (itoa nb) " d\\U+1EA7m \\U+0111\\U+1EE1, ch\\U+1ED1ng @"
                                                (sd:num (fix (+ seg phl 0.5)))) (* 2.5 sc) "L" "SD-CHU")
    (sd:text (list x1 (- y1 (* 15 sc)) 0.0)
             (strcat "T\\U+1EA3i 1 c\\U+00E2y ch\\U+1ED1ng \\U+2248 " (sd:rtos q 2) " kN/m\\U+00B2 x " (sd:rtos (/ (* (+ dlen bw) (+ seg phl)) 1e6) 2) " m\\U+00B2 = " (sd:rtos pl 1) " kN "
                     (if (<= pl (sd:al "PROPCAP")) (strcat "\\U+2264 " (sd:num (sd:al "PROPCAP")) " kN - OK") (strcat "> " (sd:num (sd:al "PROPCAP")) " kN - V\\U+01AF\\U+1EE2T: gi\\U+1EA3m b\\U+01B0\\U+1EDBc ch\\U+1ED1ng")))
             (* 2.0 sc) "L" "SD-CHU")
    (sd:text (list x1 (- y1 (* 19.5 sc)) 0.0) "Th\\U+00E1o s\\U+1EDBm: h\\U+1EA1 t\\U+1EA5m s\\U+00E0n + d\\U+1EA7m \\U+0111\\U+1EE1, GI\\U+1EEE \\U+0111\\U+1EA7u ch\\U+1ED1ng + c\\U+00E2y ch\\U+1ED1ng \\U+0111\\U+1EBFn khi b\\U+00EA t\\U+00F4ng \\U+0111\\U+1EE7 c\\U+01B0\\U+1EDDng \\U+0111\\U+1ED9 (ch\\U+1ED1ng l\\U+1EA1i theo ch\\U+1EC9 d\\U+1EABn)."
             (* 2.0 sc) "L" "SD-CHU")
    (princ (strcat "\n[SD] O " (itoa k) ": tai 1 cay chong ~" (sd:rtos pl 1) " kN (cho phep " (sd:num (sd:al "PROPCAP")) " kN).")))
  (if polys
    (if (setq o (sd:getpt "\nDiem chen bang tam (goc trai tren): " nil))
      (sd:al-table o (strcat "B\\U+1EA2NG T\\U+1EA4M COFFA NH\\U+00D4M S\\U+00C0N " name) bom sc name)))
  (sd:finish))

;; ---- SDNHOMDAM
(defun c:SDNHOMDAM (/ name b h ln t1 bien n sc hs hso o bom e x)
  (sd:begin)
  (if (not (sd:dlg "Coffa nhom dam (SDNHOMDAM)"
                   (list (list "name" "Ten dam" 'str "D1")
                         (list "b" "Be rong dam b (mm)" 'real 220.0) (list "h" "Chieu cao dam h (mm)" 'real 500.0)
                         (list "ln" "Nhip thong thuy Ln (mm)" 'real 5700.0) (list "t" "Day san (mm)" 'real 120.0)
                         (list "bien" "Dam bien (thanh ngoai cao het h)" 'tog nil)
                         (list "n" "So dam giong nhau" 'int 1) (list "sc" "Ty le ve 1/" 'int 25))))
    (exit))
  (setq name (sd:v "name") b (sd:v "b") h (sd:v "h") ln (sd:v "ln") t1 (sd:v "t") bien (sd:v "bien") n (sd:v "n") sc (float (sd:v "sc"))
        hs (max 100.0 (- h t1 (sd:al "SC"))) hso (if bien h hs) *SD:ALTIE* 0 *SD:ALPIN* 0.0)
  (if (setq o (sd:getpt "\nDiem chen mat dung thanh dam (goc trai duoi): " nil))
    (progn
      (sd:use-dimstyle sc)
      (setq bom (sd:al-face o ln hs "BS" sc (strcat "TH\\U+00C0NH TRONG D\\U+1EA6M " name " - Ln=" (sd:num ln) ", cao " (sd:num hs)) nil "T"))
      (setq bom (sd:al-face (sd:p+ o 0 (+ hs (* 16 sc))) ln hso "BS" sc (strcat "TH\\U+00C0NH NGO\\U+00C0I D\\U+1EA6M " name (if bien " (d\\U+1EA7m bi\\U+00EAn)" "") ", cao " (sd:num hso)) bom "N"))
      (setq e (sd:al-fill ln (sd:al-list "WW")) x 0.0)
      (foreach l (append (car e) (if (> (cadr e) 0) (list (cadr e))))
        (sd:rect (sd:p+ o x (- (+ b (* 8 sc)))) l b "SD-CF-VAN")
        (sd:col-last (if (member l (car e)) (sd:al-color l) 1))
        (setq bom (sd:al-add bom (if (member l (car e)) (sd:al-code "BB" b l) (sd:al-code "BB-BU" b l)) 1) x (+ x l)))
      (sd:text (sd:p+ o 0 (- (+ b (* 12 sc)))) (strcat "\\U+0110\\U+00C1Y D\\U+1EA6M " name " (r\\U+1ED9ng " (sd:num b) ")") (* 2.2 sc) "L" "SD-CHU")
      (if (> (sd:al "EC") 0)
        (progn (setq e (sd:al-fill ln (sd:al-list "SCL")))
               (foreach l (car e) (setq bom (sd:al-add bom (sd:al-code "EC" (sd:al "EC") l) 2)))))
      (setq bom (sd:al-add bom "PROP" (max 1 (1- (fix (+ (/ ln (sd:al "PS")) 0.999999)))))
            bom (sd:al-add bom "PIN" (fix (+ (/ *SD:ALPIN* 2.0) 0.5))))
      (if (> n 1) (setq bom (mapcar '(lambda (q) (cons (car q) (* n (cdr q)))) bom)))
      (sd:al-table (sd:p+ o (+ ln (* 30 sc)) (+ hs hso (* 16 sc))) (strcat "B\\U+1EA2NG T\\U+1EA4M COFFA NH\\U+00D4M D\\U+1EA6M " name (if (> n 1) (strcat " (x" (itoa n) ")") "")) bom sc name)
      (sd:use-dimstyle *SD:SCALE*)))
  (sd:finish))

;; ---- SDNHOMKHO - tong hop cong trinh + doi chieu kho
(defun sd:al-readstock (fn / f ln x r)
  (if (setq f (sd:open fn "r"))
    (progn
      (while (setq ln (read-line f))
        (setq x (sd:split (vl-string-trim " \t\"" ln) ","))
        (if (and (cadr x) (distof (vl-string-trim " \"" (cadr x)) 2))
          (setq r (sd:al-add r (strcase (vl-string-trim " \"" (car x))) (atof (vl-string-trim " \"" (cadr x)))))))
      (sd:close f)))
  r)

(defun c:SDNHOMKHO (/ op all tot fn stock rows n need have pt nm)
  (sd:begin)
  (setq all (vlax-ldata-get "SD" "ALBOM"))
  (if (not (sd:dlg "Tong hop coffa nhom + doi chieu kho (SDNHOMKHO)"
                   (list (list "note" (strcat "Da luu bang tam cua " (itoa (length all)) " cau kien: " (if all (sd:join (mapcar 'car all) ", ") "(chua co)")) 'note nil)
                         (list "op" "Thao tac" 'kw "Tonghop"
                               '(("Tonghop" . "Tong hop tat ca cau kien -> bang + CSV") ("Kho" . "Doi chieu kho (CSV: ma,so luong) -> bang thieu")
                                 ("Xoa" . "Xoa du lieu da luu")))
                         (list "n" "So dot / so tang lap lai (nhan so luong)" 'int 1 nil '("op" "Tonghop" "Kho")))))
    (exit))
  (setq op (sd:v "op"))
  (cond
    ((= op "Xoa") (vlax-ldata-delete "SD" "ALBOM") (princ "\n[SD] Da xoa du lieu bang tam coffa nhom da luu."))
    ((null all) (princ "\n[SD] Chua co bang tam nao: chay SDNHOMVACH / SDNHOMSAN / SDNHOMDAM truoc."))
    (t
     (foreach c all (foreach b (cdr c) (setq tot (sd:al-add tot (car b) (* (sd:v "n") (cdr b))))))
     (setq tot (sd:al-sorted tot))
     (if (= op "Tonghop")
       (if (setq pt (sd:getpt "\nDiem chen bang tong hop: " nil))
         (sd:al-table pt (strcat "T\\U+1ED4NG H\\U+1EE2P COFFA NH\\U+00D4M (" (itoa (length all)) " c\\U+1EA5u ki\\U+1EC7n" (if (> (sd:v "n") 1) (strcat " x " (itoa (sd:v "n"))) "") ")") tot (sd:sc) nil))
       (progn
         (setq fn (getfiled "File kho coffa nhom (CSV: ma tam, so luong)" (getvar "DWGPREFIX") "csv" 8))
         (if (and fn (setq stock (sd:al-readstock fn)))
           (progn
             (setq n 0)
             (foreach b tot
               (setq nm (car b) need (cdr b) have (cond ((cdr (assoc (strcase nm) stock))) (0.0)) n (1+ n)
                     rows (cons (list "R" (list (itoa n) nm (itoa (fix (+ need 0.5))) (itoa (fix (+ have 0.5)))
                                                (cond ((wcmatch nm "*-BU*,*`*") "GIA C\\U+00D4NG")
                                                      ((> need have) (strcat "THI\\U+1EBEU " (itoa (fix (+ (- need have) 0.5)))))
                                                      ("\\U+0110\\U+1EE6")))
                                      nil)
                                rows)))
             (princ (strcat "\n[SD] Doi chieu " (itoa n) " ma tam voi kho " fn "."))
             (if (setq pt (sd:getpt "\nDiem chen bang doi chieu kho: " nil))
               (sd:table2 pt "\\U+0110\\U+1ED0I CHI\\U+1EBEU KHO COFFA NH\\U+00D4M" '(("STT" 10) ("M\\U+00C3 T\\U+1EA4M" 34) ("C\\U+1EA6N" 14) ("KHO" 14) ("K\\U+1EBET QU\\U+1EA2" 28)) (reverse rows) -1 (sd:sc))))
           (princ "\n[SD] Khong doc duoc file kho (dong: ma tam,so luong)."))))))
  (sd:finish))

;;; --------------------------------------------------------------------------
;;;  SDRAITAM - Rai panel / da lat theo kho (Tiling Algorithm)
;;;    Che do Panel: tam tieu chuan (lon nhat) rai tu goc X, Y nho nhat cua tung o; phan thieu (mep bien) chia
;;;                  bang tam di hinh trong kho (it tam nhat, tam lon truoc), con thua = go (layer INFILL-TIMBER)
;;;    Che do Da    : vien lat nguyen + vien cat o mep, danh so theo thu tu lat, huong van da (tiep noi /
;;;                  doi guong / xoay 4 chieu); vien mang du lieu SD_TILE nen SDGACHTK / SDDATHO / SDGIACONG dung duoc
;;; --------------------------------------------------------------------------
(defun sd:gcd (a b / r) (while (> b 0) (setq r (rem a b) a b b r)) a)

;; "600x1200:10, 400x1200" -> ((600.0 1200.0 10) (400.0 1200.0 0)); so luong 0 / bo trong = khong han che
(defun sd:rt-parse (s / r x d q)
  (foreach it (sd:split (strcase s) ",")
    (setq x (sd:split it ":") q (if (cadr x) (atoi (cadr x)) 0)
          d (sd:split (vl-string-translate "*" "X" (car x)) "X"))
    (if (and (cadr d) (> (atof (car d)) 0.0) (> (atof (cadr d)) 0.0))
      (setq r (cons (list (atof (car d)) (atof (cadr d)) q) r))))
  (reverse r))

(defun sd:rt-code (a b) (strcat "P" (sd:num (min a b)) "x" (sd:num (max a b))))

;; Kho -> moi tam co ca 2 chieu quay (trung kich thuoc thi giu mot)
(defun sd:rt-orient (stk / r)
  (foreach s stk
    (if (not (vl-some '(lambda (x) (and (equal (car x) (car s) 0.5) (equal (cadr x) (cadr s) 0.5))) r))
      (setq r (cons s r)))
    (if (and (> (abs (- (car s) (cadr s))) 0.5)
             (not (vl-some '(lambda (x) (and (equal (car x) (cadr s) 0.5) (equal (cadr x) (car s) 0.5))) r)))
      (setq r (cons (list (cadr s) (car s) (caddr s)) r))))
  (reverse r))

(defun sd:rt-used (used code) (cond ((cdr (assoc code used))) (0)))
(defun sd:rt-bump (used code / o)
  (if (setq o (assoc code used)) (subst (cons code (1+ (cdr o))) o used) (cons (cons code 1) used)))
;; So tam con lai cua kho s (khong han che = 1e9)
(defun sd:rt-left (s used)
  (if (<= (caddr s) 0) 1e9 (- (caddr s) (sd:rt-used used (sd:rt-code (car s) (cadr s))))))

;; Chia doan L (mm) bang cac be rong ws: it tam nhat, uu tien tam lon, phan du la go -> (tam... phan-du)
(defun sd:rt-fill1 (L ws / u n wu rb i best c k w pcs cov lf)
  (setq ws (vl-sort (mapcar '(lambda (x) (fix (+ x 0.5))) ws) '>) u 0)
  (foreach w ws (setq u (sd:gcd (max u w) (min u w))))
  (cond
    ((or (null ws) (< u 1)) (list nil L))
    ((> (fix (/ (+ L 1e-6) u)) 1500)
     (setq lf L)
     (foreach w ws (while (<= w (+ lf 1e-6)) (setq pcs (cons (float w) pcs) lf (- lf w))))
     (list (sd:al-sortd pcs) lf))
    (t
     (setq n (fix (/ (+ L 1e-6) u)) wu (mapcar '(lambda (x) (/ x u)) ws) rb (list (cons 0 nil)) i 0)
     (repeat n
       (setq i (1+ i) best nil)
       (foreach w wu
         (if (and (<= w i) (setq c (nth (1- w) rb)) (or (null best) (< (1+ (car c)) (car best))))
           (setq best (cons (1+ (car c)) w))))
       (setq rb (cons best rb)))
     (setq k 0)
     (while (and (< k n) (null (nth k rb))) (setq k (1+ k)))
     (setq i (- n k) cov (* i u))
     (while (> i 0)
       (setq c (nth (- n i) rb) w (cdr c) pcs (cons (float (* w u)) pcs) i (- i w)))
     (list (sd:al-sortd pcs) (- L cov)))))

(defun sd:rt-shift (lst dx dy) (mapcar '(lambda (r) (list (+ (car r) dx) (+ (cadr r) dy) (caddr r) (cadddr r))) lst))
(defun sd:rt-swap (r) (list (cadr r) (car r) (cadddr r) (caddr r)))
(defun sd:rt-tarea (r) (apply '+ (cons 0.0 (mapcar '(lambda (x) (* (caddr x) (cadddr x))) (cadr r)))))

;; Lap day o chu nhat w x h (goc trai duoi = 0,0) theo hang: hang cao nhat vua o, chia be rong bang tam cung chieu cao,
;; phan du be rong / chieu cao de quy; khong tam nao vua -> go.
;; stk = kho da co ca 2 chieu quay; used = so tam da dung. Tra ve (tam go used) voi tam / go = (x y rong cao)
(defun sd:rt-row (w h stk used / ex cand hh r ok x pan n pw sub rest cnt)
  (cond
    ((or (< w 1.0) (< h 1.0)) (list nil nil used))
    ((setq ex (vl-some '(lambda (s) (if (and (equal (car s) w 1.0) (equal (cadr s) h 1.0) (> (sd:rt-left s used) 0)) s)) stk))
     (list (list (list 0.0 0.0 w h)) nil (sd:rt-bump used (sd:rt-code (car ex) (cadr ex)))))
    (t
     (setq cand (vl-remove-if-not '(lambda (s) (and (<= (cadr s) (+ h 1.0)) (> (sd:rt-left s used) 0))) stk))
     (if (null cand)
       (list nil (list (list 0.0 0.0 w h)) used)
       (progn
         (setq hh (apply 'max (mapcar 'cadr cand))
               cand (vl-remove-if-not '(lambda (s) (equal (cadr s) hh 1.0)) cand)
               ok nil)
         (while (not ok)
           (setq r (sd:rt-fill1 w (mapcar 'car cand)) ok t)
           (foreach s cand
             (setq n (length (vl-remove-if-not '(lambda (v) (equal v (car s) 1.0)) (car r))))
             (if (and ok (> n (sd:rt-left s used)))
               (setq cand (vl-remove s cand) ok nil))))
         (if (null (car r))
           ;; khong tam nao vua be rong: bo nhom chieu cao nay roi thu lai
           (sd:rt-row w h (vl-remove-if '(lambda (s) (equal (cadr s) hh 1.0)) stk) used)
           (progn
             (setq x 0.0)
             (foreach pw (car r)
               (setq pan (cons (list x 0.0 pw hh) pan) x (+ x pw) used (sd:rt-bump used (sd:rt-code pw hh))))
             (setq pan (reverse pan))
             (if (> (- w x) 1.0)
               (progn (setq sub (sd:rt-row (- w x) hh stk used))
                      (setq pan (append pan (sd:rt-shift (car sub) x 0.0)) cnt (sd:rt-shift (cadr sub) x 0.0) used (caddr sub))))
             (setq rest (- h hh))
             (if (> rest 1.0)
               (progn (setq sub (sd:rt-row w rest stk used))
                      (setq pan (append pan (sd:rt-shift (car sub) 0.0 hh)) cnt (append cnt (sd:rt-shift (cadr sub) 0.0 hh)) used (caddr sub))))
             (list pan cnt used))))))))

;; Chon cach lap day (theo hang hoac theo cot) it go nhat
(defun sd:rt-fit (w h stk used / a b)
  (setq a (sd:rt-row w h stk used)
        b (sd:rt-row h w (mapcar '(lambda (s) (list (cadr s) (car s) (caddr s))) stk) used)
        b (list (mapcar 'sd:rt-swap (car b)) (mapcar 'sd:rt-swap (cadr b)) (caddr b)))
  (if (or (< (sd:rt-tarea b) (- (sd:rt-tarea a) 1.0))
          (and (<= (abs (- (sd:rt-tarea b) (sd:rt-tarea a))) 1.0) (< (length (car b)) (length (car a)))))
    b a))

;; Huong van da cua vien (i, j): (so-lan-xoay-90 lat-ngang lat-doc)
(defun sd:rt-vein (van i j)
  (cond ((= van "Tiepnoi") (list 0 nil nil))
        ((= van "Doiguong") (list 0 (= (rem i 2) 1) (= (rem j 2) 1)))
        ((= van "Xoay4") (list (+ (* 2 (rem j 2)) (rem i 2)) nil nil))
        ((= van "Ngaunhien") (list (rem (+ (* i 3) (* j 5)) 4) (= (rem (+ i j j) 2) 1) (= (rem (+ i i j) 3) 0)))))

(defun sd:rt-vpts (vd cx cy w h / r p u v t1)
  (foreach p '((0.15 0.15) (0.40 0.52) (0.58 0.44) (0.85 0.85))
    (setq u (car p) v (cadr p))
    (repeat (car vd) (setq t1 (- 1.0 v) v u u t1))
    (if (cadr vd) (setq u (- 1.0 u)))
    (if (caddr vd) (setq v (- 1.0 v)))
    (setq r (cons (list (+ cx (* u w)) (+ cy (* v h))) r)))
  (reverse r))

(defun sd:rt-color (code stk0 / i r1)
  (setq i 0 r1 nil)
  (foreach s stk0 (if (= (sd:rt-code (car s) (cadr s)) code) (setq r1 i)) (setq i (1+ i)))
  (if r1 (nth (rem r1 8) '(3 4 5 6 30 140 200 92)) 1))

;; Cat vien (cs) voi region R: (dien-tich ents toa-do-dinh). ents tren layer lay; nil neu ngoai vung
(defun sd:rt-clip (rg cs lay / e tr cp pa ents vp)
  (sd:pline cs t lay)
  (setq e (entlast) tr (sd:region e))
  (entdel e)
  (if tr
    (progn
      (setq cp (vla-Copy rg))
      (vla-Boolean cp 1 tr)
      (setq pa (vla-get-Area cp))
      (if (< pa 1.0)
        (progn (vla-Delete cp) nil)
        (progn
          (setq ents (sd:region->ents cp lay))
          (foreach x ents
            (if (= (cdr (assoc 0 (entget x))) "LWPOLYLINE")
              (setq vp (append vp (sd:curve-pts x)))))   ;; lay mau ca cung tron de bbox / trong tam dung
          (if vp
            (list pa ents vp)
            (progn (foreach x ents (if (entget x) (entdel x))) nil)))))))

(defun sd:rt-poly-of (e / pts) (setq pts (sd:curve-pts e)) (list e pts (abs (sd:area pts))))

;; Mau van da khuyen nghi theo file .pat: (ten ti-le mau nen). mau = so ACI hoac (r g b); nen = ACI hoac nil
(setq *SD:VANDA*
  '(("Platinus" 1.2 253 252) ("DaSocDua" 0.4 (88 103 115) nil) ("ViaLactea" 1.5 7 250)
    ("DaVanGoXam" 0.75 8 nil) ("DaVanGoCo" 1.5 32 nil)))
(defun sd:vp-pre (nm) (cond ((assoc nm *SD:VANDA*)) (t (list nm 1.0 7 nil))))

(defun sd:vp-color (h col / tc)
  (if (listp col)
    (progn (setq tc (vla-get-TrueColor h)) (vla-SetRGB tc (car col) (cadr col) (caddr col)) (vla-put-TrueColor h tc))
    (vla-put-Color h col)))

;; Hatch van da (nen + van tu file .pat) tren cac bien ents. Tra ve nil neu khong tao duoc (thieu file .pat)
(defun sd:vp-hatch (ents nm sc ang org col bg / ms h r)
  (setq ms (sd:ms))
  (if bg
    (vl-catch-all-apply
      '(lambda ()
         (setq h (vla-AddHatch ms 1 "SOLID" :vlax-true))
         (vla-AppendOuterLoop h (sd:objarr (mapcar 'vlax-ename->vla-object ents)))
         (vla-put-Color h bg) (vla-put-Layer h "SD-GACH-VAN") (vla-Evaluate h))
      nil))
  (setq h nil
        r (vl-catch-all-apply
            '(lambda ()
               (setq h (vla-AddHatch ms 2 nm :vlax-true))
               (vla-AppendOuterLoop h (sd:objarr (mapcar 'vlax-ename->vla-object ents)))
               (vla-put-PatternScale h sc)
               (vla-put-PatternAngle h (* pi (/ ang 180.0)))
               (vla-put-Origin h (vlax-make-variant (vlax-safearray-fill (vlax-make-safearray vlax-vbDouble '(0 . 1)) (list (float (car org)) (float (cadr org))))))
               (vla-put-Layer h "SD-GACH-VAN")
               (sd:vp-color h col)
               (vla-Evaluate h))
            nil))
  (if (vl-catch-all-error-p r)
    (progn
      (if h (vl-catch-all-apply 'vla-Delete (list h)))
      (if (not *SD:VPWARN*)
        (progn (setq *SD:VPWARN* t)
               (princ (strcat "\n[SD] Khong tao duoc hatch '" nm "': " (vl-catch-all-error-message r)
                              "\n     Chep file " nm ".pat vao thu muc dist (da co trong Support Path sau SDMENU) roi chay lai.")))
        nil)
      nil)
    t))

;; Goc xoay hatch xap xi theo huong van (hatch khong lat guong duoc)
(defun sd:rt-vang (vd)
  (if vd (+ (* 90 (car vd)) (if (and (cadr vd) (caddr vd)) 180 (if (or (cadr vd) (caddr vd)) 90 0))) 0))

;; Hatch 1 vien: Tiepnoi / khong ve van -> goc luoi chung (van chay lien tuc qua cac vien); kieu khac -> goc tung vien
(defun sd:rt-vh (ents nm sc van vd cx cy ox oy / pre)
  (setq pre (sd:vp-pre nm))
  (foreach e ents
    (if (= (cdr (assoc 0 (entget e))) "LWPOLYLINE")
      (sd:vp-hatch (list e) nm sc (+ (sd:rt-vang vd) (cond (*SD:RTAOFF*) (0.0))) (if (member van '("Tiepnoi" "Khong")) (list ox oy) (list cx cy)) (nth 2 pre) (nth 3 pre)))))

(defun c:SDVANDA (/ ss i e pts bb xs ys flt vph vps van vpc vd ii jj ox oy n)
  (sd:begin)
  (setq *SD:RTAOFF* 0.0)
  (if (not (sd:dlg "Hatch van da len vien (SDVANDA)"
                   (list (list "vp" "Pattern van da" 'kw (cond (*SD:VPH*) ("Platinus"))
                               '(("Platinus" . "Platinus - nen xam sang, van toi") ("DaSocDua" . "Da Soc Dua 300x600") ("ViaLactea" . "Via Lactea - nen den")
                                 ("DaVanGoXam" . "Da Van Go Xam") ("DaVanGoCo" . "Da Van Go Co") ("Khac" . "Ten pattern khac (nhap ben duoi)")))
                         (list "vpn" "Ten pattern khac (file .pat trong Support Path)" 'str "" nil '("vp" "Khac"))
                         (list "vsc" "Ti le hatch (0 = khuyen nghi theo pattern)" 'real0 0.0)
                         (list "van" "Huong van" 'kw (cond (*SD:RTVAN*) ("Tiepnoi"))
                               '(("Tiepnoi" . "Tiep noi (van chay lien tuc)") ("Doiguong" . "Doi guong") ("Xoay4" . "Xoay 4 chieu") ("Ngaunhien" . "Ngau nhien"))))))
    (exit))
  (setq vph (sd:v "vp") van (sd:v "van") *SD:VPH* vph *SD:RTVAN* van)
  (if (= vph "Khac") (setq vph (sd:v "vpn")))
  (setq vpc (sd:vp-pre vph) vps (if (> (sd:v "vsc") 0.0) (sd:v "vsc") (cadr vpc))
        flt '((0 . "LWPOLYLINE") (8 . "SD-GACH,SD-GACH-CAT") (-4 . "&") (70 . 1)))
  (princ "\nChon cac vien can hatch van <Enter = tat ca vien SD-GACH / SD-GACH-CAT>: ")
  (setq ss (ssget flt))
  (if (null ss) (setq ss (ssget "_X" flt)))
  (if (null ss)
    (princ "\n[SD] Khong co vien nao (layer SD-GACH / SD-GACH-CAT).")
    (progn
      (setq i 0)
      (repeat (sslength ss)
        (setq e (ssname ss i) i (1+ i) bb (sd:bbox (sd:curve-pts e)))
        (setq pts (cons (list e (caar bb) (cadar bb)) pts)
              xs (cons (fix (+ 0.5 (caar bb))) xs) ys (cons (fix (+ 0.5 (cadar bb))) ys)))
      (setq xs (vl-sort xs '<) ys (vl-sort ys '<) ox (car xs) oy (car ys) n 0)
      (foreach p pts
        (setq ii (vl-position (fix (+ 0.5 (cadr p))) xs) jj (vl-position (fix (+ 0.5 (caddr p))) ys)
              vd (sd:rt-vein van ii jj))
        (if (sd:rt-vh (list (car p)) vph vps van vd (cadr p) (caddr p) (float ox) (float oy)) (setq n (1+ n))))
      (princ (strcat "\n[SD] Da hatch van '" vph "' cho " (itoa n) " / " (itoa (length pts)) " vien (layer SD-GACH-VAN)."))))
  (sd:finish))

;; ---- Xep vien vao tam da tho (shelf packing, cho phep xoay 90 do), nhieu tam ----
;; items = ((id rong cao) ...). Tra ve (placements so-tam); placement = (id tam x y rong cao xoay), tam = nil neu khong vua
(defun sd:lset (lst i v / r k)
  (setq k 0)
  (foreach x lst (setq r (cons (if (= k i) v x) r) k (1+ k)))
  (reverse r))

(defun sd:nest (items SW SH trim kerf rotok) (sd:nest2 items SW SH trim kerf rotok t))
;; sortp = nil: xep dung thu tu items (van lien tiep theo thu tu lat); t: lon truoc (it hao)
;; sortp: t = lon truoc; nil = dung thu tu, best-fit; "SEQ" = lien tiep: vien sau nam ngay sau vien truoc tren cung hang (van chay lien tuc)
(defun sd:nest2 (items SW SH trim kerf rotok sortp / uw uh slabs pl best o cw ch si slab j shf xn ys cost lasts seq)
  (setq uw (- SW (* 2.0 trim)) uh (- SH (* 2.0 trim)) seq (= sortp "SEQ"))
  (foreach it (if (eq sortp t) (sd:sort items '(lambda (a b) (> (max (cadr a) (caddr a)) (max (cadr b) (caddr b))))) items)
    (setq best nil)
    (foreach o (if rotok (list nil t) (list nil))
      (setq cw (if o (caddr it) (cadr it)) ch (if o (cadr it) (caddr it)))
      (if (and (<= cw (+ uw 1e-6)) (<= ch (+ uh 1e-6)))
        (progn
          (setq si 0)
          (foreach slab slabs
            (setq j 0)
            (foreach shf slab
              (setq xn (+ (caddr shf) (if (> (caddr shf) 0.0) kerf 0.0)))
              (if (and (>= (cadr shf) (- ch 1e-6)) (<= (+ xn cw) (+ uw 1e-6))
                       (or (not seq) (and (= si (1- (length slabs))) (= j (1- (length slab))))))
                (progn
                  (setq cost (+ (* 10.0 (- (cadr shf) ch)) (/ (- uw xn cw) 10.0)))
                  (if (or (null best) (< cost (car best)))
                    (setq best (list cost si j o cw ch xn (car shf) nil)))))
              (setq j (1+ j)))
            (setq lasts (last slab) ys (+ (car lasts) (cadr lasts) kerf))
            (if (and (<= (+ ys ch) (+ uh 1e-6)) (or (not seq) (= si (1- (length slabs)))))
              (progn
                (setq cost (+ 10000.0 ch (/ (- uw cw) 10.0)))
                (if (or (null best) (< cost (car best)))
                  (setq best (list cost si -1 o cw ch 0.0 ys nil)))))
            (setq si (1+ si)))
          (setq cost (+ 1e6 ch))
          (if (or (null best) (< cost (car best)))
            (setq best (list cost (length slabs) -1 o cw ch 0.0 0.0 t))))))
    (if best
      (progn
        (setq si (nth 1 best) j (nth 2 best) cw (nth 4 best) ch (nth 5 best) xn (nth 6 best) ys (nth 7 best))
        (cond ((nth 8 best) (setq slabs (append slabs (list (list (list ys ch (+ xn cw)))))))
              ((< j 0) (setq slabs (sd:lset slabs si (append (nth si slabs) (list (list ys ch (+ xn cw)))))))
              (t (setq shf (nth j (nth si slabs))
                       slabs (sd:lset slabs si (sd:lset (nth si slabs) j (list (car shf) (cadr shf) (+ xn cw)))))))
        (setq pl (cons (list (car it) si (+ trim xn) (+ trim ys) cw ch (nth 3 best)) pl)))
      (setq pl (cons (list (car it) nil nil nil nil nil nil) pl))))
  (list (reverse pl) (length slabs)))

;; Ban sao tam da tho (anh) dung kich thuoc that SW x SH, goc xoay 0: (doi-tuong goc-x goc-y)
(defun sd:img-master (e SW SH / c o f wd ht)
  (setq c (vla-Copy (vlax-ename->vla-object e)))
  (if (> (abs (vla-get-Rotation c)) 1e-6) (vla-put-Rotation c 0.0))
  (setq o (vlax-get c 'Origin) wd (vla-get-Width c) ht (vla-get-Height c))
  (if (> (abs (- (/ wd ht) (/ SW SH))) (* 0.02 (/ SW SH)))
    (princ (strcat "\n[SD] Ti le anh (" (sd:num wd) " x " (sd:num ht) ") lech ti le tam that (" (sd:num SW) " x " (sd:num SH)
                   "): vien cat se lech neu anh bi cat vien hoac keo gian.")))
  (vla-ScaleEntity c (vlax-3d-point (car o) (cadr o) 0.0) (/ SW wd))
  (list c (car o) (cadr o)))

;; Cat 1 vien tu anh tam: copy anh -> xoay (neu xep xoay) -> doi ve dung vi tri vien -> IMAGECLIP
;; pl = placement; (tx ty tw th) khung bao vien tren ban ve; pts = da giac (nil = chu nhat)
(defun sd:img-piece (mst pl tx ty tw th pts / cp ox oy cs cd e)
  (setq ox (cadr mst) oy (caddr mst)
        cs (list (+ ox (nth 2 pl) (/ (nth 4 pl) 2.0)) (+ oy (nth 3 pl) (/ (nth 5 pl) 2.0)) 0.0)
        cd (list (+ tx (/ tw 2.0)) (+ ty (/ th 2.0)) 0.0)
        cp (vla-Copy (car mst)))
  (if (nth 6 pl) (vla-Rotate cp (vlax-3d-point cs) (/ pi 2.0)))
  (vla-Move cp (vlax-3d-point cs) (vlax-3d-point cd))
  (vla-put-Layer cp "SD-GACH-ANH")
  (setq e (vlax-vla-object->ename cp))
  (if (and pts (> (length pts) 2))
    (progn
      (command "_.IMAGECLIP" e "_D")
      (command "_.IMAGECLIP" e "_N" "_P")
      (foreach q pts (command (trans (list (car q) (cadr q) 0.0) 0 1)))
      (command ""))
    (progn (command "_.IMAGECLIP" e "_D")
           (command "_.IMAGECLIP" e "_N" "_R" (trans (list tx ty 0.0) 0 1) (trans (list (+ tx tw) (+ ty th) 0.0) 0 1))))
  e)

;; So do cat tam da (ve tai pt): khung tam + vien da xep, so hieu vien
;;; ---- So do cat tam da: vien = to xanh la + so hieu + kich thuoc; vun = to xam + kich thuoc; duong cat = do, balloon so thu tu cat ----
(defun sd:dg-layers ()
  (sd:make-layer "SD-NEST-TAM" 7 "Continuous" 50)
  (sd:make-layer "SD-NEST-LE" 8 "DASHED" 13)
  (sd:make-layer "SD-NEST-VIEN" 3 "Continuous" 35)
  (sd:make-layer "SD-NEST-VUN" 9 "Continuous" 13)
  (sd:make-layer "SD-NEST-TO" 9 "Continuous" 13)
  (sd:make-layer "SD-DUONG-CAT" 1 "Continuous" 25)
  (sd:make-layer "SD-NEST-CHU" 7 "Continuous" 18))

;; To mau dac hinh chu nhat (hatch SOLID, trong suot ~70%): thu nhieu cach ghi de chay duoc tren moi ban AutoCAD
(defun sd:dg-fill (x y w h col lay / base tail pts)
  (setq pts (list (list 10 x y) (list 10 (+ x w) y) (list 10 (+ x w) (+ y h)) (list 10 x (+ y h)))
        base (list '(0 . "HATCH") '(100 . "AcDbEntity") (cons 8 lay) (cons 62 col))
        tail (list '(100 . "AcDbHatch") '(10 0.0 0.0 0.0) '(210 0.0 0.0 1.0) '(2 . "SOLID") '(70 . 1) '(71 . 0) '(91 . 1)))
  (or (entmake (append base (list (cons 440 33554508)) tail (list '(92 . 7) '(72 . 0) '(73 . 1) '(93 . 4)) pts (list '(97 . 0) '(75 . 0) '(76 . 1) '(98 . 0))))
      (entmake (append base tail (list '(92 . 7) '(72 . 0) '(73 . 1) '(93 . 4)) pts (list '(97 . 0) '(75 . 0) '(76 . 1) '(98 . 0))))
      (entmake (append base tail (list '(92 . 3) '(72 . 0) '(73 . 1) '(93 . 4)) pts (list '(97 . 0) '(75 . 0) '(76 . 1) '(98 . 0))))))

;; Chu 1 dong co mau + goc xoay (rad)
(defun sd:dg-text (pt str h j lay col ang / h72 v73)
  (setq h72 (cond ((wcmatch j "*C") 1) ((wcmatch j "*R") 2) (t 0))
        v73 (cond ((wcmatch j "M?") 2) ((wcmatch j "T?") 3) (t 0)))
  (entmake (list '(0 . "TEXT") (cons 8 lay) (cons 62 col) (cons 7 (sd:tstyle)) (cons 10 pt)
                 (cons 11 pt) (cons 40 h) (cons 1 str) (cons 50 ang) (cons 72 h72) (cons 73 v73))))

;; Chu 1 dong vua o w x h: ngang, hoac xoay 90 do neu o cao hon rong nhieu; hmax = cao toi da, hmin = nho nhat con doc duoc; tra ve (cao goc) hoac nil
(defun sd:dg-fit (str w h hmax hmin / n hh a)
  (setq n (max 1 (strlen str))
        hh (min hmax (* 0.85 h) (/ (* 0.92 w) (* 0.75 n))))
  (if (>= hh hmin) (setq a (list hh 0.0)))
  (if (> h (* 1.5 w))
    (progn
      (setq hh (min hmax (* 0.85 w) (/ (* 0.92 h) (* 0.75 n))))
      (if (and (>= hh hmin) (or (null a) (> hh (car a)))) (setq a (list hh (/ pi 2.0))))))
  a)

;; Nhan vien trong o: dong 1 = so hieu (to), dong 2 = kich thuoc (nho, neu con cho)
(defun sd:dg-tile-label (id w h cx cy sc / s2 f1 th1 ang aw ah th2 gap d1 d2 ux uy)
  (setq s2 (strcat (sd:rtos w 0) "x" (sd:rtos h 0))
        f1 (sd:dg-fit id w h (* 2.4 sc) (* 0.9 sc)))
  (if f1
    (progn
      (setq th1 (car f1) ang (cadr f1)
            aw (if (= ang 0.0) w h) ah (if (= ang 0.0) h w)
            th2 (min (* 0.62 th1) (/ (* 0.92 aw) (* 0.75 (strlen s2))))
            gap (* 0.35 th1) ux (- (sin ang)) uy (cos ang))
      (if (and (>= th2 (* 0.7 sc)) (>= ah (+ th1 gap (* 1.3 th2))))
        (setq d1 (/ (+ th2 gap) 2.0) d2 (- (/ (+ th1 gap) 2.0))
              d1 (+ d1 0.0))
        (setq d1 0.0 th2 nil))
      (sd:dg-text (list (+ cx (* ux d1)) (+ cy (* uy d1)) 0.0) id th1 "MC" "SD-NEST-CHU" 7 ang)
      (if th2
        (sd:dg-text (list (+ cx (* ux d2)) (+ cy (* uy d2)) 0.0) s2 th2 "MC" "SD-NEST-CHU" 2 ang)))))

;; Ve so do cat cho nsl tam: khung tam (net day) + le xen (net dut) + vien (to xanh) + vun (to xam) + duong cat (do, balloon thu tu)
;; cuts / remn = nil khi chi ve vi tri xep
(defun sd:dg-draw (pls nsl SW SH pt sc cuts remn / k x0 y0 pl q ct n a b r trim used nt nr nc lay1 gx f dx dy)
  (sd:dg-layers)
  (setq trim (cond (*SD:ITRIM*) (0.0)) r (* 1.3 sc) y0 (cadr pt) k 0
        dx (+ SW (max 300.0 (* 8.0 sc))))
  (repeat nsl
    (setq x0 (+ (car pt) (* k dx)) used 0.0 nt 0 nr 0 nc 0)
    ;; 1) to mau nen: vun (xam) roi vien (xanh) - ve truoc de net / chu nam tren
    (foreach q (vl-remove-if-not '(lambda (r2) (= (car r2) k)) remn)
      (setq nr (1+ nr))
      (sd:dg-fill (+ x0 (nth 1 q)) (+ y0 (nth 2 q)) (nth 3 q) (nth 4 q) 9 "SD-NEST-TO"))
    (foreach pl pls
      (if (equal (cadr pl) k)
        (progn (setq nt (1+ nt) used (+ used (* (nth 4 pl) (nth 5 pl))))
               (sd:dg-fill (+ x0 (nth 2 pl)) (+ y0 (nth 3 pl)) (nth 4 pl) (nth 5 pl) 3 "SD-NEST-TO"))))
    ;; 2) khung tam + le xen
    (sd:rect (list x0 y0 0.0) SW SH "SD-NEST-TAM")
    (if (and (> trim 0.5) (< (* 2.0 trim) (min SW SH)))
      (sd:rect (list (+ x0 trim) (+ y0 trim) 0.0) (- SW (* 2.0 trim)) (- SH (* 2.0 trim)) "SD-NEST-LE"))
    ;; 3) net vien va vun
    (foreach q (vl-remove-if-not '(lambda (r2) (= (car r2) k)) remn)
      (sd:rect (list (+ x0 (nth 1 q)) (+ y0 (nth 2 q)) 0.0) (nth 3 q) (nth 4 q) "SD-NEST-VUN"))
    (foreach pl pls
      (if (equal (cadr pl) k)
        (sd:rect (list (+ x0 (nth 2 pl)) (+ y0 (nth 3 pl)) 0.0) (nth 4 pl) (nth 5 pl) "SD-NEST-VIEN")))
    ;; 4) duong cat do + balloon thu tu o dau net (khong de len giua net cho khoi che chu)
    (setq n 0)
    (foreach ct (sd:cut-seq (vl-remove-if-not '(lambda (c) (= (car c) k)) cuts))
      (setq n (1+ n) nc n
            a (list (+ x0 (nth 1 ct)) (+ y0 (nth 2 ct)) 0.0)
            b (list (+ x0 (nth 3 ct)) (+ y0 (nth 4 ct)) 0.0))
      (sd:line a b "SD-DUONG-CAT")
      (sd:circle a r "SD-DUONG-CAT")
      (sd:dg-text a (itoa n) (* 1.25 sc) "MC" "SD-DUONG-CAT" 1 0.0))
    ;; 5) chu: so hieu + kich thuoc vien, kich thuoc vun (chi ghi khi vua o)
    (foreach pl pls
      (if (equal (cadr pl) k)
        (sd:dg-tile-label (car pl) (nth 4 pl) (nth 5 pl)
                          (+ x0 (nth 2 pl) (/ (nth 4 pl) 2.0)) (+ y0 (nth 3 pl) (/ (nth 5 pl) 2.0)) sc)))
    (foreach q (vl-remove-if-not '(lambda (r2) (= (car r2) k)) remn)
      (if (setq f (sd:dg-fit (strcat "VUN " (sd:rtos (nth 3 q) 0) "x" (sd:rtos (nth 4 q) 0)) (nth 3 q) (nth 4 q) (* 1.5 sc) (* 0.8 sc)))
        (sd:dg-text (list (+ x0 (nth 1 q) (/ (nth 3 q) 2.0)) (+ y0 (nth 2 q) (/ (nth 4 q) 2.0)) 0.0)
                    (strcat "VUN " (sd:rtos (nth 3 q) 0) "x" (sd:rtos (nth 4 q) 0)) (car f) "MC" "SD-NEST-CHU" 7 (cadr f))))
    ;; 6) tieu de + tom tat
    (sd:dg-text (list (+ x0 (/ SW 2.0)) (+ y0 SH (* 5.5 sc)) 0.0) (strcat "TAM DA " (itoa (1+ k))) (* 3.0 sc) "MC" "SD-NEST-CHU" 7 0.0)
    (sd:dg-text (list (+ x0 (/ SW 2.0)) (+ y0 SH (* 2.2 sc)) 0.0)
                (strcat (sd:rtos SW 0) " x " (sd:rtos SH 0) " mm  |  " (itoa nt) " vien  |  dung " (sd:rtos (* 100.0 (/ used (* SW SH))) 1) " %"
                        (if cuts (strcat "  |  " (itoa nc) " duong cat") "")
                        (if remn (strcat "  |  " (itoa nr) " vun") ""))
                (* 1.7 sc) "MC" "SD-NEST-CHU" 7 0.0)
    (setq k (1+ k)))
  ;; chu giai (1 lan, duoi tam dau)
  (setq gx (car pt) y0 (- (cadr pt) (* 4.0 sc)))
  (sd:dg-fill gx (- y0 (* 2.0 sc)) (* 3.0 sc) (* 2.0 sc) 3 "SD-NEST-TO")
  (sd:rect (list gx (- y0 (* 2.0 sc)) 0.0) (* 3.0 sc) (* 2.0 sc) "SD-NEST-VIEN")
  (sd:dg-text (list (+ gx (* 4.0 sc)) (- y0 sc) 0.0) "VIEN CAT (so hieu T.. + kich thuoc dai x rong)" (* 1.5 sc) "ML" "SD-NEST-CHU" 7 0.0)
  (if remn
    (progn
      (setq y0 (- y0 (* 3.2 sc)))
      (sd:dg-fill gx (- y0 (* 2.0 sc)) (* 3.0 sc) (* 2.0 sc) 9 "SD-NEST-TO")
      (sd:rect (list gx (- y0 (* 2.0 sc)) 0.0) (* 3.0 sc) (* 2.0 sc) "SD-NEST-VUN")
      (sd:dg-text (list (+ gx (* 4.0 sc)) (- y0 sc) 0.0) "VUN / PHE LIEU GIU LAI (khong dung lam vien)" (* 1.5 sc) "ML" "SD-NEST-CHU" 7 0.0)))
  (if cuts
    (progn
      (setq y0 (- y0 (* 3.2 sc)))
      (sd:line (list gx (- y0 sc) 0.0) (list (+ gx (* 3.0 sc)) (- y0 sc) 0.0) "SD-DUONG-CAT")
      (sd:circle (list gx (- y0 sc) 0.0) r "SD-DUONG-CAT")
      (sd:dg-text (list gx (- y0 sc) 0.0) "1" (* 1.25 sc) "MC" "SD-DUONG-CAT" 1 0.0)
      (sd:dg-text (list (+ gx (* 4.0 sc)) (- y0 sc) 0.0) "DUONG CAT: so trong balloon = thu tu cat (cat tach lon truoc, manh nho sau cung)" (* 1.5 sc) "ML" "SD-NEST-CHU" 1 0.0)))
  (if (> trim 0.5)
    (progn
      (setq y0 (- y0 (* 3.2 sc)))
      (sd:line (list gx (- y0 sc) 0.0) (list (+ gx (* 3.0 sc)) (- y0 sc) 0.0) "SD-NEST-LE")
      (sd:dg-text (list (+ gx (* 4.0 sc)) (- y0 sc) 0.0) (strcat "LE XEN BIEN " (sd:rtos trim 0) " mm (khong dung)") (* 1.5 sc) "ML" "SD-NEST-CHU" 8 0.0))))

(defun sd:img-diagram (pls nsl SW SH pt sc) (sd:dg-draw pls nsl SW SH pt sc nil nil))

;; Khung vien: goc canh dai nhat (rad) + kich thuoc trong khung do (tw dai theo goc, th) + tam vien (toa do that)
(defun sd:tile-frame (pts / a b ang la best lp x0 y0 x1 y1 cl)
  (setq a (last pts))
  (foreach b pts
    (setq la (distance a b))
    (if (or (null best) (> la (car best))) (setq best (list la (angle a b))))
    (setq a b))
  (setq ang (cond (*SD:IFRAME*) ((cadr best))) ; *SD:IFRAME*: luoi rai co goc xac dinh -> moi vien dung chung khung cua luoi (van song song)
        lp (mapcar '(lambda (q) (sd:rot (list (car q) (cadr q)) (- ang))) pts)
        x0 (apply 'min (mapcar 'car lp)) x1 (apply 'max (mapcar 'car lp))
        y0 (apply 'min (mapcar 'cadr lp)) y1 (apply 'max (mapcar 'cadr lp))
        cl (sd:rot (list (/ (+ x0 x1) 2.0) (/ (+ y0 y1) 2.0)) ang))
  (list ang (- x1 x0) (- y1 y0) cl))

;; Dat 1 vien tu anh: copy anh -> xoay (goc nen + 90 neu xep xoay) -> dua tam manh anh ve tam vien -> IMAGECLIP da giac theo vien
(defun sd:img-place (mst pl base cw pts / cp cs e)
  (setq cs (list (+ (cadr mst) (nth 2 pl) (/ (nth 4 pl) 2.0)) (+ (caddr mst) (nth 3 pl) (/ (nth 5 pl) 2.0)) 0.0)
        cp (vla-Copy (car mst)))
  (vla-Rotate cp (vlax-3d-point cs) (+ base (if (nth 6 pl) (/ pi 2.0) 0.0)))
  (vla-Move cp (vlax-3d-point cs) (vlax-3d-point (list (car cw) (cadr cw) 0.0)))
  (vla-put-Layer cp "SD-GACH-ANH")
  (setq e (vlax-vla-object->ename cp))
  (command "_.IMAGECLIP" e "_D")   ;; copy mang theo duong cat cu cua anh goc: xoa truoc, neu khong AutoCAD hoi "Delete old boundary?" va nuot sai doi so
  (command "_.IMAGECLIP" e "_N" "_P")
  (foreach q pts (command (trans (list (car q) (cadr q) 0.0) 0 1)))
  (command "")
  ;; nho tam vien de SDMOANH tu ghep anh voi polyline vien sau khi chinh bien
  (vl-catch-all-apply 'sd:put-xd
    (list e (list -3 (list "SD_ANH" (cons 1040 (float (car cw))) (cons 1040 (float (cadr cw)))
                           ;; goc xoay anh so voi canh dai vien (99 = luoi chung, khong tu xoay lai)
                           (cons 1040 (if *SD:IFRAME* 99.0 (rem (- (+ base (if (nth 6 pl) (/ pi 2.0) 0.0)) (car (sd:tile-frame pts))) (* 2.0 pi))))))))
  e)

;; Thu tu chay doc theo duong vien: bat dau tu vien trai nhat, moi buoc di sang vien gan nhat chua di (van chay lien tuc quanh vien)
(defun sd:tile-chain (tiles / cur r rest best d)
  (setq rest tiles
        cur (car (sd:sort tiles '(lambda (a b) (if (equal (car (nth 5 a)) (car (nth 5 b)) 1.0)
                                                 (< (cadr (nth 5 a)) (cadr (nth 5 b)))
                                                 (< (car (nth 5 a)) (car (nth 5 b))))))))
  (while cur
    (setq r (cons (cons 0 cur) r) rest (vl-remove cur rest) best nil)
    (foreach x rest
      (setq d (distance (nth 5 cur) (nth 5 x)))
      (if (or (null best) (< d (car best))) (setq best (list d x))))
    (setq cur (cadr best)))
  (reverse r))

;; Thu tu lat ngoang nghoeo: hang (theo y) tu duoi len, hang chan trai -> phai, hang le phai -> trai. tiles = ((id pts ang tw th cw) ...)
(defun sd:tile-order (tiles / rh rows)
  (setq rh (max 1.0 (apply 'min (mapcar '(lambda (r) (min (nth 3 r) (nth 4 r))) tiles))))
  (setq tiles (mapcar '(lambda (r) (cons (fix (+ 0.5 (/ (cadr (nth 5 r)) rh))) r)) tiles))
  (sd:sort tiles '(lambda (a b)
                    (if (= (car a) (car b))
                      (if (= (rem (car a) 2) 0)
                        (< (car (nth 6 a)) (car (nth 6 b)))
                        (> (car (nth 6 a)) (car (nth 6 b))))
                      (< (car a) (car b))))))

(defun c:SDANHDA () (sd:begin) (setq *SD:IFRAME* nil) (sd:anhda nil) (sd:finish))

;; Cat anh da vao cac vien: els = danh sach ename polyline (nil = hoi quet chon). Dung cho SDANHDA va SDGACH (khai bao chung 1 hop thoai)
;; ---- Xep THEO THU TU (van lien tuc) nhung van cat xuyen va lap cho trong, tung tam mot ----
;; Moi tam chi lay tu win vien dau chua xep (cua so); win = 1 la dung thu tu tuyet doi, lon hon thi vien nho phia sau lap vao cho trong con lai.
;; Thu 4 cach cham diem / tach o, chon cach xep duoc nhieu dien tich nhat vao tam do. Tra ve nhu sd:nest-g1
(defun sd:take (lst n / r)
  (while (and lst (> n 0)) (setq r (cons (car lst) r) lst (cdr lst) n (1- n)))
  (reverse r))

(defun sd:nw-slab (part SW SH trim kerf rotok vun / best bs v res a)
  (foreach v '((0 1) (2 1) (0 2) (0 0))
    (setq res (sd:nest-g1 part SW SH trim kerf rotok vun (car v) (cadr v))
          a (apply '+ (mapcar '(lambda (p) (if (and (cadr p) (= (cadr p) 0)) (* (nth 4 p) (nth 5 p)) 0.0)) (car res))))
    (if (or (null bs) (> a bs)) (setq bs a best res)))
  best)

(defun sd:nest-w (items SW SH trim kerf rotok vun win / rest n res spill out cuts remn k ids c r)
  (setq rest items k 0 win (max 1 win))
  (while rest
    (setq n (min win (length rest)) res nil)
    (while (not res)
      (setq res (sd:nw-slab (sd:take rest n) SW SH trim kerf rotok vun)
            spill (vl-some '(lambda (p) (and (cadr p) (> (cadr p) 0))) (car res)))
      (if (and (not spill) (< n (length rest)))
        (setq n (min (length rest) (+ n win)) res nil)))
    (setq ids nil)
    (foreach p (car res)
      (cond ((null (cadr p)) (setq out (cons p out) ids (cons (car p) ids)))
            ((= (cadr p) 0) (setq out (cons (cons (car p) (cons k (cddr p))) out) ids (cons (car p) ids)))))
    (foreach c (caddr res) (if (= (car c) 0) (setq cuts (cons (cons k (cdr c)) cuts))))
    (foreach r (cadddr res) (if (= (car r) 0) (setq remn (cons (cons k (cdr r)) remn))))
    (setq rest (vl-remove-if '(lambda (it) (member (car it) ids)) rest) k (1+ k)))
  (list (reverse out) k (reverse cuts) (reverse remn)))

;;; --------------------------------------------------------------------------
;;;  SDTUDONG - Che do tu dong cho ca phien: sua bien vien (grip, stretch, move...) xong thi anh IMAGECLIP tu cat lai theo bien moi
;;;  Theo doi chung ca ban ve (khong can chon vien), nho trang thai Bat / Tat trong registry nen tu bat khi nap ShopDrawing.lsp
;;; --------------------------------------------------------------------------
(defun sd:ud-lay-p (lay) (member (strcase lay) '("SD-GACH" "SD-GACH-CAT" "SD-GACH-VIEN" "SD-GACH-DOC")))

;; Ghi nho polyline vien vua bi sua (chi doc tenh chat nhe; viec nang lam sau khi lenh ket thuc)
(defun sd:ud-dbmod (rx args / obj h)
  (if (and (not *SD:RXBUSY*) args)
    (vl-catch-all-apply
      '(lambda ()
         (setq obj (car args))
         (if (= (type obj) 'ENAME) (setq obj (vlax-ename->vla-object obj)))
         (if (and (= (type obj) 'VLA-OBJECT) (not (vlax-erased-p obj))
                  (= (vla-get-ObjectName obj) "AcDbPolyline") (sd:ud-lay-p (vla-get-Layer obj)))
           (progn (setq h (vla-get-Handle obj))
                  (if (not (member h *SD:RXPEND*)) (setq *SD:RXPEND* (cons h *SD:RXPEND*))))))
      nil)))

;; ---- Lien ket vien <-> anh (khong phu thuoc vi tri hien tai): anh di theo vien khi MOVE / ROTATE, chi cat lai khi bien doi hinh ----
;; *SD:RXMAP* = ((ma-vien ma-anh da-giac goc-anh goc-xoay-anh) ...), lap lai sau cac lenh SD tao / doi vien + anh
(defun sd:ud-adiff (a b / d)
  (setq d (rem (- a b) (* 2.0 pi)))
  (cond ((> d pi) (- d (* 2.0 pi))) ((< d (- pi)) (+ d (* 2.0 pi))) (t d)))

;; Da giac b co phai la da giac a chi tinh tien + xoay (cung thu tu dinh)? Tra ve (tam-cu tam-moi goc-xoay) hoac nil
(defun sd:ud-rigid (a b tol / n c0 c1 th ok i p)
  (if (and a b (= (length a) (length b)) (> (length a) 2))
    (progn
      (setq n (float (length a))
            c0 (list (/ (apply '+ (mapcar 'car a)) n) (/ (apply '+ (mapcar 'cadr a)) n))
            c1 (list (/ (apply '+ (mapcar 'car b)) n) (/ (apply '+ (mapcar 'cadr b)) n))
            th (if (> (distance c0 (car a)) 1e-6)
                 (- (angle c1 (car b)) (angle c0 (car a)))
                 (- (angle (car b) (cadr b)) (angle (car a) (cadr a))))
            ok t i 0)
      (while (and ok (< i (length a)))
        (setq p (polar c1 (+ (angle c0 (nth i a)) th) (distance c0 (nth i a))))
        (if (> (distance p (nth i b)) tol) (setq ok nil))
        (setq i (1+ i)))
      (if ok (list c0 c1 th)))))

;; Anh dung tam vien nam trong da giac (hoac gan nhat trong ban kinh): il = ((ma-anh ename cx cy) ...), bb = (x0 y0 x1 y1)
(defun sd:ud-pick (pts bb il / cx cy rad r best d)
  (setq cx (/ (apply '+ (mapcar 'car pts)) (float (length pts)))
        cy (/ (apply '+ (mapcar 'cadr pts)) (float (length pts)))
        rad (apply 'max (mapcar '(lambda (q) (distance (list cx cy) q)) pts)))
  (foreach im il
    (if (and (null r) (<= (car bb) (nth 2 im) (caddr bb)) (<= (cadr bb) (nth 3 im) (cadddr bb))
             (sd:inpoly (list (nth 2 im) (nth 3 im)) pts))
      (setq r im))
    (setq d (distance (list cx cy) (list (nth 2 im) (nth 3 im))))
    (if (and (<= d (+ rad 50.0)) (or (null best) (< d (car best)))) (setq best (cons d im))))
  (cond (r) ((cdr best))))

;; Ghi nho cap vien - anh va hinh hoc hien tai cua anh
(defun sd:ud-mapset (h im pts / g)
  (setq g (sd:im-geom im)
        *SD:RXMAP* (cons (list h (cdr (assoc 5 (entget im))) pts (car g) (cadr g))
                         (vl-remove (assoc h *SD:RXMAP*) *SD:RXMAP*))))

;; Trang thai anh so voi luc ghi nho: FOLLOW = anh chua di (dich theo vien), SKIP = anh da di cung vien (vd chon ca anh khi MOVE), OTHER = anh bi sua rieng
(defun sd:ud-img-state (im ent rg / g o a e)
  (setq g (sd:im-geom im) o (car g) a (cadr g)
        e (polar (cadr rg) (+ (angle (car rg) (nth 3 ent)) (caddr rg)) (distance (car rg) (nth 3 ent))))
  (cond ((and (< (distance o (nth 3 ent)) 0.05) (< (abs (sd:ud-adiff a (nth 4 ent))) 1e-5)) 'FOLLOW)
        ((and (< (distance o e) 0.05) (< (abs (sd:ud-adiff a (+ (nth 4 ent) (caddr rg)))) 1e-5)) 'SKIP)
        (t 'OTHER)))

;; Dich + xoay anh theo vien: p' = tam-moi + R(goc) (p - tam-cu); duong cat IMAGECLIP nam trong anh nen di theo
(defun sd:ud-follow (im rg / o c0 c1 th)
  (setq o (vlax-ename->vla-object im) c0 (car rg) c1 (cadr rg) th (caddr rg))
  (if (> (abs th) 1e-9) (vla-Rotate o (vlax-3d-point (car c0) (cadr c0) 0.0) th))
  (vla-Move o (vlax-3d-point (car c0) (cadr c0) 0.0) (vlax-3d-point (car c1) (cadr c1) 0.0))
  (setq *SD:IMCLIPS* nil))

;; Cap nhat tam vien ghi trong SD_ANH (de SDMOANH / SDRON / SDDICHVAN con tim ra anh sau khi vien da di xa)
(defun sd:ud-setctr (im c / xd)
  (setq xd (mapcar 'cdr (cdadr (assoc -3 (entget im '("SD_ANH"))))))
  (if (>= (length xd) 3)
    (vl-catch-all-apply 'sd:put-xd
      (list im (list -3 (list "SD_ANH" (cons 1040 (float (car c))) (cons 1040 (float (cadr c))) (cons 1040 (nth 2 xd))))))))

(defun sd:ud-ended (rx cmd / hs ims e pts im n os ce oa ent rg st fr)
  (cond
    (*SD:RXBUSY*)
    ;; lenh cua ShopDrawing tu lo anh va hatch; undo / redo khong xu ly
    ((wcmatch (strcase (car cmd)) "SD*,U,UNDO,OOPS,REDO,MREDO,*SAVE,CLOSE,QUIT")
     (setq *SD:RXPEND* nil)
     ;; lenh vua tao / doi vien + anh: lap lai ban do lien ket vien - anh de MOVE / ROTATE vien sau do keo anh di theo
     (if (wcmatch (strcase (car cmd)) "SDANHDA,SDMOANH,SDRON,SDDOCDA,SDRAITAM,SDLOT,SDLENH,SDXOAVIEN,SDDICHVAN,SDMAP*,SDPHUONGAN,SDTHANGDA")
       (vl-catch-all-apply 'sd:ud-snap nil)))
    ((null *SD:RXPEND*))
    (t
     (setq *SD:RXBUSY* t hs *SD:RXPEND* *SD:RXPEND* nil n 0 os (getvar "OSMODE") ce (getvar "CMDECHO") *SD:IMCLIPS* nil)
     (setvar "OSMODE" 0) (setvar "CMDECHO" 0)
     (vl-catch-all-apply
       '(lambda ()
          (foreach h hs
            (if (and (setq e (handent h)) (entget e) (= (cdr (assoc 0 (entget e))) "LWPOLYLINE") (= 1 (logand 1 (cdr (assoc 70 (entget e))))))
              (progn
                (setq pts (sd:curve-pts e) ent (assoc h *SD:RXMAP*) im nil rg nil *SD:IFRAME* nil)
                ;; anh theo ban do lien ket (khong phu thuoc vi tri); khong co thi tim theo vi tri nhu truoc
                (if (and ent (setq im (handent (cadr ent))) (null (entget im))) (setq im nil))
                (if (null im)
                  (progn
                    (if (null ims) (setq ims (ssget "_X" '((0 . "IMAGE") (-3 ("SD_ANH"))))))
                    (setq im (if ims (sd:im-find pts ims)))))
                (setq oa (cdr (assoc h *SD:RXANG*)) fr (sd:tile-frame pts)
                      *SD:RXANG* (cons (cons h (car fr)) (vl-remove (assoc h *SD:RXANG*) *SD:RXANG*)))
                (cond
                  ((null im))
                  ;; vien chi tinh tien / xoay (MOVE, ROTATE): anh di theo vien, khong can cat lai
                  ((and ent (equal (cadr ent) (cdr (assoc 5 (entget im)))) (setq rg (sd:ud-rigid (caddr ent) pts 0.2)))
                   (if (and (< (distance (car rg) (cadr rg)) 1e-6) (< (abs (caddr rg)) 1e-9))
                     nil
                     (progn
                       (setq st (sd:ud-img-state im ent rg))
                       (cond ((= st 'FOLLOW) (sd:ud-follow im rg) (setq n (1+ n)))
                             ((= st 'SKIP))
                             (t (sd:im-reclip im (sd:inset-pts pts (/ (cond (*SD:IRON*) (0.0)) 2.0)) 10.0 oa) (setq n (1+ n))))
                       (sd:ud-setctr im (cadddr fr))))
                   (sd:ud-mapset h im pts))
                  ;; bien doi hinh (grip, stretch...): cat lai anh theo bien moi
                  (t
                   (sd:im-reclip im (sd:inset-pts pts (/ (cond (*SD:IRON*) (0.0)) 2.0)) 10.0 oa)
                   (setq n (1+ n))
                   (sd:ud-setctr im (cadddr fr))
                   (sd:ud-mapset h im pts))))))
       nil)
       nil)
     (setvar "OSMODE" os) (setvar "CMDECHO" ce)
     (if (> n 0) (princ (strcat "\n[SD] Tu dong: da dich / cat lai anh " (itoa n) " vien theo vien moi.")))
     (if *SD:XOAYHINT*
       (progn (princ "\n[SD] Co vien het kho theo chieu van hien tai nhung xoay 90 do thi du: chay SDMOANH va chon Hoi / Tu xoay, hoac doi SDMOANH > Het kho thanh Tu xoay de SDTUDONG tu xoay.")
              (setq *SD:XOAYHINT* nil)))
     (setq *SD:RXBUSY* nil))))

;; Goc canh dai hien tai cua cac vien + ban do lien ket vien - anh (goi khi bat SDTUDONG, khi nap, va sau cac lenh SD tao / doi vien + anh)
(defun sd:ud-snap (/ ss ims i e pts il xd bb im h)
  (setq *SD:RXANG* nil *SD:IFRAME* nil *SD:RXMAP* nil)
  (setq *SD:IMCLIPS* nil)
  (foreach c (sd:im-clips)
    (setq il (cons (list (cdr (assoc 5 (entget (car c)))) (car c) (cadr c) (caddr c)) il)))
  (if (setq ss (ssget "_X" '((0 . "LWPOLYLINE") (8 . "SD-GACH,SD-GACH-CAT,SD-GACH-VIEN,SD-GACH-DOC") (-4 . "&") (70 . 1))))
    (progn
      (setq i 0)
      (repeat (sslength ss)
        (setq e (ssname ss i) i (1+ i))
        (vl-catch-all-apply
          '(lambda ()
             (setq h (cdr (assoc 5 (entget e))) pts (sd:curve-pts e)
                   *SD:RXANG* (cons (cons h (car (sd:tile-frame pts))) *SD:RXANG*))
             (if il
               (progn
                 (setq bb (list (apply 'min (mapcar 'car pts)) (apply 'min (mapcar 'cadr pts))
                                (apply 'max (mapcar 'car pts)) (apply 'max (mapcar 'cadr pts))))
                 (if (setq im (sd:ud-pick pts bb il)) (sd:ud-mapset h (cadr im) pts)))))
          nil))))
  (length *SD:RXANG*))


(defun sd:ud-on ()
  (if (not *SD:RXDB*)
    (setq *SD:RXDB* (vlr-acdb-reactor "SD-tudong" '((:vlr-objectModified . sd:ud-dbmod)))
          *SD:RXCMD* (vlr-command-reactor "SD-tudong" '((:vlr-commandEnded . sd:ud-ended)))
          *SD:RXPEND* nil *SD:RXBUSY* nil))
  t)

(defun sd:ud-off ()
  (if *SD:RXDB* (vl-catch-all-apply 'vlr-remove (list *SD:RXDB*)))
  (if *SD:RXCMD* (vl-catch-all-apply 'vlr-remove (list *SD:RXCMD*)))
  (setq *SD:RXDB* nil *SD:RXCMD* nil *SD:RXPEND* nil *SD:RXBUSY* nil *SD:RXMAP* nil)
  nil)

(defun sd:ud-flag (/ v)
  (setq v (vl-catch-all-apply 'vl-registry-read (list "HKEY_CURRENT_USER\\Software\\ShopDrawing" "AutoSync")))
  (and (not (vl-catch-all-error-p v)) (= v "1")))
(defun sd:ud-flag-set (on)
  (vl-catch-all-apply 'vl-registry-write (list "HKEY_CURRENT_USER\\Software\\ShopDrawing" "AutoSync" (if on "1" "0"))))

;; Goi khi nap ShopDrawing.lsp (moi ban ve): bat lai neu lan truoc da bat
(defun sd:ud-autoload ()
  (if (sd:ud-flag) (progn (sd:ud-on) (sd:ud-snap) (princ "\n[SD] Tu dong cat lai anh khi sua bien vien: BAT (SDTUDONG de tat)."))))

(defun c:SDTUDONG (/ n)
  (sd:begin)
  (cond
    (*SD:RXDB*
     (sd:ud-off) (sd:ud-flag-set nil)
     (princ "\n[SD] Da TAT che do tu dong cat lai anh khi sua bien vien (nho cho cac lan mo sau)."))
    (t
     (sd:ud-on) (sd:ud-flag-set t) (setq n (sd:ud-snap))
     (princ (strcat "\n[SD] Da BAT che do tu dong cho ca phien va cac ban ve mo sau: MOVE / ROTATE vien thi anh di theo vien; grip / stretch thi anh IMAGECLIP tu cat lai theo bien moi, "
                    "hatch lien ket tu theo. Dang theo doi " (itoa n) " vien hien co va ca vien tao them sau. Chay lai SDTUDONG de tat."))))
  (sd:finish))

;;; --------------------------------------------------------------------------
;;;  SDRONIN - Cho ron / duong vien hien ra khi IN: doi mau + be rong net cac layer vien, dua duong vien len tren anh va hatch
;;;  (duong vien mau toi bi in thanh den chim vao da toi; net qua mong bi mat khi in co nho; anh che duong vien)
;;; --------------------------------------------------------------------------
(setq *SD:RONLAY* '("SD-GACH" "SD-GACH-CAT" "SD-GACH-VIEN" "SD-GACH-DOC"))

;; Be rong net hop le gan nhat (mm * 100)
(defun sd:lw-near (lw / best)
  (foreach v '(0 5 9 13 15 18 20 25 30 35 40 50 53 60 70 80 90 100 106 120 140 158 200 211)
    (if (or (null best) (< (abs (- v lw)) (abs (- best lw)))) (setq best v)))
  best)

;; Bang ma vat lieu -> mau tu chuoi "G1=Den;G2=Trang": (("G1" . 250) ("G2" . 255))
(defun sd:ronin-map (str / r kv)
  (foreach x (sd:split str ";")
    (if (setq kv (sd:split x "="))
      (if (and (= (length kv) 2) (member (strcase (cadr kv)) '("TRANG" "DEN")))
        (setq r (cons (cons (strcase (car kv)) (if (= (strcase (cadr kv)) "TRANG") 255 250)) r)))))
  r)

;; Dat mau / net rieng cho 1 polyline vien (col / lw100 = nil: khong co, tra ve theo layer). Tra ve (mau-cu net-cu) de khoi phuc dung
(defun sd:ronin-ent (e col lw100 / ed new g o62 o370)
  (setq ed (entget e '("SD_TILE")) o62 (cdr (assoc 62 ed)) o370 (cdr (assoc 370 ed)))
  (foreach g ed
    (cond ((member (car g) '(62 370)))
          (t (setq new (cons g new))
             (if (= (car g) 8)
               (progn (if col (setq new (cons (cons 62 col) new)))
                      (if lw100 (setq new (cons (cons 370 lw100) new))))))))
  (entmod (reverse new))
  (list o62 o370))

;; Polyline vien do SDANHDA cat anh nhung nam ngoai cac layer SD-GACH* (VD boundary tu hatch): nho handle de ron in / SDRONIN / SDIN cung tac dong
(defun sd:ron-extra (/ r e)
  (foreach h (vlax-ldata-get "SD" "RON-EXTRA")
    (if (and (setq e (handent h)) (entget e) (= (cdr (assoc 0 (entget e))) "LWPOLYLINE")) (setq r (cons h r))))
  (reverse r))
(defun sd:ron-extra-add (els / lst ed hd)
  (setq lst (sd:ron-extra))
  (foreach e els
    (setq ed (entget e) hd (cdr (assoc 5 ed)))
    (if (and (not (member (strcase (cdr (assoc 8 ed))) *SD:RONLAY*)) (not (member hd lst)))
      (setq lst (cons hd lst))))
  (vlax-ldata-put "SD" "RON-EXTRA" lst)
  lst)

(defun sd:imgframe (mau / ifo ikh)
  (cond
    ((= mau "Khoiphuc")
     (if (and (setq ifo (sd:cfg "RONIN-IMGF" -1)) (>= ifo 0))
       (progn (setvar "IMAGEFRAME" ifo) (sd:cfg-put "RONIN-IMGF" -1))))
    (t
     (setq ikh (sd:cfg "RONIN-KHUNG" "Khongin"))
     (if (< (sd:cfg "RONIN-IMGF" -1) 0) (sd:cfg-put "RONIN-IMGF" (getvar "IMAGEFRAME")))
     (setvar "IMAGEFRAME" (cond ((= ikh "An") 0) ((= ikh "Giu") 1) (2))))))

(defun sd:ronin-apply (mau lw mapstr front / lays old l n ss i lo mp nm2 xd col sv e h old2 nxe)
  (sd:imgframe mau)
  (setq n 0 lays (vla-get-Layers (sd:doc)) old (vlax-ldata-get "SD" "RONIN-OLD") sv (vlax-ldata-get "SD" "RONIN-ENT"))
  (foreach nm *SD:RONLAY*
    (if (tblsearch "LAYER" nm)
      (progn
        (setq l (vla-Item lays nm))
        (cond
          ((= mau "Khoiphuc")
           (if (setq lo (assoc nm old))
             (progn (vla-put-Color l (cadr lo)) (vla-put-Lineweight l (caddr lo)) (setq n (1+ n)))))
          (t
           (if (not (assoc nm old))
             (setq old (cons (list nm (vla-get-Color l) (vla-get-Lineweight l)) old)))
           (vla-put-Color l (if (= mau "Trang") 255 250))
           (vla-put-Lineweight l (sd:lw-near (fix (+ 0.5 (* 100.0 lw)))))
           (vla-put-Plottable l :vlax-true)
           (setq n (1+ n)))))))
  (setq mp (if (and (/= mau "Khoiphuc") mapstr (/= mapstr "")) (sd:ronin-map mapstr)))
  (cond
    ;; khoi phuc: tra lai dung mau / net rieng cu cua tung vien da bi doi (khong dung vao mau do nguoi dung tu dat)
    ((= mau "Khoiphuc")
     (setq nm2 0)
     (if sv
       (foreach r sv
         (if (setq e (handent (car r))) (progn (sd:ronin-ent e (cadr r) (caddr r)) (setq nm2 (1+ nm2)))))
       ;; chua co ban ghi (ban cu): bo mau rieng cua moi vien
       (if (setq ss (ssget "_X" (list '(0 . "LWPOLYLINE") '(-3 ("SD_TILE")) (cons 8 (sd:join *SD:RONLAY* ",")))))
         (progn (setq i 0) (repeat (sslength ss) (sd:ronin-ent (ssname ss i) nil nil) (setq i (1+ i) nm2 (1+ nm2))))))
     (vlax-ldata-put "SD" "RONIN-ENT" nil)
     (if (> nm2 0) (princ (strcat "\n[SD] Da tra mau / net rieng cu cho " (itoa nm2) " vien."))))
    (mp
     (if (setq ss (ssget "_X" (list '(0 . "LWPOLYLINE") '(-3 ("SD_TILE")) (cons 8 (sd:join *SD:RONLAY* ",")))))
       (progn
         (setq i 0 nm2 0)
         (repeat (sslength ss)
           (setq e (ssname ss i) i (1+ i)
                 xd (mapcar 'cdr (cdadr (assoc -3 (entget e '("SD_TILE"))))))
           (if (and xd (setq col (cdr (assoc (strcase (car xd)) mp))))
             (progn
               (setq old2 (sd:ronin-ent e col (sd:lw-near (fix (+ 0.5 (* 100.0 lw))))) h (cdr (assoc 5 (entget e))) nm2 (1+ nm2))
               (if (not (assoc h sv)) (setq sv (cons (cons h old2) sv))))))
         (vlax-ldata-put "SD" "RONIN-ENT" sv)
         (if (> nm2 0) (princ (strcat "\n[SD] Mau rieng theo vat lieu: " (itoa nm2) " vien.")))))))
  ;; polyline ngoai layer SD-GACH* da cat anh bang SDANHDA: dat mau / net rieng tung polyline (luu mau cu de khoi phuc)
  (if (/= mau "Khoiphuc")
    (progn
      (setq nxe 0)
      (foreach hd (sd:ron-extra)
        (setq e (handent hd)
              old2 (sd:ronin-ent e (if (= mau "Trang") 255 250) (sd:lw-near (fix (+ 0.5 (* 100.0 lw)))))
              nxe (1+ nxe))
        (if (not (assoc hd sv)) (setq sv (cons (cons hd old2) sv))))
      (vlax-ldata-put "SD" "RONIN-ENT" sv)
      (if (> nxe 0) (princ (strcat "\n[SD] Polyline vien ngoai layer SD-GACH (da cat anh): " (itoa nxe) " vien dat mau / net ron.")))))
  (if (/= mau "Khoiphuc") (vlax-ldata-put "SD" "RONIN-OLD" old))
  (if (and (= mau "Khoiphuc") old) (vlax-ldata-put "SD" "RONIN-OLD" nil))
  (if (and front (/= mau "Khoiphuc"))
    (progn
      (setq ss (ssget "_X" (list '(0 . "LWPOLYLINE") (cons 8 (sd:join *SD:RONLAY* ",")))))
      (foreach hd (sd:ron-extra) (setq ss (cond (ss) ((ssadd)))) (ssadd (handent hd) ss))
      (if ss (command "_.DRAWORDER" ss "" "_F"))))
  (command "_.REGENALL")
  (princ (strcat "\n[SD] " (itoa n) " layer vien: "
                 (cond ((= mau "Trang") (strcat "mau trang thuan, net " (sd:num lw) " mm"))
                       ((= mau "Den") (strcat "mau den, net " (sd:num lw) " mm"))
                       (t "da khoi phuc mau va net cu"))
                 (if (and front (/= mau "Khoiphuc")) "; duong vien da dua len tren anh va hatch" "") "."))
  n)

(defun c:SDRONIN ()
  (sd:begin)
  (if (sd:dlg "Ron hien ra khi in (SDRONIN)"
              (list (list "mau" "Mau duong ron / vien tren cac layer vien" 'kw (sd:cfg "RONIN-MAU" "Trang")
                          '(("Trang" . "Trang thuan (ACI 255): hien tren da / anh toi khi in")
                            ("Den" . "Den (ACI 250)")
                            ("Khoiphuc" . "Khoi phuc mau va net cu")))
                    (list "lw" "Be rong net khi in (mm)" 'real (sd:cfg "RONIN-LW" 0.25) nil '("mau" "Trang" "Den"))
                    (list "map" "Theo vat lieu: ma=mau, VD G1=Den;G2=Trang (de trong = cung 1 mau cho tat ca)" 'str (sd:cfg "RONIN-MAP" "") nil '("mau" "Trang" "Den"))
                    (list "front" "Dua duong vien (polyline) len tren anh va hatch" 'tog t)
                    (list "khung" "Khung vien den cua anh da (IMAGEFRAME)" 'kw (sd:cfg "RONIN-KHUNG" "Khongin")
                          '(("Khongin" . "Hien khi ve, khong in (IMAGEFRAME 2)") ("An" . "An han (IMAGEFRAME 0)") ("Giu" . "Giu nguyen khung (IMAGEFRAME 1)"))
                          '("mau" "Trang" "Den"))))
    (progn
      (sd:cfg-put "RONIN-KHUNG" (cond ((sd:v "khung")) ("Khongin")))
      (sd:cfg-put "RONIN-MAU" (sd:v "mau")) (sd:cfg-put "RONIN-LW" (cond ((sd:v "lw")) (0.25)))
      (sd:cfg-put "RONIN-MAP" (cond ((sd:v "map")) ("")))
      (sd:ronin-apply (sd:v "mau") (cond ((sd:v "lw")) (0.25)) (cond ((sd:v "map")) ("")) (sd:v "front"))
      (if (/= (sd:v "mau") "Khoiphuc")
        (princ "\n   Khi in: dung bang net acad.ctb (mau ACI 255 in dung mau trang); KHONG dung monochrome.ctb vi se doi ron thanh den, chim vao da toi. Tich 'Plot object lineweights'. Neu in nho (Fit to paper) thi tang be rong net hoac ron."))))
  (sd:finish))

;;; --------------------------------------------------------------------------
;;;  Thu vien vat lieu: nho thong so lan truoc theo ma vat lieu (cfg "VL-MAU", moi ban ve), hien danh sach de chon nhanh
;;;  Moi muc: (ma ten W H day ron khe kieu). Moi nhat nam dau, toi da 12 muc.
;;; --------------------------------------------------------------------------
(defun sd:vl-load () (sd:cfg "VL-MAU" nil))

(defun sd:vl-save (mat name W H thk jt gap pat / lst)
  (if (and mat (/= mat ""))
    (progn
      (setq lst (vl-remove-if '(lambda (r) (= (strcase (car r)) (strcase mat))) (sd:vl-load)))
      (sd:cfg-put "VL-MAU" (sd:take (cons (list mat name W H thk jt gap pat) lst) 12)))))

(defun sd:vl-line (k r)
  (strcat "\n  " (itoa k) ". " (car r) "  " (cadr r) "  [" (rtos (nth 2 r) 2 0) "x" (rtos (nth 3 r) 2 0) "x" (rtos (nth 4 r) 2 0)
          "  ron " (rtos (nth 5 r) 2 1) "  khe " (rtos (nth 6 r) 2 1) "  " (nth 7 r) "]"))

(defun sd:vl-show (lst / k)
  (setq k 0)
  (foreach r lst (setq k (1+ k)) (princ (sd:vl-line k r))))

;; hien danh sach, nhap so de dien san cac gia tri mac dinh cua hop thoai ngay sau do; Enter = nhap moi
(defun sd:vl-pick (/ lst n r)
  (if (setq lst (sd:vl-load))
    (progn
      (princ "\nVat lieu da dung (moi nhat truoc):")
      (sd:vl-show lst)
      (setq n (getint "\nChon so de dung lai thong so <Enter = nhap moi>: "))
      (if (and n (>= n 1) (<= n (length lst)))
        (progn
          (setq r (nth (1- n) lst))
          (setq *SD:GCODE* (nth 0 r) *SD:GNAME* (nth 1 r) *SD:GW* (nth 2 r) *SD:GH* (nth 3 r) *SD:GT* (nth 4 r)
                *SD:GJ* (nth 5 r) *SD:GGAP* (nth 6 r) *SD:GPAT* (nth 7 r))
          (if (member (nth 7 r) '("Thang" "Sole")) (sd:cfg-put "LOT-PAT" (nth 7 r)))
          (princ (strcat "\n[SD] Dung lai: " (car r) " - sua trong hop thoai neu can."))
          t)))))

(defun c:SDVATLIEU (/ lst n)
  (sd:begin)
  (if (null (setq lst (sd:vl-load)))
    (princ "\n[SD] Chua nho vat lieu nao. Chay SDGACH hoac SDLOT mot lan, thong so se duoc luu lai.")
    (progn
      (princ "\nVat lieu da nho:")
      (sd:vl-show lst)
      (setq n (getint "\nNhap so de XOA khoi danh sach <Enter = thoat>: "))
      (if (and n (>= n 1) (<= n (length lst)))
        (progn
          (sd:cfg-put "VL-MAU" (vl-remove (nth (1- n) lst) lst))
          (princ (strcat "\n[SD] Da xoa " (car (nth (1- n) lst)) " khoi danh sach."))))))
  (sd:finish))

;;; --------------------------------------------------------------------------
;;;  SDXOAVIEN - Go bo vien: xoa cung luc polyline vien + anh + hatch + so hieu T.. trong vung chon,
;;;  de lo ra chi tiet nam duoi (mat cat mui bac...). Moi vien la nhieu doi tuong rieng (polyline, anh, hatch), lenh nay xoa gon 1 lan
;;; --------------------------------------------------------------------------
(defun sd:hatch-center (e / o bb mn mx)
  (setq o (vlax-ename->vla-object e))
  (vla-GetBoundingBox o 'mn 'mx)
  (setq mn (vlax-safearray->list mn) mx (vlax-safearray->list mx))
  (list (/ (+ (car mn) (car mx)) 2.0) (/ (+ (cadr mn) (cadr mx)) 2.0)))

(defun c:SDXOAVIEN (/ ss i e ed lay polys ents ims hs txs pts im h c n k)
  (sd:begin)
  (princ "\nChon vung can go bo vien (quet cua so; xoa polyline vien + anh + hatch + so hieu T.. cua cac vien trong vung): ")
  (if (setq ss (ssget))
    (progn
      (setq i 0)
      (repeat (sslength ss)
        (setq e (ssname ss i) i (1+ i) ed (entget e) lay (strcase (cdr (assoc 8 ed))))
        (cond
          ((and (= (cdr (assoc 0 ed)) "LWPOLYLINE") (member lay *SD:RONLAY*) (= 1 (logand 1 (cdr (assoc 70 ed)))))
           (setq polys (cons e polys)))
          ((or (and (= (cdr (assoc 0 ed)) "IMAGE") (= lay "SD-GACH-ANH"))
               (and (= (cdr (assoc 0 ed)) "HATCH") (= lay "SD-GACH-VAN")))
           (setq ents (cons e ents)))))
      ;; anh / hatch / so hieu thuoc cac vien da chon nhung nam ngoai vung quet
      (setq ims (ssget "_X" '((0 . "IMAGE") (-3 ("SD_ANH"))))
            hs  (ssget "_X" '((0 . "HATCH") (8 . "SD-GACH-VAN")))
            txs (ssget "_X" '((0 . "TEXT") (8 . "SD-CHU") (1 . "T#*"))))
      (foreach pe polys
        (setq pts (sd:curve-pts pe))
        (if (and ims (setq im (sd:im-find pts ims)) (not (member im ents))) (setq ents (cons im ents)))
        (if hs
          (progn (setq k 0)
                 (repeat (sslength hs)
                   (setq h (ssname hs k) k (1+ k))
                   (if (and (not (member h ents)) (sd:inpoly (sd:hatch-center h) pts)) (setq ents (cons h ents))))))
        (if txs
          (progn (setq k 0)
                 (repeat (sslength txs)
                   (setq h (ssname txs k) k (1+ k) c (cdr (assoc 10 (entget h))))
                   (if (and (not (member h ents)) (sd:inpoly (list (car c) (cadr c)) pts)) (setq ents (cons h ents)))))))
      (setq n 0)
      (foreach x (append polys ents) (if (entget x) (progn (entdel x) (setq n (1+ n)))))
      (princ (strcat "\n[SD] Da go " (itoa (length polys)) " vien (" (itoa n) " doi tuong gom polyline, anh, hatch, so hieu): chi tiet nam duoi da lo ra. Hoan lai bang UNDO.")))
    (princ "\n[SD] Chua chon gi."))
  (sd:finish))

;;; --------------------------------------------------------------------------
;;;  SDLOT - Chay mot lan cho nhieu phong / khu vuc: rai vien (SDGACH) cho tung vung, chon diem bat dau tot nhat tu dong,
;;;  ghi ten khu vuc, thong ke tung vung + tong, kiem tra vien cat hep, (tuy chon) cat anh va hatch van cho tat ca
;;; --------------------------------------------------------------------------
;; Tach cac polyline kin thanh vung lat va lo / cot: da giac nam tron trong da giac khac o do sau le la lo, chan la vung
;; Tra ve ((ename-vung (ename-lo ...)) ...)
(defun sd:lot-split (ss / pl i e pts dp par anc r)
  (setq i 0)
  (repeat (sslength ss)
    (setq e (ssname ss i) i (1+ i) pts (sd:curve-pts e))
    (setq pl (cons (list e pts (abs (sd:area pts))) pl)))
  (foreach p pl
    (setq dp 0 par nil)
    (foreach q pl
      (if (and (not (eq (car p) (car q))) (> (nth 2 q) (nth 2 p))
               (vl-every '(lambda (v) (sd:inpoly v (nth 1 q))) (nth 1 p)))
        (progn (setq dp (1+ dp))
               (if (or (null par) (< (nth 2 q) (nth 2 par))) (setq par q)))))
    (setq anc (cons (list (car p) dp (if par (car par))) anc)))
  (foreach x anc
    (if (= (rem (cadr x) 2) 0)
      (setq r (cons (list (car x)
                          (mapcar 'car (vl-remove-if-not '(lambda (y) (and (= (rem (cadr y) 2) 1) (eq (caddr y) (car x)))) anc)))
                    r))))
  (reverse r))

;; Diem bat dau tot nhat (toa do WCS, goc vien trai-duoi cua luoi) cho vung outer-pts tru cac lo, luoi W x H, ron jt, goc ang (rad)
(defun sd:lot-best (outer-pts holes W H jt ang hep q / rp rh cands res)
  (setq rp (mapcar '(lambda (p) (sd:rot p (- ang))) outer-pts)
        rh (mapcar '(lambda (hp) (mapcar '(lambda (p) (sd:rot p (- ang))) hp)) holes)
        cands (sd:od-cands rp W H jt q))
  (foreach c cands (setq res (cons (list c (sd:od-eval rp rh W H jt (cadr c) (caddr c) hep)) res)))
  (setq res (car (sd:sort res 'sd:od-less)))
  (list (sd:rot (list (cadr (car res)) (caddr (car res))) ang) (car (car res)) (cadr res)))

(defun c:SDLOT (/ cpt ss rooms rm k outer holes mat name W H thk jt gap pat ang start q hep nhan anh van sc o b lastv news
                  nf nc ns arr cpa xd rows tn tc tf tarea twaste fn f e r pts lbl allnew)
  (sd:begin)
  (setq sc (sd:sc))
  (sd:vl-pick)
  (if (sd:dlg "Chay lo nhieu phong (SDLOT)"
              (list (list "mat" "Ma vat lieu" 'str (cond (*SD:GCODE*) ("G1")))
                    (list "name" "Ten vat lieu" 'str (cond (*SD:GNAME*) ("Granite 600x600x20")))
                    (list "W" "Vien thanh pham - ngang W (mm)" 'real (cond (*SD:GW*) (600.0)))
                    (list "H" "Vien thanh pham - dung H (mm)" 'real (cond (*SD:GH*) (600.0)))
                    (list "thk" "Chieu day da / gach (mm)" 'real (cond (*SD:GT*) (20.0)))
                    (list "jt" "Be rong mach / ron (mm)" 'real0 (cond (*SD:GJ*) ((sd:cfg "RON-CU" 2.0))))
                    (list "gap" "Khe sat tuong va quanh lo (mm)" 'real0 (cond (*SD:GGAP*) (0.0)))
                    (list "pat" "Kieu lat" 'kw (sd:cfg "LOT-PAT" "Thang") '(("Thang" . "Thang") ("Sole" . "So le (diem bat dau = tam vung)")))
                    (list "ang" "Goc xoay luoi (do)" 'real0 (sd:cfg "LOT-ANG" 0.0))
                    (list "start" "Diem bat dau tung vung" 'kw (sd:cfg "LOT-START" "Tot")
                          '(("Tot" . "Tot nhat (it vien hep, it vien cat; chi lat thang)") ("Tam" . "Tam vung") ("Goc" . "Goc trai-duoi vung")
                            ("Chung" . "Mot diem goc chung cho moi vung: luoi ron lien tuc xuyen cac phong (chon diem sau)")))
                    (list "q" "Do ky khi chon diem tot nhat" 'kw (sd:cfg "LOT-Q" "Nhanh")
                          '(("Nhanh" . "Nhanh: 6 diem") ("Ky" . "Ky: them 25 diem quet")) '("start" "Tot"))
                    (list "hep" "Vien cat hep hon (mm) tinh la vun" 'real (sd:cfg "LOT-HEP" 50.0))
                    (list "nhan" "Ghi ten khu vuc (KV1, KV2...) va dien tich" 'tog t)
                    (list "anh" "Sau do cat anh tam da cho tat ca cac vien (SDANHDA, hoi 1 lan)" 'tog nil)
                    (list "van" "Sau do hatch van da cho cac vien (SDVANDA)" 'tog nil)))
    (progn
      (setq mat (sd:v "mat") name (sd:v "name") W (sd:v "W") H (sd:v "H") thk (sd:v "thk") jt (sd:v "jt") gap (sd:v "gap")
            pat (sd:cfg-put "LOT-PAT" (sd:v "pat")) ang (sd:cfg-put "LOT-ANG" (cond ((sd:v "ang")) (0.0)))
            start (sd:cfg-put "LOT-START" (sd:v "start")) q (sd:cfg-put "LOT-Q" (cond ((sd:v "q")) ("Nhanh")))
            hep (sd:cfg-put "LOT-HEP" (sd:v "hep")) nhan (sd:v "nhan") anh (sd:v "anh") van (sd:v "van")
            *SD:GCODE* mat *SD:GNAME* name *SD:GW* W *SD:GH* H *SD:GJ* (sd:cfg-put "RON-CU" jt) *SD:GGAP* gap *SD:GT* thk)
      (sd:vl-save mat name W H thk jt gap pat)
      (princ "\nQuet chon tat ca polyline kin: bien cac phong / khu vuc (lo, cot nam trong se tu nhan la lo): ")
      (if (setq ss (ssget '((0 . "LWPOLYLINE") (-4 . "&") (70 . 1))))
        (progn
          (if (= start "Chung")
            (if (setq cpt (sd:getpt "\nDiem goc luoi chung (goc duoi-trai cua mot vien hoac giao diem ron): " nil))
              (setq cpt (sd:2d cpt))
              (progn (princ "\n[SD] Chua chon diem chung: dung goc trai-duoi tung vung.") (setq start "Goc"))))
          (setq rooms (sd:lot-split ss) k 0 tn 0 tc 0 tf 0 tarea 0.0 twaste 0.0 *SD:NBRUN* t)
          (princ (strcat "\n[SD] " (itoa (length rooms)) " khu vuc, " (itoa (- (sslength ss) (length rooms))) " lo / cot."))
          (foreach rm rooms
            (setq k (1+ k) outer (car rm) holes (cadr rm) pts (sd:curve-pts outer) o nil lbl "")
            (cond ((and (= start "Tot") (= pat "Thang"))
                   (setq b (sd:lot-best pts (mapcar 'sd:curve-pts holes) W H jt (* pi (/ ang 180.0)) hep (if (= q "Ky") 1 0))
                         o (car b) lbl (strcat (cadr b) ", " (itoa (cadr (caddr b))) " cat")))
                  ((= start "Chung") (setq o cpt lbl "luoi chung"))
                  ((= start "Goc")
                   (setq o (sd:rot (list (apply 'min (mapcar 'car (mapcar '(lambda (p) (sd:rot p (- (* pi (/ ang 180.0))))) pts)))
                                         (apply 'min (mapcar 'cadr (mapcar '(lambda (p) (sd:rot p (- (* pi (/ ang 180.0))))) pts))))
                                   (* pi (/ ang 180.0)))
                         lbl "goc")))
            (setq lastv (entlast)
                  *SD:GBATCH* t *SD:GOUTER* outer *SD:GHOLES* holes *SD:GSTART* o
                  *SD:BATCH* (list (cons "MAT" mat) (cons "NAME" name) (cons "W" (sd:rtos W 3)) (cons "H" (sd:rtos H 3))
                                   (cons "THK" (sd:rtos thk 3)) (cons "JT" (sd:rtos jt 3)) (cons "GAP" (sd:rtos gap 3))
                                   (cons "PAT" pat) (cons "ANG" (sd:rtos ang 3)) (cons "AL" (if (or o (= start "Goc")) "Goc" "Mach"))
                                   (cons "ANH" "0"))
                  r (vl-catch-all-apply 'c:SDGACH nil)
                  *SD:GBATCH* nil *SD:GOUTER* nil *SD:GHOLES* nil *SD:GSTART* nil *SD:BATCH* nil)
            (if (vl-catch-all-error-p r)
              (princ (strcat "\n[SD] KV" (itoa k) ": khong chia duoc (" (vl-catch-all-error-message r) ")."))
              (progn
                (setq news (sd:gach-new lastv) nf 0 nc 0 ns 0 arr 0.0 cpa 0.0)
                (foreach e news
                  (setq xd (mapcar 'cdr (cdadr (assoc -3 (entget e '("SD_TILE"))))))
                  (if (and xd (/= (nth 1 xd) "X"))
                    (progn
                      (setq arr (+ arr (nth 5 xd)))
                      (if (= (nth 1 xd) "F")
                        (setq nf (1+ nf))
                        (progn (setq nc (1+ nc) cpa (+ cpa (nth 5 xd)))
                               (if (< (min (nth 3 xd) (nth 4 xd)) hep) (setq ns (1+ ns))))))))
                (setq allnew (append allnew news)
                      tn (+ tn 1) tf (+ tf nf) tc (+ tc nc)
                      twaste (+ twaste (- (* nc W H) cpa)) tarea (+ tarea arr))
                (setq rows (cons (list (strcat "KV" (itoa k)) (sd:rtos (/ (abs (sd:area pts)) 1e6) 2) (itoa nf) (itoa nc) (itoa ns)
                                       (sd:rtos (if (> (+ nf nc) 0) (/ (* 100.0 (- (* nc W H) cpa)) (* (+ nf nc) W H)) 0.0) 1) lbl)
                                 rows))
                (if nhan
                  (sd:text (sd:centroid pts) (strcat "KV" (itoa k) " - " (sd:rtos (/ (abs (sd:area pts)) 1e6) 2) " m2")
                           (* 3.0 sc) "MC" "SD-CHU"))
                (princ (strcat "\n  KV" (itoa k) ": " (sd:rtos (/ (abs (sd:area pts)) 1e6) 2) " m2, " (itoa nf) " nguyen, " (itoa nc) " cat"
                               (if (> ns 0) (strcat ", " (itoa ns) " cat hep < " (sd:num hep) " mm") "")
                               (if (/= lbl "") (strcat " [" lbl "]") ""))))))
          (setq *SD:NBRUN* nil)
          (princ (strcat "\n[SD] SDLOT: " (itoa (length rooms)) " khu vuc, " (itoa tf) " vien nguyen + " (itoa tc) " vien cat, hao hut "
                         (sd:rtos (if (> (+ tf tc) 0) (/ (* 100.0 twaste) (* (+ tf tc) W H)) 0.0) 1) "% (uoc tinh, chua tinh dung chung manh cat)."))
          (if (and rows (setq fn (sd:csv-name "_LotNhieuPhong.csv")) (setq f (sd:open fn "w")))
            (progn
              (write-line "sep=;" f)
              (write-line "Khu vuc;Dien tich (m2);Vien nguyen;Vien cat;Vien cat hep;Hao hut (%);Diem bat dau" f)
              (foreach r (reverse rows) (write-line (sd:join r ";") f))
              (princ (strcat "\n[SD] Da xuat: " (sd:close f)))))
          (if (and anh allnew) (sd:anhda allnew))
          (if van (c:SDVANDA)))
        (princ "\n[SD] Chua chon polyline."))))
  (setq *SD:NBRUN* nil *SD:GBATCH* nil)
  (sd:finish))

;;; --------------------------------------------------------------------------
;;;  SDTRUNGRON - Kiem tra luoi ron lien tuc xuyen cac phong: nhom vien lech luoi chinh bao nhieu mm, khoanh may, de xuat dich
;;; --------------------------------------------------------------------------
;; Dua v ve khoang [-p/2, p/2]
(defun sd:rg-fold (v p) (- v (* p (fix (+ (/ v p) (if (>= v 0.0) 0.5 -0.5))))))
;; items = ((ox oy tag) ...) -> cac nhom ((ox oy so-luong (tag ...)) ...), nhom dong nhat truoc
(defun sd:rg-classify (items tol / cls hit)
  (foreach it items
    (setq hit nil)
    (foreach c cls
      (if (and (null hit) (<= (abs (- (car it) (car c))) tol) (<= (abs (- (cadr it) (cadr c))) tol)) (setq hit c)))
    (if hit
      (setq cls (subst (list (car hit) (cadr hit) (1+ (caddr hit)) (cons (caddr it) (cadddr hit))) hit cls))
      (setq cls (cons (list (car it) (cadr it) 1 (list (caddr it))) cls))))
  (vl-sort cls '(lambda (a b) (> (caddr a) (caddr b)))))

(defun sd:rg-scan (ss jt tol sole / i e xd pts fr ang ang0 c0 w h w0 h0 items v ox oy px py nang nsz nin)
  (setq i 0 nang 0 nsz 0 nin 0 *SD:IFRAME* nil)
  (repeat (sslength ss)
    (setq e (ssname ss i) i (1+ i) xd (mapcar 'cdr (cdadr (assoc -3 (entget e '("SD_TILE"))))))
    (if (and (>= (length xd) 12) (= (nth 1 xd) "F") (>= (length (setq pts (sd:curve-pts e))) 3))
      (progn
        (setq fr (sd:tile-frame pts) ang (car fr) w (cadr fr) h (caddr fr) nin (1+ nin))
        (if (null ang0) (setq ang0 ang w0 w h0 h c0 (cadddr fr) px (+ w0 jt) py (+ h0 jt)))
        (setq v (rem (- ang ang0) pi))
        (if (> v (/ pi 2.0)) (setq v (- v pi)))
        (if (< v (- (/ pi 2.0))) (setq v (+ v pi)))
        (cond ((< (abs v) 0.02))
              ((< (abs (- (abs v) (/ pi 2.0))) 0.02) (setq v w w h h v))
              (t (setq w nil)))
        (cond ((null w) (setq nang (1+ nang)))
              ((or (> (abs (- w w0)) 1.0) (> (abs (- h h0)) 1.0)) (setq nsz (1+ nsz)))
              (t (setq v (sd:rot (list (- (car (cadddr fr)) (car c0)) (- (cadr (cadddr fr)) (cadr c0))) (- ang0))
                       ox (if sole 0.0 (sd:rg-fold (car v) px)) oy (sd:rg-fold (cadr v) py)
                       items (cons (list ox oy e) items)))))))
  (list (if items (sd:rg-classify items tol)) nang nsz nin (length items) (if ang0 (+ w0 jt)) ))

(defun c:SDTRUNGRON (/ ss jt tol sole rs cls main nang nsz nin sc k boxes bx lay px)
  (sd:begin)
  (if (setq ss (sd:select-tiles "\nCh\\U+1ECDn c\\U+00E1c vi\\U+00EAn c\\U+1EA7n ki\\U+1EC3m tra l\\U+01B0\\U+1EDBi ron (Enter = t\\U+1EA5t c\\U+1EA3 trong b\\U+1EA3n v\\U+1EBD): "))
    (if (sd:dlg "Ki\\U+1EC3m tra l\\U+01B0\\U+1EDBi ron xuy\\U+00EAn c\\U+00E1c ph\\U+00F2ng (SDTRUNGRON)"
                (list (list "jt" "B\\U+1EC1 r\\U+1ED9ng ron (mm)" 'real0 (sd:cfg "RON-CU" 2.0))
                      (list "tol" "L\\U+1EC7ch cho ph\\U+00E9p gi\\U+1EEFa hai l\\U+01B0\\U+1EDBi (mm)" 'real (sd:cfg "RG-TOL" 2.0))
                      (list "kieu" "Ki\\U+1EC3u l\\U+00E1t" 'kw (sd:cfg "RG-KIEU" "Thang") '(("Thang" . "Th\\U+1EB3ng: ki\\U+1EC3m tra c\\U+1EA3 hai ph\\U+01B0\\U+01A1ng") ("Sole" . "So le: ch\\U+1EC9 ki\\U+1EC3m tra ph\\U+01B0\\U+01A1ng d\\U+1ECDc")))))
      (progn
        (setq jt (sd:cfg-put "RON-CU" (sd:v "jt")) tol (sd:cfg-put "RG-TOL" (sd:v "tol")) sole (= (sd:cfg-put "RG-KIEU" (sd:v "kieu")) "Sole")
              sc (sd:sc) rs (sd:rg-scan ss jt tol sole) cls (car rs) nang (cadr rs) nsz (caddr rs) nin (cadddr rs) px (nth 5 rs))
        (cond
          ((null cls) (princ "\n[SD] Kh\\U+00F4ng c\\U+00F3 vi\\U+00EAn nguy\\U+00EAn (F) n\\U+00E0o \\U+0111\\U+1EC3 ki\\U+1EC3m tra."))
          (t
           (setq main (car cls) lay (sd:make-layer "SD-RON-LECH" 1 "Continuous" 25))
           (sd:cd-clear lay)
           (princ (strcat "\n[SD] SDTRUNGRON: " (itoa (nth 4 rs)) "/" (itoa nin) " vi\\U+00EAn nguy\\U+00EAn \\U+0111\\U+01B0\\U+1EE3c x\\U+00E9t; l\\U+01B0\\U+1EDBi ch\\U+00EDnh " (itoa (caddr main)) " vi\\U+00EAn, "
                          (itoa (length (cdr cls))) " nh\\U+00F3m l\\U+1EC7ch."))
           (if (> nang 0) (princ (strcat "\n  " (itoa nang) " vi\\U+00EAn kh\\U+00E1c h\\U+01B0\\U+1EDBng l\\U+01B0\\U+1EDBi (b\\U+1ECF qua).")))
           (if (> nsz 0) (princ (strcat "\n  " (itoa nsz) " vi\\U+00EAn kh\\U+00E1c kh\\U+1ED5 (b\\U+1ECF qua).")))
           (setq k 0)
           (foreach c (cdr cls)
             (setq k (1+ k) boxes nil)
             (foreach e (cadddr c) (setq boxes (cons (sd:cd-bbox (sd:curve-pts e)) boxes)))
             (princ (strcat "\n  Nh\\U+00F3m " (itoa k) ": " (itoa (caddr c)) " vi\\U+00EAn l\\U+1EC7ch (" (sd:rtos (- (car c) (car main)) 1) ", " (sd:rtos (- (cadr c) (cadr main)) 1)
                            ") mm so v\\U+1EDBi l\\U+01B0\\U+1EDBi ch\\U+00EDnh (tr\\U+1EE5c x theo h\\U+01B0\\U+1EDBng l\\U+01B0\\U+1EDBi); d\\U+1EDDi nh\\U+00F3m (" (sd:rtos (- (car main) (car c)) 1) ", " (sd:rtos (- (cadr main) (cadr c)) 1) ") mm \\U+0111\\U+1EC3 ron tr\\U+00F9ng."))
             (foreach bx (sd:cd-cluster boxes px)
               (sd:cd-cloud bx (* 3.0 sc) (* 8.0 sc) lay)
               (sd:text (list (car bx) (+ (cadddr bx) (* 6.0 sc))) (strcat "RON L\\U+1EC6CH (" (sd:rtos (- (car c) (car main)) 1) ", " (sd:rtos (- (cadr c) (cadr main)) 1) ") mm") (* 2.5 sc) "L" lay)))
           (if (null (cdr cls)) (princ "\n  L\\U+01B0\\U+1EDBi ron li\\U+00EAn t\\U+1EE5c, kh\\U+00F4ng c\\U+00F3 nh\\U+00F3m l\\U+1EC7ch."))))))
    (princ "\n[SD] Kh\\U+00F4ng t\\U+00ECm th\\U+1EA5y vi\\U+00EAn n\\U+00E0o (SDGACH / SDLOT)."))
  (sd:finish))

;;; --------------------------------------------------------------------------
;;;  SDKIEMTONG - Luot kiem tong: ho so so lieu, vien hep / nho / thieu ma, ron khong deu, luoi ron lech, chuoi cao do; bao cao + CSV
;;; --------------------------------------------------------------------------
(defun c:SDKIEMTONG (/ ss tl i hep nho tolr tol jt tolg full fr ar mn nhep nnho nmat prs gaps med nbad rs cls nns n rows msgs m sc pt fn f sole)
  (sd:begin)
  (if (sd:dlg "L\\U+01B0\\U+1EE3t ki\\U+1EC3m t\\U+1ED5ng (SDKIEMTONG)"
              (list (list "hep" "Vi\\U+00EAn c\\U+1EAFt h\\U+1EB9p h\\U+01A1n (mm) b\\U+1ECB b\\U+00E1o" 'real (sd:cfg "KT-HEP" 50.0))
                    (list "nho" "Vi\\U+00EAn c\\U+1EAFt nh\\U+1ECF h\\U+01A1n (% vi\\U+00EAn nguy\\U+00EAn) b\\U+1ECB b\\U+00E1o" 'real (sd:cfg "KT-NHO" 15.0))
                    (list "tolr" "Ron l\\U+1EC7ch so v\\U+1EDBi ron ph\\U+1ED5 bi\\U+1EBFn qu\\U+00E1 (mm) b\\U+1ECB b\\U+00E1o" 'real (sd:cfg "KT-TOLR" 1.0))
                    (list "jt" "B\\U+1EC1 r\\U+1ED9ng ron (mm)" 'real0 (sd:cfg "RON-CU" 2.0))
                    (list "tolg" "L\\U+1EC7ch cho ph\\U+00E9p gi\\U+1EEFa hai l\\U+01B0\\U+1EDBi ron (mm)" 'real (sd:cfg "RG-TOL" 2.0))
                    (list "bang" "Ghi b\\U+00E1o c\\U+00E1o ra b\\U+1EA3n v\\U+1EBD" 'tog nil)))
    (progn
      (setq hep (sd:cfg-put "KT-HEP" (sd:v "hep")) nho (sd:cfg-put "KT-NHO" (sd:v "nho")) tolr (sd:cfg-put "KT-TOLR" (sd:v "tolr"))
            jt (sd:cfg-put "RON-CU" (sd:v "jt")) tolg (sd:cfg-put "RG-TOL" (sd:v "tolg")) sc (sd:sc) tol 15.0 *SD:IFRAME* nil
            sole (= (sd:cfg "RG-KIEU" "Thang") "Sole"))
      ;; 1. ho so so lieu
      (setq nns 0 n 0)
      (foreach k (sd:ho-keys) (setq n (1+ n)) (if (= (sd:ho-state (car k)) "NS") (setq nns (1+ nns))))
      (setq rows (cons (list "H\\U+1ED3 s\\U+01A1 s\\U+1ED1 li\\U+1EC7u (SDHOSO)" (strcat (itoa nns) "/" (itoa n) " s\\U+1ED1 ch\\U+01B0a x\\U+00E1c nh\\U+1EADn") (if (> nns 0) "CH\\U+01AFA X\\U+00C1C NH\\U+1EACN" "\\U+0110\\U+1EA0T")) rows))
      ;; 2 - 4. vien
      (if (setq ss (ssget "_X" '((0 . "LWPOLYLINE") (-4 . "&") (70 . 1) (-3 ("SD_TILE")))))
        (progn
          (setq i 0 nhep 0 nnho 0 nmat 0 nbad 0)
          (repeat (sslength ss) (setq tl (cons (sd:vn-rec (1+ i) (ssname ss i) nil) tl) i (1+ i)))
          (setq tl (reverse tl) full (sd:kt-full tl))
          (foreach r tl
            (setq fr (sd:tile-frame (nth 1 r)) mn (min (cadr fr) (caddr fr)) ar (abs (sd:area (nth 1 r))))
            (if (and (< mn hep) (or (null full) (< ar (* 0.98 full)))) (setq nhep (1+ nhep))
              (if (and full (< ar (* 0.01 nho full))) (setq nnho (1+ nnho)))))
          (setq rows (cons (list "Vi\\U+00EAn c\\U+1EAFt h\\U+1EB9p" (strcat (itoa nhep) " vi\\U+00EAn < " (sd:num hep) " mm") (if (> nhep 0) "C\\U+1EA2NH B\\U+00C1O" "\\U+0110\\U+1EA0T")) rows)
                rows (cons (list "Vi\\U+00EAn c\\U+1EAFt nh\\U+1ECF" (strcat (itoa nnho) " vi\\U+00EAn < " (sd:num nho) "% vi\\U+00EAn nguy\\U+00EAn") (if (> nnho 0) "C\\U+1EA2NH B\\U+00C1O" "\\U+0110\\U+1EA0T")) rows))
          (if (> (length tl) 1500)
            (setq rows (cons (list "Ron kh\\U+00F4ng \\U+0111\\U+1EC1u" (strcat (itoa (length tl)) " vi\\U+00EAn: qu\\U+00E1 nhi\\U+1EC1u, ch\\U+1EA1y SDKTLAT ri\\U+00EAng") "B\\U+1ECE QUA") rows))
            (progn
              (setq prs (sd:vn-pairs tl tol) gaps (sd:sort (mapcar 'caddr prs) '(lambda (a b) (< a b))))
              (if gaps (setq med (nth (/ (length gaps) 2) gaps)))
              (foreach pr prs (if (and med (> (abs (- (caddr pr) med)) tolr)) (setq nbad (1+ nbad))))
              (setq rows (cons (list "Ron kh\\U+00F4ng \\U+0111\\U+1EC1u" (strcat (itoa nbad) " m\\U+1ED1i n\\U+1ED1i l\\U+1EC7ch > " (sd:num tolr) " mm so v\\U+1EDBi ron ph\\U+1ED5 bi\\U+1EBFn " (if med (sd:rtos med 1) "-") " mm") (if (> nbad 0) "C\\U+1EA2NH B\\U+00C1O" "\\U+0110\\U+1EA0T")) rows))))
          (setq rs (sd:rg-scan ss jt tolg sole) cls (car rs))
          (setq rows (cons (list "L\\U+01B0\\U+1EDBi ron li\\U+00EAn t\\U+1EE5c" (cond ((null cls) "kh\\U+00F4ng c\\U+00F3 vi\\U+00EAn nguy\\U+00EAn \\U+0111\\U+1EC3 x\\U+00E9t")
                                                           ((null (cdr cls)) (strcat (itoa (nth 4 rs)) " vi\\U+00EAn nguy\\U+00EAn c\\U+00F9ng m\\U+1ED9t l\\U+01B0\\U+1EDBi"))
                                                           (t (strcat (itoa (length (cdr cls))) " nh\\U+00F3m l\\U+1EC7ch l\\U+01B0\\U+1EDBi ch\\U+00EDnh (ch\\U+1EA1y SDTRUNGRON \\U+0111\\U+1EC3 khoanh)")))
                                 (cond ((null cls) "B\\U+1ECE QUA") ((cdr cls) "C\\U+1EA2NH B\\U+00C1O") (t "\\U+0110\\U+1EA0T"))) rows)))
        (setq rows (cons (list "Vi\\U+00EAn \\U+1ED1p l\\U+00E1t" "kh\\U+00F4ng c\\U+00F3 vi\\U+00EAn n\\U+00E0o trong b\\U+1EA3n v\\U+1EBD" "B\\U+1ECE QUA") rows)))
      ;; 5. chuoi cao do
      (if (vlax-ldata-get "SD" "LC-M")
        (progn
          (setq msgs (sd:lc-check (sd:cfg "LC-M" 0.0) (sd:cfg "LC-BC" 20.0) (sd:cfg "LC-IW" 1.0) (sd:cfg "LC-ID" 1.5) (sd:cfg "HB-RL" -0.05) (sd:cfg "LC-DK" 0.0)))
          (setq rows (cons (list "Chu\\U+1ED7i cao \\U+0111\\U+1ED9 (SDLIENCAODO)" (if msgs (strcat (itoa (length msgs)) " c\\U+1EA3nh b\\U+00E1o (ch\\U+1EA1y SDLIENCAODO xem chi ti\\U+1EBFt)") "kh\\U+00F4ng c\\U+00F3 c\\U+1EA3nh b\\U+00E1o") (if msgs "C\\U+1EA2NH B\\U+00C1O" "\\U+0110\\U+1EA0T")) rows)))
        (setq rows (cons (list "Chu\\U+1ED7i cao \\U+0111\\U+1ED9 (SDLIENCAODO)" "ch\\U+01B0a nh\\U+1EADp s\\U+1ED1 li\\U+1EC7u" "B\\U+1ECE QUA") rows)))
      (setq rows (reverse rows) n 0)
      (foreach r rows (if (member (caddr r) '("C\\U+1EA2NH B\\U+00C1O" "CH\\U+01AFA X\\U+00C1C NH\\U+1EACN")) (setq n (1+ n))))
      (princ "\n[SD] SDKIEMTONG: b\\U+00E1o c\\U+00E1o ki\\U+1EC3m t\\U+1ED5ng")
      (foreach r rows (princ (strcat "\n  [" (caddr r) "] " (car r) ": " (cadr r))))
      (princ (strcat "\n  " (itoa n) "/" (itoa (length rows)) " m\\U+1EE5c c\\U+1EA7n x\\U+1EED l\\U+00FD tr\\U+01B0\\U+1EDBc khi ph\\U+00E1t h\\U+00E0nh. M\\U+1EE5c B\\U+1ECE QUA ngh\\U+0129a l\\U+00E0 ch\\U+01B0a ki\\U+1EC3m \\U+0111\\U+01B0\\U+1EE3c, kh\\U+00F4ng ph\\U+1EA3i \\U+0111\\U+1EA1t."))
      (if (and (sd:v "bang") (setq pt (sd:getpt "\n\\U+0110i\\U+1EC3m ch\\U+00E8n b\\U+00E1o c\\U+00E1o (g\\U+00F3c tr\\U+00E1i tr\\U+00EAn) <b\\U+1ECF qua>: " nil)))
        (sd:table2 pt "B\\U+00C1O C\\U+00C1O KI\\U+1EC2M TRA T\\U+1ED4NG" '(("M\\U+1EE4C KI\\U+1EC2M" 52) ("K\\U+1EBET QU\\U+1EA2" 80) ("TR\\U+1EA0NG TH\\U+00C1I" 30))
                   (mapcar '(lambda (r) (list "R" (list (car r) (cadr r) (caddr r)) nil)) rows) -1 sc))
      (if (and (setq fn (sd:csv-name "_KiemTong.csv")) (setq f (sd:open fn "w")))
        (progn
          (write-line "sep=;" f)
          (write-line "Muc kiem;Ket qua;Trang thai" f)
          (foreach r rows (write-line (sd:join r ";") f))
          (princ (strcat "\n[SD] \\U+0110\\U+00E3 xu\\U+1EA5t: " (sd:close f)))))))
  (sd:finish))

;;; --------------------------------------------------------------------------
;;;  SDHOSO - Ho so so lieu du an: cac so dung chung cho nhieu lenh (ron, cao do, doc, du...), co trang thai da xac nhan / chua xac nhan
;;; --------------------------------------------------------------------------
;; (khoa nhan don-vi mac-dinh); khoa chinh la khoa nho cua tung lenh (sd:cfg)
(defun sd:ho-keys ()
  '(("RON-CU" "B\\U+1EC1 r\\U+1ED9ng ron" "mm" 2.0) ("LC-M" "Cao \\U+0111\\U+1ED9 s\\U+00E0n ch\\U+00EDnh ho\\U+00E0n thi\\U+1EC7n" "m" 0.0) ("LC-BC" "S\\U+00E0n WC h\\U+1EA1 so v\\U+1EDBi s\\U+00E0n ch\\U+00EDnh t\\U+1EA1i ng\\U+01B0\\U+1EE1ng c\\U+1EEDa" "mm" 20.0)
    ("LC-IW" "D\\U+1ED1c s\\U+00E0n WC v\\U+1EC1 ph\\U+1EC5u thu" "%" 1.0) ("LC-ID" "D\\U+1ED1c s\\U+00E2n h\\U+1ED3 v\\U+1EC1 ph\\U+1EC5u / r\\U+00E3nh thu" "%" 1.5) ("LC-DK" "Cao \\U+0111\\U+1ED9 s\\U+00E2n h\\U+1ED3 t\\U+1EA1i m\\U+00E9p h\\U+1ED3" "m" 0.0)
    ("HB-RL" "Cao \\U+0111\\U+1ED9 m\\U+1EF1c n\\U+01B0\\U+1EDBc h\\U+1ED3" "m" -0.05) ("HB-D1" "\\U+0110\\U+1ED9 s\\U+00E2u n\\U+01B0\\U+1EDBc \\U+0111\\U+1EA7u n\\U+00F4ng" "mm" 1000.0) ("HB-D2" "\\U+0110\\U+1ED9 s\\U+00E2u n\\U+01B0\\U+1EDBc \\U+0111\\U+1EA7u s\\U+00E2u" "mm" 1500.0)
    ("BC-TD" "D\\U+00E0y \\U+0111\\U+00E1 \\U+0111\\U+1EE9ng t\\U+1EA1i ch\\U+1ED7 \\U+0111\\U+1ED5i cao \\U+0111\\U+1ED9" "mm" 20.0) ("BC-KL" "Keo ch\\U+1EEBa th\\U+00EAm t\\U+1EA1i ch\\U+1ED7 \\U+0111\\U+1ED5i cao \\U+0111\\U+1ED9" "mm" 10.0) ("CD-DU" "D\\U+01B0 m\\U+1EB7c \\U+0111\\U+1ECBnh c\\U+1EA1nh s\\U+00E1t t\\U+01B0\\U+1EDDng" "mm" 10.0)))
;; "XN" khi da xac nhan va gia tri khong doi tu luc xac nhan, nguoc lai "NS" (chua xac nhan: mac dinh, nhap tay chua duyet, hoac da doi sau khi duyet)
(defun sd:ho-state (k / rec cur)
  (setq rec (assoc k (sd:cfg "HOSO-ST" nil)) cur (vlax-ldata-get "SD" k))
  (if (and rec (= (cadr rec) "XN") (numberp cur) (numberp (caddr rec)) (< (abs (- cur (caddr rec))) 1e-6)) "XN" "NS"))
(defun sd:ho-warn (keys / bad)
  (foreach k keys (if (= (sd:ho-state k) "NS") (setq bad (cons (cadr (assoc k (sd:ho-keys))) bad))))
  (if bad (princ (strcat "\n[?] S\\U+1ED1 li\\U+1EC7u ch\\U+01B0a x\\U+00E1c nh\\U+1EADn trong h\\U+1ED3 s\\U+01A1 (SDHOSO): " (sd:join (reverse bad) "; ") "."))))

(defun c:SDHOSO (/ flds k st rows nns pt n)
  (sd:begin)
  (foreach k (sd:ho-keys)
    (setq flds (append flds (list (list (car k) (strcat (cadr k) " (" (caddr k) ")") 'real0 (sd:cfg (car k) (cadddr k)))
                                  (list (strcat "x" (car k)) "   \\U+0111\\U+00E3 x\\U+00E1c nh\\U+1EADn v\\U+1EDBi thi\\U+1EBFt k\\U+1EBF / hi\\U+1EC7n tr\\U+1EA1ng" 'tog (= (sd:ho-state (car k)) "XN"))))))
  ;; 27 muc de hai cot chia dung giua cac cap (so, xac nhan)
  (setq flds (append flds (list (list "bang" "Ghi b\\U+1EA3ng h\\U+1ED3 s\\U+01A1 s\\U+1ED1 li\\U+1EC7u ra b\\U+1EA3n v\\U+1EBD" 'tog nil)
                                (list "n1" "S\\U+1ED1 ch\\U+01B0a x\\U+00E1c nh\\U+1EADn l\\U+00E0 m\\U+1EB7c \\U+0111\\U+1ECBnh ho\\U+1EB7c n\\U+1ED9i suy: c\\U+00E1c l\\U+1EC7nh kh\\U+00E1c s\\U+1EBD c\\U+1EA3nh b\\U+00E1o." 'note)
                                (list "n2" "L\\U+1EC7nh kh\\U+00F4ng t\\U+1EF1 ki\\U+1EC3m ch\\U+1EE9ng s\\U+1ED1: b\\U+1EA1n ch\\U+1ECBu tr\\U+00E1ch nhi\\U+1EC7m khi t\\U+00EDch x\\U+00E1c nh\\U+1EADn." 'note))))
  (if (sd:dlg "H\\U+1ED3 s\\U+01A1 s\\U+1ED1 li\\U+1EC7u d\\U+1EF1 \\U+00E1n (SDHOSO): t\\U+00EDch \\U+0111\\U+00E3 x\\U+00E1c nh\\U+1EADn khi s\\U+1ED1 l\\U+1EA5y t\\U+1EEB thi\\U+1EBFt k\\U+1EBF ho\\U+1EB7c \\U+0111o hi\\U+1EC7n tr\\U+1EA1ng" flds)
    (progn
      (setq nns 0 n 0)
      (foreach k (sd:ho-keys)
        (sd:cfg-put (car k) (cond ((sd:v (car k))) ((cadddr k))))
        (setq st (if (sd:v (strcat "x" (car k))) "XN" "NS") n (1+ n))
        (if (= st "NS") (setq nns (1+ nns)))
        (setq rows (cons (list (car k) st (sd:cfg (car k) (cadddr k))) rows)))
      (sd:cfg-put "HOSO-ST" (reverse rows))
      (princ "\n[SD] SDHOSO: h\\U+1ED3 s\\U+01A1 s\\U+1ED1 li\\U+1EC7u d\\U+1EF1 \\U+00E1n")
      (foreach k (sd:ho-keys)
        (princ (strcat "\n  " (if (= (sd:ho-state (car k)) "XN") "[\\U+0111\\U+00E3 x\\U+00E1c nh\\U+1EADn]   " "[CH\\U+01AFA x\\U+00E1c nh\\U+1EADn] ") (cadr k) " = " (sd:num (sd:cfg (car k) (cadddr k))) " " (caddr k))))
      (princ (strcat "\n  " (itoa nns) "/" (itoa n) " s\\U+1ED1 li\\U+1EC7u ch\\U+01B0a x\\U+00E1c nh\\U+1EADn: s\\U+1ED1 ch\\U+01B0a x\\U+00E1c nh\\U+1EADn l\\U+00E0 m\\U+1EB7c \\U+0111\\U+1ECBnh ho\\U+1EB7c n\\U+1ED9i suy, kh\\U+00F4ng d\\U+00F9ng l\\U+00E0m s\\U+1ED1 cu\\U+1ED1i khi ph\\U+00E1t h\\U+00E0nh b\\U+1EA3n v\\U+1EBD."))
      (if (and (sd:v "bang") (setq pt (sd:getpt "\n\\U+0110i\\U+1EC3m ch\\U+00E8n b\\U+1EA3ng h\\U+1ED3 s\\U+01A1 s\\U+1ED1 li\\U+1EC7u (g\\U+00F3c tr\\U+00E1i tr\\U+00EAn) <b\\U+1ECF qua>: " nil)))
        (sd:table2 pt "H\\U+1ED2 S\\U+01A0 S\\U+1ED0 LI\\U+1EC6U D\\U+1EF0 \\U+00C1N"
                   '(("S\\U+1ED0 LI\\U+1EC6U" 62) ("GI\\U+00C1 TR\\U+1ECA" 22) ("\\U+0110\\U+01A0N V\\U+1ECA" 14) ("TR\\U+1EA0NG TH\\U+00C1I" 34))
                   (mapcar '(lambda (k) (list "R" (list (cadr k) (sd:num (sd:cfg (car k) (cadddr k))) (caddr k)
                                                         (if (= (sd:ho-state (car k)) "XN") "\\U+0110\\U+00C3 X\\U+00C1C NH\\U+1EACN" "CH\\U+01AFA X\\U+00C1C NH\\U+1EACN")) nil))
                           (sd:ho-keys))
                   -1 (sd:sc)))))
  (sd:finish))

;;; --------------------------------------------------------------------------
;;;  SDDIMVIEN - Dim tu dong theo hang vien: chuoi tung vien (+ tong), ngang / dung, ngoai phong hoac xuyen trong phong
;;; --------------------------------------------------------------------------
;; Cac vien (khong tinh lo X) trong he luoi xoay ang0: ((xmin xmax ymin ymax) ...)
(defun sd:dv-tiles (ss ang0 / i e xd pts lp r)
  (setq i 0)
  (repeat (sslength ss)
    (setq e (ssname ss i) i (1+ i) xd (mapcar 'cdr (cdadr (assoc -3 (entget e '("SD_TILE"))))))
    (if (and (>= (length xd) 12) (/= (nth 1 xd) "X") (>= (length (setq pts (sd:curve-pts e))) 3))
      (progn
        (setq lp (mapcar '(lambda (p) (sd:rot (list (car p) (cadr p)) (- ang0))) pts))
        (setq r (cons (list (apply 'min (mapcar 'car lp)) (apply 'max (mapcar 'car lp))
                            (apply 'min (mapcar 'cadr lp)) (apply 'max (mapcar 'cadr lp)))
                      r)))))
  r)
;; Chuoi toa do ron / mep theo mot phuong: ia ib = chi so min / max doc theo phuong dim, ja jb = chi so phuong con lai, coord = duong cat
(defun sd:dv-chain (tl ia ib ja jb coord jt / row pts prev)
  (setq row (vl-remove-if-not '(lambda (r) (and (<= (nth ja r) coord) (>= (nth jb r) coord))) tl)
        row (vl-sort row '(lambda (a b) (< (nth ia a) (nth ia b)))))
  (if row
    (progn
      (setq pts (list (nth ia (car row))) prev (car row))
      (foreach r (cdr row)
        (if (<= (- (nth ia r) (nth ib prev)) (+ jt 1.5))
          (setq pts (cons (/ (+ (nth ia r) (nth ib prev)) 2.0) pts))
          (setq pts (cons (nth ia r) (cons (nth ib prev) pts))))
        (setq prev r))
      (reverse (cons (nth ib prev) pts)))))
;; Dim mot doan (hai diem toa do luoi p1 p2) theo truc ax ("X" / "Y" cua luoi), duong dim di qua diem luoi pd
(defun sd:dv-dim1 (p1 p2 ax ang0 pd / g1 g2 gd q n)
  (setq g1 (sd:rot p1 ang0) g2 (sd:rot p2 ang0) gd (sd:rot pd ang0)
        q (fix (+ 0.5 (/ ang0 (/ pi 2.0)))) n (abs (- ang0 (* q (/ pi 2.0)))))
  (if (< n 0.002)
    (sd:dim g1 g2 (if (= (= ax "X") (= (rem (abs q) 2) 0)) "H" "V") gd)
    (sd:dimal g1 g2 gd)))
;; Ve mot chuoi (+ tong neu hai hang); ax = "X" (dim ngang luoi) / "Y"; lc = toa do con lai cua duong dim; dir = +1 / -1 huong ra ngoai de dat dong tong
(defun sd:dv-draw (pts ax ang0 lc dir two off2 / a)
  (setq a pts)
  (while (cadr a)
    (sd:dv-dim1 (if (= ax "X") (list (car a) lc) (list lc (car a))) (if (= ax "X") (list (cadr a) lc) (list lc (cadr a))) ax ang0
                (if (= ax "X") (list (car a) lc) (list lc (car a))))
    (setq a (cdr a)))
  (if (and two (cadr pts))
    (sd:dv-dim1 (if (= ax "X") (list (car pts) lc) (list lc (car pts))) (if (= ax "X") (list (last pts) lc) (list lc (last pts))) ax ang0
                (if (= ax "X") (list (car pts) (+ lc (* dir off2))) (list (+ lc (* dir off2)) (car pts))))))

(defun c:SDDIMVIEN (/ ss tl sc fr ang0 huong hang vitri canh kc jt two xl yl xmin xmax ymin ymax pt lp h0 w0 ycand pts n nd)
  (sd:begin)
  (if (setq ss (sd:select-tiles "\nCh\\U+1ECDn c\\U+00E1c vi\\U+00EAn c\\U+1EE7a ph\\U+00F2ng c\\U+1EA7n dim (Enter = t\\U+1EA5t c\\U+1EA3 trong b\\U+1EA3n v\\U+1EBD): "))
    (if (sd:dlg "Dim t\\U+1EF1 \\U+0111\\U+1ED9ng theo h\\U+00E0ng vi\\U+00EAn (SDDIMVIEN)"
                (list (list "huong" "H\\U+01B0\\U+1EDBng dim" 'kw (sd:cfg "DV-HUONG" "Ca") '(("Ngang" . "Ngang theo l\\U+01B0\\U+1EDBi") ("Dung" . "\\U+0110\\U+1EE9ng theo l\\U+01B0\\U+1EDBi") ("Ca" . "C\\U+1EA3 hai")))
                      (list "hang" "S\\U+1ED1 h\\U+00E0ng dim" 'kw (sd:cfg "DV-HANG" "Hai") '(("Mot" . "M\\U+1ED9t h\\U+00E0ng: t\\U+1EEBng vi\\U+00EAn") ("Hai" . "Hai h\\U+00E0ng: t\\U+1EEBng vi\\U+00EAn + t\\U+1ED5ng")))
                      (list "vitri" "V\\U+1ECB tr\\U+00ED \\U+0111\\U+01B0\\U+1EDDng dim" 'kw (sd:cfg "DV-VITRI" "Ngoai") '(("Ngoai" . "Ngo\\U+00E0i ph\\U+00F2ng (h\\U+00E0ng vi\\U+00EAn s\\U+00E1t m\\U+00E9p)") ("Trong" . "Trong ph\\U+00F2ng (\\U+0111i qua \\U+0111i\\U+1EC3m ch\\U+1ECDn)")))
                      (list "canh" "Ph\\U+00EDa \\U+0111\\U+1EB7t dim ngo\\U+00E0i ph\\U+00F2ng" 'kw (sd:cfg "DV-CANH" "DT") '(("DT" . "D\\U+01B0\\U+1EDBi v\\U+00E0 tr\\U+00E1i") ("TP" . "Tr\\U+00EAn v\\U+00E0 ph\\U+1EA3i") ("Bon" . "C\\U+1EA3 b\\U+1ED1n ph\\U+00EDa")))
                      (list "kc" "Kho\\U+1EA3ng c\\U+00E1ch \\U+0111\\U+01B0\\U+1EDDng dim \\U+0111\\U+1EBFn m\\U+00E9p ph\\U+00F2ng (mm)" 'real (sd:cfg "DV-KC" (* 12.0 (sd:sc))))
                      (list "jt" "B\\U+1EC1 r\\U+1ED9ng ron (mm; ron nh\\U+1ECF h\\U+01A1n th\\U+00EC g\\U+1ED9p v\\U+00E0o b\\U+01B0\\U+1EDBc vi\\U+00EAn)" 'real0 (sd:cfg "RON-CU" 2.0))))
      (progn
        (setq huong (sd:cfg-put "DV-HUONG" (sd:v "huong")) hang (sd:cfg-put "DV-HANG" (sd:v "hang")) vitri (sd:cfg-put "DV-VITRI" (sd:v "vitri"))
              canh (sd:cfg-put "DV-CANH" (sd:v "canh")) kc (sd:cfg-put "DV-KC" (sd:v "kc")) jt (sd:cfg-put "RON-CU" (sd:v "jt"))
              two (= hang "Hai") sc (sd:sc) *SD:IFRAME* nil)
        ;; goc luoi = canh dai nhat cua vien dau tien
        (setq fr (sd:tile-frame (sd:curve-pts (ssname ss 0))) ang0 (car fr))
        (setq tl (sd:dv-tiles ss ang0))
        (if (null tl)
          (princ "\n[SD] Kh\\U+00F4ng c\\U+00F3 vi\\U+00EAn n\\U+00E0o \\U+0111\\U+1EC3 dim.")
          (progn
            (setq xmin (apply 'min (mapcar 'car tl)) xmax (apply 'max (mapcar 'cadr tl))
                  ymin (apply 'min (mapcar 'caddr tl)) ymax (apply 'max (mapcar 'cadddr tl))
                  h0 (- (cadddr (car tl)) (caddr (car tl))) w0 (- (cadr (car tl)) (car (car tl))) n 0)
            (sd:use-dimstyle sc)
            (if (= vitri "Trong")
              (if (setq pt (sd:getpt "\n\\U+0110i\\U+1EC3m n\\U+1EB1m tr\\U+00EAn h\\U+00E0ng / c\\U+1ED9t vi\\U+00EAn c\\U+1EA7n dim trong ph\\U+00F2ng: " nil))
                (progn
                  (setq pt (sd:rot (list (car pt) (cadr pt)) (- ang0)))
                  (if (member huong '("Ngang" "Ca"))
                    (if (setq pts (sd:dv-chain tl 0 1 2 3 (cadr pt) jt))
                      (progn (sd:dv-draw pts "X" ang0 (cadr pt) 1 two (* 8.0 sc)) (setq n (+ n (1- (length pts)))))))
                  (if (member huong '("Dung" "Ca"))
                    (if (setq pts (sd:dv-chain tl 2 3 0 1 (car pt) jt))
                      (progn (sd:dv-draw pts "Y" ang0 (car pt) 1 two (* 8.0 sc)) (setq n (+ n (1- (length pts)))))))))
              (progn
                ;; ngoai phong: lay hang / cot sat mep (thu vai vi tri cho den khi gap hang co vien)
                (foreach side (cond ((= canh "DT") '("D" "T")) ((= canh "TP") '("U" "P")) (t '("D" "U" "T" "P")))
                  (cond
                    ((and (member side '("D" "U")) (member huong '("Ngang" "Ca")))
                     (setq pts nil nd 0)
                     (while (and (null pts) (< nd 12))
                       (setq ycand (if (= side "D") (+ ymin (* nd 0.1 h0) 1.0) (- ymax (* nd 0.1 h0) 1.0))
                             pts (sd:dv-chain tl 0 1 2 3 ycand jt) nd (1+ nd)))
                     (if pts
                       (progn (sd:dv-draw pts "X" ang0 (if (= side "D") (- ymin kc) (+ ymax kc)) (if (= side "D") -1 1) two (* 8.0 sc))
                              (setq n (+ n (1- (length pts)))))))
                    ((and (member side '("T" "P")) (member huong '("Dung" "Ca")))
                     (setq pts nil nd 0)
                     (while (and (null pts) (< nd 12))
                       (setq xl (if (= side "T") (+ xmin (* nd 0.1 w0) 1.0) (- xmax (* nd 0.1 w0) 1.0))
                             pts (sd:dv-chain tl 2 3 0 1 xl jt) nd (1+ nd)))
                     (if pts
                       (progn (sd:dv-draw pts "Y" ang0 (if (= side "T") (- xmin kc) (+ xmax kc)) (if (= side "T") -1 1) two (* 8.0 sc))
                              (setq n (+ n (1- (length pts)))))))))))
            (princ (strcat "\n[SD] SDDIMVIEN: \\U+0111\\U+00E3 dim " (itoa n) " \\U+0111o\\U+1EA1n (layer SD-KICHTHUOC; b\\U+01B0\\U+1EDBc vi\\U+00EAn = vi\\U+00EAn + ron " (sd:rtos jt 1) " mm)."))
            (princ "\n  Dim ghi k\\U+00EDch th\\U+01B0\\U+1EDBc h\\U+00ECnh h\\U+1ECDc hi\\U+1EC7n c\\U+00F3 c\\U+1EE7a b\\U+1EA3n v\\U+1EBD: n\\U+1EBFu s\\U+1EEDa vi\\U+00EAn sau \\U+0111\\U+00F3 ph\\U+1EA3i dim l\\U+1EA1i.")))))
    (princ "\n[SD] Kh\\U+00F4ng t\\U+00ECm th\\U+1EA5y vi\\U+00EAn n\\U+00E0o (SDGACH / SDLOT)."))
  (sd:finish))

;;; --------------------------------------------------------------------------
;;;  SDOPTUONG - Op tuong trung ron san: tuong trai phang theo canh, ron dung tuong trung ron san, kiem tra trung, hang tren cung
;;; --------------------------------------------------------------------------
;; Gom cac gia tri da sap thanh tam cum (gan nhau <= g)
(defun sd:ot-cluster (ts g / r cur)
  (foreach x ts
    (if (and cur (<= (- x (car cur)) g))
      (setq cur (cons x cur))
      (progn (if cur (setq r (cons (/ (apply '+ cur) (float (length cur))) r)))
             (setq cur (list x)))))
  (if cur (setq r (cons (/ (apply '+ cur) (float (length cur))) r)))
  (reverse r))
;; Cac ron san cat mat tuong p->q: toa do doc tuong (mm tu p) cua tam moi ron; tiles = ds da giac; near = khoang sat tuong
(defun sd:ot-fjoints (tiles p q near jt / len ux uy ts d tp)
  (setq len (distance p q) ux (/ (- (car q) (car p)) len) uy (/ (- (cadr q) (cadr p)) len))
  (foreach pts tiles
    (foreach v pts
      (setq d (abs (- (* (- (car v) (car p)) uy) (* (- (cadr v) (cadr p)) ux)))
            tp (+ (* (- (car v) (car p)) ux) (* (- (cadr v) (cadr p)) uy)))
      (if (and (<= d near) (> tp -1.0) (< tp (+ len 1.0))) (setq ts (cons tp ts)))))
  (sd:ot-cluster (vl-sort ts '<) (+ jt 2.0)))
;; Tam ron tuong doc theo 1 canh dai len: bat dau tu ron san j0 (nil = goc canh), buoc pw
(defun sd:ot-wjoints (j0 len pw jt / r x)
  (setq x (if j0 (- j0 (* pw (fix (+ 1.0 (/ j0 pw))))) (- (/ jt 2.0))))
  (while (< x (+ len pw))
    (setq r (cons x r) x (+ x pw)))
  (reverse r))

(defun c:SDOPTUONG (/ sc es e pts closed segs tl ssf i xd W H jt cao h0 near tol doors p1 p2 d1 d2 ep dacc p q len fa
                      fj wj j0 iv a b ca cb x0 x1 nf ncut area rows k y0 y1 ntot nmatch f dmin lay1 lay2 hcut j)
  (sd:begin)
  (setq sc (sd:sc))
  (setq es (entsel "\nCh\\U+1ECDn \\U+0111\\U+01B0\\U+1EDDng m\\U+1EB7t t\\U+01B0\\U+1EDDng (polyline, k\\U+00EDn ho\\U+1EB7c h\\U+1EDF): "))
  (if (not (and es (= (cdr (assoc 0 (entget (car es)))) "LWPOLYLINE")))
    (princ "\n[SD] C\\U+1EA7n ch\\U+1ECDn 1 polyline th\\U+1EC3 hi\\U+1EC7n m\\U+1EB7t t\\U+01B0\\U+1EDDng.")
    (if (sd:dlg "\\U+1ED0p t\\U+01B0\\U+1EDDng tr\\U+00F9ng ron s\\U+00E0n (SDOPTUONG)"
                (list (list "W" "Vi\\U+00EAn \\U+1ED1p: r\\U+1ED9ng d\\U+1ECDc t\\U+01B0\\U+1EDDng (mm)" 'real (sd:cfg "OT-W" 600.0))
                      (list "H" "Vi\\U+00EAn \\U+1ED1p: cao (mm)" 'real (sd:cfg "OT-H" 300.0))
                      (list "jt" "B\\U+1EC1 r\\U+1ED9ng ron (mm)" 'real0 (sd:cfg "RON-CU" 2.0))
                      (list "cao" "Chi\\U+1EC1u cao \\U+1ED1p t\\U+1EEB m\\U+1EB7t s\\U+00E0n ho\\U+00E0n thi\\U+1EC7n (mm)" 'real (sd:cfg "OT-CAO" 2400.0))
                      (list "h0" "\\U+1ED0p b\\U+1EAFt \\U+0111\\U+1EA7u cao h\\U+01A1n s\\U+00E0n (mm; ch\\U+1EEBa len ch\\U+00E2n t\\U+01B0\\U+1EDDng)" 'real0 (sd:cfg "OT-H0" 0.0))
                      (list "near" "Ron s\\U+00E0n t\\U+00EDnh khi vi\\U+00EAn s\\U+00E0n c\\U+00E1ch t\\U+01B0\\U+1EDDng kh\\U+00F4ng qu\\U+00E1 (mm)" 'real (sd:cfg "OT-NEAR" 60.0))
                      (list "tol" "Ron t\\U+01B0\\U+1EDDng coi l\\U+00E0 tr\\U+00F9ng ron s\\U+00E0n khi l\\U+1EC7ch kh\\U+00F4ng qu\\U+00E1 (mm)" 'real (sd:cfg "OT-TOL" 2.0))))
      (progn
        (setq W (sd:cfg-put "OT-W" (sd:v "W")) H (sd:cfg-put "OT-H" (sd:v "H")) jt (sd:cfg-put "RON-CU" (sd:v "jt"))
              cao (sd:cfg-put "OT-CAO" (sd:v "cao")) h0 (sd:cfg-put "OT-H0" (sd:v "h0"))
              near (sd:cfg-put "OT-NEAR" (sd:v "near")) tol (sd:cfg-put "OT-TOL" (sd:v "tol"))
              e (car es) closed (vlax-curve-isClosed e) pts (sd:curve-pts e) i 0)
        (sd:ho-warn '("RON-CU"))
        (princ "\nCh\\U+1ECDn c\\U+00E1c vi\\U+00EAn S\\U+00C0N c\\U+1EE7a ph\\U+00F2ng n\\U+00E0y \\U+0111\\U+1EC3 l\\U+1EA5y ron s\\U+00E0n (Enter = b\\U+1ECF qua, \\U+1ED1p b\\U+1EAFt \\U+0111\\U+1EA7u t\\U+1EEB g\\U+00F3c t\\U+01B0\\U+1EDDng): ")
        (if (setq ssf (ssget '((-3 ("SD_TILE")))))
          (repeat (sslength ssf)
            (setq xd (mapcar 'cdr (cdadr (assoc -3 (entget (ssname ssf i) '("SD_TILE"))))) )
            (if (and (>= (length xd) 12) (/= (nth 1 xd) "X")) (setq tl (cons (sd:curve-pts (ssname ssf i)) tl)))
            (setq i (1+ i))))
        (while (and (setq p1 (sd:getpt "\n\\U+0110i\\U+1EC3m \\U+0111\\U+1EA7u l\\U+1ED7 c\\U+1EEDa tr\\U+00EAn \\U+0111\\U+01B0\\U+1EDDng t\\U+01B0\\U+1EDDng <Enter = h\\U+1EBFt>: " nil))
                    (setq p2 (sd:getpt "\n\\U+0110i\\U+1EC3m cu\\U+1ED1i l\\U+1ED7 c\\U+1EEDa: " p1)))
          (setq d1 (vlax-curve-getDistAtPoint e (vlax-curve-getClosestPointTo e p1))
                d2 (vlax-curve-getDistAtPoint e (vlax-curve-getClosestPointTo e p2))
                doors (cons (list (min d1 d2) (max d1 d2)) doors)))
        (setq doors (sd:sort doors '(lambda (x y) (< (car x) (car y))))
              segs (mapcar 'list pts (if closed (append (cdr pts) (list (car pts))) (cdr pts))))
        (if (setq ep (sd:getpt "\n\\U+0110i\\U+1EC3m ch\\U+00E8n m\\U+1EB7t \\U+0111\\U+1EE9ng \\U+1ED1p (\\U+0111\\U+1EA7u t\\U+01B0\\U+1EDDng, cao \\U+0111\\U+1ED9 s\\U+00E0n): " nil))
          (progn
            (sd:make-layer "SD-OP-TUONG" 7 "Continuous" 18)
            (setq lay1 (sd:make-layer "SD-OP-RON-TRUNG" 3 "Continuous" 18) lay2 (sd:make-layer "SD-OP-RON-LECH" 1 "Continuous" 25)
                  dacc 0.0 nf 0 ncut 0 area 0.0 ntot 0 nmatch 0 hcut nil)
            (foreach s segs
              (setq p (car s) q (cadr s) len (distance p q)
                    fj (if tl (sd:ot-fjoints tl p q near jt))
                    j0 (if fj (car fj))
                    wj (sd:ot-wjoints j0 len (+ W jt) jt))
              ;; cac doan lien tuc (tru lo cua) cua canh nay, toa do cuc bo
              (foreach iv (sd:subtract dacc (+ dacc len) doors)
                (setq a (- (car iv) dacc) b (- (cadr iv) dacc))
                (foreach j wj
                  (setq ca (max a (+ j (/ jt 2.0))) cb (min b (- (+ j (+ W jt)) (/ jt 2.0))))
                  (if (> (- cb ca) 1.0)
                    (progn
                      (setq k 0 y0 h0)
                      (while (< y0 (- cao 1.0))
                        (setq y1 (min (+ y0 H) cao))
                        (sd:rect (sd:p+ ep (+ dacc ca) y0) (- cb ca) (- y1 y0) "SD-OP-TUONG")
                        (if (and (equal (- cb ca) W 0.5) (equal (- y1 y0) H 0.5)) (setq nf (1+ nf)) (setq ncut (1+ ncut)))
                        (setq area (+ area (* (- cb ca) (- y1 y0))) y0 (+ y0 H jt) k (1+ k))
                        (if (and (>= y0 cao) (< (- y1 (- y0 H jt)) H)) (setq hcut (- y1 (- y0 H jt)))))))))
              ;; kiem tra trung ron: tung ron san trong doan nay
              (foreach f fj
                (if (and (> f 5.0) (< f (- len 5.0)))
                  (progn
                    (setq dmin (apply 'min (mapcar '(lambda (j) (abs (- f j))) wj)) ntot (1+ ntot))
                    (if (<= dmin tol)
                      (progn (setq nmatch (1+ nmatch))
                             (sd:line (sd:p+ ep (+ dacc f) (* -4.0 sc)) (sd:p+ ep (+ dacc f) (* -12.0 sc)) lay1))
                      (progn (sd:line (sd:p+ ep (+ dacc f) (* -4.0 sc)) (sd:p+ ep (+ dacc f) (* -12.0 sc)) lay2)
                             (sd:text (sd:p+ ep (+ dacc f) (* -14.0 sc)) (strcat "l\\U+1EC7ch " (sd:rtos dmin 1)) (* 2.0 sc) "MC" lay2))))))
              (setq dacc (+ dacc len)))
            (sd:line ep (sd:p+ ep dacc 0) "SD-OP-TUONG")
            (sd:text (sd:p+ ep 0 (+ cao (* 12.0 sc)))
                     (strcat "M\\U+1EB6T \\U+0110\\U+1EE8NG \\U+1ED0P T\\U+01AF\\U+1EDCNG " (sd:num W) "\\U+00D7" (sd:num H) ", ron " (sd:num jt) ", cao " (sd:num cao) ": " (itoa nf) " vi\\U+00EAn nguy\\U+00EAn, " (itoa ncut) " vi\\U+00EAn c\\U+1EAFt, " (sd:rtos (/ area 1e6) 2) " m\\U+00B2")
                     (* 3.0 sc) "L" "SD-CHU")
            (princ (strcat "\n[SD] SDOPTUONG: " (itoa nf) " vi\\U+00EAn nguy\\U+00EAn + " (itoa ncut) " vi\\U+00EAn c\\U+1EAFt, " (sd:rtos (/ area 1e6) 2) " m\\U+00B2."))
            (if tl
              (progn
                (princ (strcat "\n  Ron s\\U+00E0n c\\U+1EAFt t\\U+01B0\\U+1EDDng: " (itoa ntot) ", tr\\U+00F9ng ron t\\U+01B0\\U+1EDDng (l\\U+1EC7ch \\U+2264 " (sd:num tol) " mm): " (itoa nmatch)
                               (if (> ntot 0) (strcat " (" (sd:rtos (/ (* 100.0 nmatch) ntot) 0) "%)") "") "."))
                (if (and (> ntot 0) (< nmatch ntot))
                  (princ (strcat "\n  [!] " (itoa (- ntot nmatch)) " ron s\\U+00E0n kh\\U+00F4ng tr\\U+00F9ng ron t\\U+01B0\\U+1EDDng (v\\U+1EA1ch \\U+0111\\U+1ECF SD-OP-RON-LECH). Mu\\U+1ED1n tr\\U+00F9ng h\\U+1EBFt: r\\U+1ED9ng vi\\U+00EAn \\U+1ED1p + ron = b\\U+01B0\\U+1EDBc vi\\U+00EAn s\\U+00E0n d\\U+1ECDc t\\U+01B0\\U+1EDDng ho\\U+1EB7c \\U+01B0\\U+1EDBc s\\U+1ED1 c\\U+1EE7a n\\U+00F3, v\\U+00E0 \\U+0111\\U+1ED5i r\\U+1ED9ng vi\\U+00EAn \\U+1ED1p / ron cho kh\\U+1EDBp.")))
                (if (and (> ntot 0) (= nmatch ntot)) (princ "\n  Ron t\\U+01B0\\U+1EDDng tr\\U+00F9ng to\\U+00E0n b\\U+1ED9 ron s\\U+00E0n d\\U+1ECDc t\\U+01B0\\U+1EDDng.")))
              (princ "\n  Ch\\U+01B0a ch\\U+1ECDn vi\\U+00EAn s\\U+00E0n: ron t\\U+01B0\\U+1EDDng b\\U+1EAFt \\U+0111\\U+1EA7u t\\U+1EEB g\\U+00F3c t\\U+01B0\\U+1EDDng, ch\\U+01B0a ki\\U+1EC3m tra tr\\U+00F9ng ron s\\U+00E0n."))
            (if (and hcut (< hcut 50.0)) (princ (strcat "\n  [!] H\\U+00E0ng \\U+1ED1p tr\\U+00EAn c\\U+00F9ng ch\\U+1EC9 cao " (sd:rtos hcut 0) " mm: n\\U+00EAn \\U+0111\\U+1ED5i chi\\U+1EC1u cao \\U+1ED1p ho\\U+1EB7c \\U+0111i\\U+1EC3m b\\U+1EAFt \\U+0111\\U+1EA7u.")))
            (princ "\n  Ron \\U+0111\\U+1EE9ng t\\U+01B0\\U+1EDDng theo ron s\\U+00E0n d\\U+1ECDc t\\U+01B0\\U+1EDDng; ron ngang chia t\\U+1EEB m\\U+1EB7t s\\U+00E0n (ho\\U+1EB7c t\\U+1EEB cao \\U+0111\\U+1ED9 ch\\U+1EEBa len) l\\U+00EAn. L\\U+1ED7 c\\U+1EEDa ch\\U+1EC9 x\\U+00E9t theo chi\\U+1EC1u d\\U+1ECDc t\\U+01B0\\U+1EDDng, ch\\U+01B0a tr\\U+1EEB cao l\\U+1ED7 c\\U+1EEDa."))))))
  (sd:finish))

;;; --------------------------------------------------------------------------
;;;  SDVAN - Kiem tra van da lien tuc giua cac vien ke nhau (dua vao vi tri cat tren tam do SDANHDA ghi lai)
;;;  SDKTLAT - Kiem tra ban ve lat: vien cat hep / nho, ron khong deu, vien chong nhau, o thieu ma vat lieu
;;; --------------------------------------------------------------------------
;; Hai da giac ke nhau: co 1 cap canh gan song song, cach <= tol, phan chong chieu dai >= 30. Tra ve khoang cach ron trung binh, hoac nil
(defun sd:vn-adj (pa pb tol / a1 b1 l ux uy d1 d2 t1 t2 ov r)
  (setq a1 (last pa))
  (foreach a2 pa
    (setq l (distance a1 a2) b1 (last pb))
    (if (> l 1e-6)
      (progn
        (setq ux (/ (- (car a2) (car a1)) l) uy (/ (- (cadr a2) (cadr a1)) l))
        (foreach b2 pb
          (if (null r)
            (progn
              (setq d1 (- (* (- (car b1) (car a1)) uy) (* (- (cadr b1) (cadr a1)) ux))
                    d2 (- (* (- (car b2) (car a1)) uy) (* (- (cadr b2) (cadr a1)) ux))
                    t1 (+ (* (- (car b1) (car a1)) ux) (* (- (cadr b1) (cadr a1)) uy))
                    t2 (+ (* (- (car b2) (car a1)) ux) (* (- (cadr b2) (cadr a1)) uy))
                    ov (- (min l (max t1 t2)) (max 0.0 (min t1 t2))))
              (if (and (<= (abs d1) tol) (<= (abs d2) tol) (>= ov 30.0))
                (setq r (/ (+ (abs d1) (abs d2)) 2.0)))))
          (setq b1 b2))))
    (setq a1 a2))
  r)

;; Ban ghi SDANHDA (id cx cy tam sx sy rong cao goc) ma tam do nam trong vien, nil neu khong co
(defun sd:vn-data (pts c r lk / res)
  (foreach x lk
    (if (and (null res) (<= (distance (list (cadr x) (caddr x)) c) (+ r 1.0))
             (sd:inpoly (list (cadr x) (caddr x)) pts))
      (setq res x)))
  res)

;; Ban ghi vien: (stt da-giac tam ban-kinh ename du-lieu-cat)
(defun sd:vn-rec (idx e lk / pts cx cy n r)
  (setq pts (sd:curve-pts e) n (float (length pts))
        cx (/ (apply '+ (mapcar 'car pts)) n) cy (/ (apply '+ (mapcar 'cadr pts)) n)
        r (apply 'max (mapcar '(lambda (q) (distance (list cx cy) q)) pts)))
  (list idx pts (list cx cy) r e (if lk (sd:vn-data pts (list cx cy) r lk))))

;; Cac cap vien ke nhau: ((a b ron) ...)
(defun sd:vn-pairs (tl tol / r rest a g)
  (setq rest tl)
  (while rest
    (setq a (car rest) rest (cdr rest))
    (foreach b rest
      (if (<= (distance (nth 2 a) (nth 2 b)) (+ (nth 3 a) (nth 3 b) tol))
        (if (setq g (sd:vn-adj (nth 1 a) (nth 1 b) tol))
          (setq r (cons (list a b g) r))))))
  r)

;; Hai vien ke nhau co cung 1 mieng van khong: (T lech) hoac (ly-do lech)
(defun sd:vn-cont (a b tolc / ca cb e dx dy ang d)
  (setq ca (nth 5 a) cb (nth 5 b))
  (cond
    ((or (null ca) (null cb) (null (nth 3 ca)) (null (nth 3 cb)) (null (nth 4 ca)) (null (nth 4 cb)))
     (list "khong co du lieu cat" 0.0))
    ((/= (nth 3 ca) (nth 3 cb)) (list "khac tam da" 0.0))
    ((> (abs (rem (- (nth 8 ca) (nth 8 cb)) (* 2.0 pi))) 0.02) (list "khac huong van" 0.0))
    (t
     (setq ang (nth 8 ca)
           e (sd:rot (list (- (car (nth 2 b)) (car (nth 2 a))) (- (cadr (nth 2 b)) (cadr (nth 2 a)))) (- ang))
           dx (- (+ (nth 4 cb) (/ (nth 6 cb) 2.0)) (+ (nth 4 ca) (/ (nth 6 ca) 2.0)))
           dy (- (+ (nth 5 cb) (/ (nth 7 cb) 2.0)) (+ (nth 5 ca) (/ (nth 7 ca) 2.0)))
           d (distance (list dx dy) e))
     (if (<= d tolc) (list t d) (list "lech vi tri tren tam" d)))))

;; Ghep van doi xung (bookmatch): hai vien ke nhau phai cat tu 2 tam LIEN TIEP (so tam hon kem 1),
;; cung huong va cung vi tri tren tam (lat guong khi lap). Tra ve (T lech) hoac (ly-do lech)
(defun sd:vn-book (a b tolc / ca cb d)
  (setq ca (nth 5 a) cb (nth 5 b))
  (cond
    ((or (null ca) (null cb) (null (nth 3 ca)) (null (nth 3 cb)) (null (nth 4 ca)) (null (nth 4 cb))
         (not (numberp (nth 3 ca))) (not (numberp (nth 3 cb))))
     (list "khong co du lieu cat" 0.0))
    ((/= (abs (- (nth 3 ca) (nth 3 cb))) 1) (list "khong phai 2 tam lien tiep (bookmatch)" 0.0))
    ((> (abs (rem (- (nth 8 ca) (nth 8 cb)) (* 2.0 pi))) 0.02) (list "khac huong van" 0.0))
    (t (setq d (distance (list (+ (nth 4 ca) (/ (nth 6 ca) 2.0)) (+ (nth 5 ca) (/ (nth 7 ca) 2.0)))
                         (list (+ (nth 4 cb) (/ (nth 6 cb) 2.0)) (+ (nth 5 cb) (/ (nth 7 cb) 2.0)))))
       (if (<= d tolc) (list t d) (list "lech vi tri doi xung tren tam" d)))))

(defun sd:vn-mid (a b) (list (/ (+ (car (nth 2 a)) (car (nth 2 b))) 2.0) (/ (+ (cadr (nth 2 a)) (cadr (nth 2 b))) 2.0)))

(defun c:SDVAN (/ ss tl i lk prs ok bad rs sc reasons fn f rows)
  (sd:begin)
  (setq *SD:IFRAME* nil)
  (if (not (setq lk (vlax-ldata-get "SD" "ANHDA")))
    (princ "\n[SD] Chua co du lieu cat tam: chay SDANHDA truoc (vi tri cat tung vien tren tam duoc ghi lai).")
    (if (sd:dlg "Kiem tra van da lien tuc (SDVAN)"
                (list (list "tol" "Khoang cach ron toi da giua 2 vien ke nhau (mm)" 'real (sd:cfg "VAN-TOL" 15.0))
                      (list "tolc" "Do lech cho phep giua vi tri tren ban ve va tren tam (mm)" 'real (sd:cfg "VAN-TOLC" 15.0))
                      (list "book" "Ghep van doi xung (bookmatch): 2 vien ke nhau cat tu 2 tam lien tiep, cung vi tri" 'tog nil)
                      (list "mark" "Khoanh do cac moi noi bi dut van (layer SD-KIEMTRA)" 'tog t)))
      (progn
        (sd:cfg-put "VAN-TOL" (sd:v "tol")) (sd:cfg-put "VAN-TOLC" (sd:v "tolc"))
        (princ "\nQuet chon cac polyline vien da: ")
        (if (setq ss (ssget '((0 . "LWPOLYLINE") (-4 . "&") (70 . 1))))
          (progn
            (sd:make-layer "SD-KIEMTRA" 1 "Continuous" 35)
            (setq i 0 sc (sd:sc) ok 0 bad 0)
            (repeat (sslength ss) (setq tl (cons (sd:vn-rec (1+ i) (ssname ss i) lk) tl) i (1+ i)))
            (setq tl (reverse tl) prs (sd:vn-pairs tl (sd:v "tol")))
            (foreach pr prs
              (setq rs (if (sd:v "book") (sd:vn-book (car pr) (cadr pr) (sd:v "tolc")) (sd:vn-cont (car pr) (cadr pr) (sd:v "tolc"))))
              (if (eq (car rs) t)
                (setq ok (1+ ok))
                (progn
                  (setq bad (1+ bad) reasons (sd:addcnt (car rs) 1 reasons)
                        rows (cons (list (itoa (car (car pr))) (itoa (car (cadr pr))) (car rs) (sd:rtos (cadr rs) 0)) rows))
                  (if (sd:v "mark") (sd:lk-mark (sd:vn-mid (car pr) (cadr pr)) (* 2.0 sc) "" sc)))))
            (princ (strcat "\n[SD] SDVAN: " (itoa (length tl)) " vien, " (itoa (length prs)) " moi noi giua cac vien ke nhau: "
                           (itoa ok) " lien tuc van (" (sd:rtos (if prs (/ (* 100.0 ok) (length prs)) 0.0) 0) "%), " (itoa bad) " bi dut."))
            (foreach r reasons (princ (strcat "\n   " (car r) ": " (itoa (cdr r)) " moi noi")))
            (if (and rows (setq fn (sd:csv-name "_KiemTraVan.csv")) (setq f (sd:open fn "w")))
              (progn
                (write-line "sep=;" f)
                (write-line "Vien A;Vien B;Ly do;Lech (mm)" f)
                (foreach r (reverse rows) (write-line (sd:join r ";") f))
                (princ (strcat "\n[SD] Da xuat: " (sd:close f))))))
          (princ "\n[SD] Chua chon polyline.")))))
  (sd:finish))

;; Vien nguyen = hinh chu nhat xuat hien nhieu nhat (dai x rong lam tron); tra ve dien tich, nil neu khong co
(defun sd:kt-full (tl / g k e best)
  (foreach r tl
    (if (sd:dm-rect-p (nth 1 r))
      (progn
        (setq e (sd:tile-frame (nth 1 r))
              k (list (fix (+ 0.5 (max (cadr e) (caddr e)))) (fix (+ 0.5 (min (cadr e) (caddr e)))))
              g (sd:addcnt k 1 g)))))
  (foreach x g (if (or (null best) (> (cdr x) (cdr best))) (setq best x)))
  (if best (* (float (car (car best))) (cadr (car best)))))

(defun sd:kt-mat (r / xd)
  (if (setq xd (cdadr (assoc -3 (entget (nth 4 r) '("SD_TILE"))))) (cdr (car xd))))

(defun c:SDKTLAT (/ ss tl i hep nho tolr tol full fr ar mn rows prs gaps med nhep nnho ncho nbad nmat sc fn f ok med1 m g kgap bnd bo dmin nwall nchuyen)
  (sd:begin)
  (setq *SD:IFRAME* nil)
  (if (sd:dlg "Kiem tra ban ve lat (SDKTLAT)"
              (list (list "hep" "Vien cat hep hon (mm) bi bao" 'real (sd:cfg "KT-HEP" 50.0))
                    (list "nho" "Vien cat nho hon (% vien nguyen) bi bao" 'real (sd:cfg "KT-NHO" 15.0))
                    (list "tol" "Khoang cach ron toi da giua 2 vien ke nhau (mm)" 'real (sd:cfg "KT-TOL" 15.0))
                    (list "tolr" "Ron lech so voi ron pho bien qua (mm) bi bao" 'real (sd:cfg "KT-TOLR" 1.0))
                    (list "kgap" "Khe gian no chu vi toi thieu (mm): vien sat tuong ma cach tuong it hon bi bao, 0 = bo qua" 'real0 (sd:cfg "KT-KGAP" 0.0))
                    (list "mark" "Khoanh do cho co van de (layer SD-KIEMTRA)" 'tog t)))
    (progn
      (setq kgap (sd:cfg-put "KT-KGAP" (cond ((sd:v "kgap")) (0.0))))
      (setq hep (sd:cfg-put "KT-HEP" (sd:v "hep")) nho (sd:cfg-put "KT-NHO" (sd:v "nho")) tol (sd:cfg-put "KT-TOL" (sd:v "tol"))
            tolr (sd:cfg-put "KT-TOLR" (sd:v "tolr")) sc (sd:sc))
      (princ "\nQuet chon cac polyline vien da / gach: ")
      (if (setq ss (ssget '((0 . "LWPOLYLINE") (-4 . "&") (70 . 1))))
        (progn
          (sd:make-layer "SD-KIEMTRA" 1 "Continuous" 35)
          (setq i 0 nhep 0 nnho 0 nbad 0 nmat 0 nwall 0 nchuyen 0)
          (if (> kgap 0.0)
            (if (setq bnd (entsel "\nChon polyline bien vung lat (de kiem khe gian no chu vi) <bo qua>: "))
              (setq bo (car bnd))))
          (repeat (sslength ss) (setq tl (cons (sd:vn-rec (1+ i) (ssname ss i) nil) tl) i (1+ i)))
          (setq tl (reverse tl) full (sd:kt-full tl))
          ;; tung vien: hep, nho, thieu ma vat lieu
          (foreach r tl
            (setq fr (sd:tile-frame (nth 1 r)) mn (min (cadr fr) (caddr fr)) ar (abs (sd:area (nth 1 r))))
            (if (not (cdadr (assoc -3 (entget (nth 4 r) '("SD_TILE"))))) (setq nmat (1+ nmat)))
            (if (and (< mn hep) (or (null full) (< ar (* 0.98 full))))
              (progn (setq nhep (1+ nhep) rows (cons (list (itoa (car r)) "vien cat hep" (sd:rtos mn 0)) rows))
                     (if (sd:v "mark") (sd:lk-mark (nth 2 r) (* 3.0 sc) "HEP" sc))))
            ;; khe gian no chu vi: dinh vien nao cach bien < kgap (tru sai so 0.5 mm) thi thieu khe
            (if (and bo (entget bo))
              (progn
                (setq dmin nil)
                (foreach q (nth 1 r)
                  (setq g (distance (list (car q) (cadr q) 0.0)
                                    (vlax-curve-getClosestPointTo bo (list (car q) (cadr q) 0.0))))
                  (if (or (null dmin) (< g dmin)) (setq dmin g)))
                (if (and dmin (< dmin (- kgap 0.5)))
                  (progn (setq nwall (1+ nwall) rows (cons (list (itoa (car r)) "thieu khe gian no sat tuong" (sd:rtos dmin 1)) rows))
                         (if (sd:v "mark") (sd:lk-mark (nth 2 r) (* 3.0 sc) "KHE" sc))))))
            (if (and full (< ar (* 0.01 nho full)) (not (and (< mn hep))))
              (progn (setq nnho (1+ nnho) rows (cons (list (itoa (car r)) "vien cat nho" (sd:rtos (/ ar 100.0) 0)) rows))
                     (if (sd:v "mark") (sd:lk-mark (nth 2 r) (* 3.0 sc) "NHO" sc)))))
          ;; ron khong deu: so voi ron trung vi
          (setq prs (sd:vn-pairs tl tol) gaps (sd:sort (mapcar 'caddr prs) '(lambda (a b) (< a b))))
          (if gaps (setq med (nth (/ (length gaps) 2) gaps)))
          (foreach pr prs
            (if (and med (> (abs (- (caddr pr) med)) tolr))
              (progn (setq nbad (1+ nbad) rows (cons (list (strcat (itoa (car (car pr))) "-" (itoa (car (cadr pr)))) "ron khong deu" (sd:rtos (caddr pr) 1)) rows))
                     (if (sd:v "mark") (sd:lk-mark (sd:vn-mid (car pr) (cadr pr)) (* 2.0 sc) "RON" sc)))))
          ;; chuyen tiep vat lieu: 2 vien ke nhau khac ma vat lieu, ron nho hon kgap -> can khe chuyen tiep
          (if (> kgap 0.0)
            (foreach pr prs
              (if (and (sd:kt-mat (car pr)) (sd:kt-mat (cadr pr))
                       (/= (sd:kt-mat (car pr)) (sd:kt-mat (cadr pr))) (< (caddr pr) (- kgap 0.5)))
                (progn (setq nchuyen (1+ nchuyen)
                             rows (cons (list (strcat (itoa (car (car pr))) "-" (itoa (car (cadr pr)))) "chuyen vat lieu thieu khe" (sd:rtos (caddr pr) 1)) rows))
                       (if (sd:v "mark") (sd:lk-mark (sd:vn-mid (car pr) (cadr pr)) (* 2.0 sc) "CHUYEN" sc))))))
          (princ (strcat "\n[SD] SDKTLAT: " (itoa (length tl)) " vien, " (itoa (length prs)) " moi noi."
                         (if (> kgap 0.0) (strcat "\n   Vien sat tuong thieu khe gian no < " (sd:num kgap) " mm: " (itoa nwall)
                                                  "\n   Cho chuyen vat lieu thieu khe: " (itoa nchuyen)) "")
                         (if full (strcat "\n   Vien nguyen: dien tich " (sd:rtos (/ full 1e6) 3) " m2/vien") "")
                         "\n   Vien cat hep < " (sd:num hep) " mm: " (itoa nhep)
                         "\n   Vien cat nho < " (sd:num nho) "% vien nguyen: " (itoa nnho)
                         "\n   Ron khong deu (pho bien " (if med (sd:rtos med 1) "-") " mm, lech > " (sd:num tolr) "): " (itoa nbad)
                         "\n   Vien chua co ma vat lieu (SD_TILE): " (itoa nmat)))
          (if (and rows (setq fn (sd:csv-name "_KiemTraLat.csv")) (setq f (sd:open fn "w")))
            (progn
              (write-line "sep=;" f)
              (write-line "Vien;Van de;Gia tri (mm hoac cm2)" f)
              (foreach r (reverse rows) (write-line (sd:join r ";") f))
              (princ (strcat "\n[SD] Da xuat: " (sd:close f))))))
        (princ "\n[SD] Chua chon polyline."))))
  (sd:finish))

;;; --------------------------------------------------------------------------
;;;  SDDIEMBD - So sanh cac diem bat dau rai luoi vien: vien cat, vien cat hep, hao hut, goi y diem tot nhat
;;; --------------------------------------------------------------------------
;; Giao da giac pts (co the lom) voi hinh chu nhat [x0 x1] x [y0 y1]: da giac giao (co the suy bien nhung dien tich dung) hoac nil
(defun sd:cl-rect (pts x0 y0 x1 y1 / r)
  (setq r (sd:clipx pts x0 t))
  (if r (setq r (sd:clipx r x1 nil)))
  (if r (setq r (mapcar 'reverse r)))
  (if r (setq r (sd:clipx r y0 t)))
  (if r (setq r (sd:clipx r y1 nil)))
  (if r (mapcar 'reverse r)))

(defun sd:cl-area (pts) (if (and pts (> (length pts) 2)) (abs (sd:area pts)) 0.0))

;; Danh gia luoi vien W x H, ron jt, goc vien trai-duoi tai (ox oy) tren vung rp (tru cac lo holes), toa do da xoay theo luoi.
;; Tra ve (so-vien-nguyen so-vien-cat so-vien-cat-hep canh-hep-nhat hao-hut% )
(defun sd:od-eval (rp holes W H jt ox oy hep / bb x0 y0 x1 y1 px py i j i1 j1 tx ty c a nf nc ns mn cut full bw bh xs ys)
  (setq bb (sd:bbox rp) x0 (car (car bb)) y0 (cadr (car bb)) x1 (car (cadr bb)) y1 (cadr (cadr bb))
        px (+ W jt) py (+ H jt) full (* W H) nf 0 nc 0 ns 0 cut 0.0 mn 1e9
        i (fix (- (/ (- x0 ox) px) 1.0)) i1 (fix (+ (/ (- x1 ox) px) 1.0))
        j1 (fix (+ (/ (- y1 oy) py) 1.0)))
  (while (<= i i1)
    (setq j (fix (- (/ (- y0 oy) py) 1.0)))
    (while (<= j j1)
      (setq tx (+ ox (* i px)) ty (+ oy (* j py)))
      (if (and (< tx x1) (> (+ tx W) x0) (< ty y1) (> (+ ty H) y0))
        (progn
          (setq c (sd:cl-rect rp tx ty (+ tx W) (+ ty H)) a (sd:cl-area c))
          (foreach ho holes (if (> a 1.0) (setq a (- a (sd:cl-area (sd:cl-rect ho tx ty (+ tx W) (+ ty H)))))))
          (if (> a 1.0)
            (if (>= a (* 0.999 full))
              (setq nf (1+ nf))
              (progn
                (setq nc (1+ nc) cut (+ cut a)
                      xs (mapcar 'car c) ys (mapcar 'cadr c)
                      bw (- (apply 'max xs) (apply 'min xs)) bh (- (apply 'max ys) (apply 'min ys)))
                (setq mn (min mn bw bh))
                (if (< (min bw bh) hep) (setq ns (1+ ns))))))))
      (setq j (1+ j)))
    (setq i (1+ i)))
  (list nf nc ns (if (< mn 1e9) mn 0.0)
        (if (> (+ nf nc) 0) (/ (* 100.0 (- (* nc full) cut)) (* (+ nf nc) full)) 0.0)))

;; Cac diem bat dau ung vien (ten ox oy) trong he luoi da xoay; q = 1 them luoi thu mat 5 x 5 trong 1 chu ky
(defun sd:od-cands (rp W H jt q / bb x0 y0 x1 y1 cx cy px py r k m)
  (setq bb (sd:bbox rp) x0 (car (car bb)) y0 (cadr (car bb)) x1 (car (cadr bb)) y1 (cadr (cadr bb))
        cx (/ (+ x0 x1) 2.0) cy (/ (+ y0 y1) 2.0) px (+ W jt) py (+ H jt)
        r (list (list "Goc trai-duoi" x0 y0) (list "Goc phai-duoi" (- x1 W) y0)
                (list "Goc trai-tren" x0 (- y1 H)) (list "Goc phai-tren" (- x1 W) (- y1 H))
                (list "Tam vien o tam" (- cx (/ W 2.0)) (- cy (/ H 2.0)))
                (list "Mach o tam" (+ cx (/ jt 2.0)) (+ cy (/ jt 2.0)))))
  (if (and q (> q 0))
    (progn
      (setq k 0)
      (while (< k 5)
        (setq m 0)
        (while (< m 5)
          (setq r (append r (list (list (strcat "Luoi " (itoa k) "," (itoa m)) (+ x0 (* k (/ px 5.0))) (+ y0 (* m (/ py 5.0)))))))
          (setq m (1+ m)))
        (setq k (1+ k)))))
  r)

(defun sd:od-less (a b)
  (cond ((/= (nth 2 (cadr a)) (nth 2 (cadr b))) (< (nth 2 (cadr a)) (nth 2 (cadr b))))
        ((/= (nth 1 (cadr a)) (nth 1 (cadr b))) (< (nth 1 (cadr a)) (nth 1 (cadr b))))
        (t (< (nth 4 (cadr a)) (nth 4 (cadr b))))))

(defun c:SDDIEMBD (/ r e pts hs holes i W H jt hep q huong ang rp rh cands res best sc ow k kgap o ho2)
  (sd:begin)
  (setq *SD:IFRAME* nil)
  (if (sd:dlg "So sanh diem bat dau rai (SDDIEMBD)"
              (list (list "W" "Vien - dai (mm)" 'real (sd:cfg "DB-W" 600.0))
                    (list "H" "Vien - rong (mm)" 'real (sd:cfg "DB-H" 600.0))
                    (list "jt" "Ron (mm)" 'real0 (sd:cfg "DB-JT" 2.0))
                    (list "huong" "Huong luoi" 'kw (sd:cfg "DB-HUONG" "Truc")
                          '(("Truc" . "Theo truc X, Y") ("Canh" . "Theo canh dai nhat cua vung") ("Goc" . "Nhap goc (do)")))
                    (list "ang" "Goc luoi (do)" 'real0 (sd:cfg "DB-ANG" 0.0) nil '("huong" "Goc"))
                    (list "hep" "Vien cat hep hon (mm) tinh la vun" 'real (sd:cfg "DB-HEP" 50.0))
                    (list "q" "Do ky" 'kw (sd:cfg "DB-Q" "Nhanh")
                          '(("Nhanh" . "Nhanh: 6 diem (4 goc, 2 tam)") ("Ky" . "Ky: them 25 diem quet trong 1 chu ky luoi")))
                    (list "kg" "Khe sat tuong (mm): vung lat lui vao tu bien, lo/cot no ra (0 = khong)" 'real0 (sd:cfg "DB-KG" 0.0))
                    (list "ve" "Danh dau diem tot nhat tren ban ve" 'tog t)))
    (progn
      (setq kgap (sd:cfg-put "DB-KG" (cond ((sd:v "kg")) (0.0))))
      (setq W (sd:cfg-put "DB-W" (sd:v "W")) H (sd:cfg-put "DB-H" (sd:v "H")) jt (sd:cfg-put "DB-JT" (sd:v "jt"))
            huong (sd:cfg-put "DB-HUONG" (sd:v "huong")) hep (sd:cfg-put "DB-HEP" (sd:v "hep")) q (sd:cfg-put "DB-Q" (sd:v "q"))
            ang (sd:cfg-put "DB-ANG" (cond ((sd:v "ang")) (0.0))) sc (sd:sc))
      (if (setq r (entsel "\nChon polyline kin la bien vung lat: "))
        (if (and (= (cdr (assoc 0 (entget (car r)))) "LWPOLYLINE") (= 1 (logand 1 (cdr (assoc 70 (entget (car r)))))))
          (progn
            (setq e (car r) pts (sd:curve-pts e))
            ;; khe sat tuong: lui bien vao kgap
            (if (> kgap 0.0)
              (if (setq o (sd:offset e kgap t))
                (setq pts (sd:curve-pts o))
                (princ "\n[SD] Khong lui vao duoc khe sat tuong, tinh theo bien goc.")))
            (princ "\nChon cac polyline kin la lo / cot trong vung <Enter = khong co>: ")
            (if (setq hs (ssget '((0 . "LWPOLYLINE") (-4 . "&") (70 . 1))))
              (progn (setq i 0)
                     (repeat (sslength hs)
                       (if (not (equal (ssname hs i) e))
                         (setq holes (cons (sd:curve-pts (if (and (> kgap 0.0) (setq ho2 (sd:offset (ssname hs i) kgap nil))) ho2 (ssname hs i))) holes)))
                       (setq i (1+ i)))))
            ;; goc luoi (rad)
            (setq ang (cond ((= huong "Truc") 0.0)
                            ((= huong "Canh")
                             (setq ow (last pts) k nil)
                             (foreach b pts (if (or (null k) (> (distance ow b) (car k))) (setq k (list (distance ow b) (angle ow b)))) (setq ow b))
                             (cadr k))
                            (t (* pi (/ ang 180.0))))
                  rp (mapcar '(lambda (p) (sd:rot p (- ang))) pts)
                  rh (mapcar '(lambda (hp) (mapcar '(lambda (p) (sd:rot p (- ang))) hp)) holes)
                  cands (sd:od-cands rp W H jt (if (= q "Ky") 1 0)))
            (princ (strcat "\n[SD] Dang danh gia " (itoa (length cands)) " diem bat dau, luoi " (sd:num W) " x " (sd:num H)
                           ", goc " (sd:rtos (* 180.0 (/ ang pi)) 1) " do ..."))
            (foreach c cands
              (setq res (cons (list c (sd:od-eval rp rh W H jt (cadr c) (caddr c) hep)) res)))
            (setq res (sd:sort res 'sd:od-less))
            (princ "\n   Diem bat dau (luoi)          Nguyen  Cat  Cat-hep  Canh-hep-nhat  Hao-hut")
            (setq k 0)
            (foreach x res
              (if (< k 8)
                (princ (strcat "\n " (if (= k 0) "> " "  ") (car (car x)) "   " (itoa (car (cadr x))) "   " (itoa (cadr (cadr x))) "   "
                               (itoa (caddr (cadr x))) "   " (sd:rtos (cadddr (cadr x)) 0) " mm   " (sd:rtos (nth 4 (cadr x)) 1) "%")))
              (setq k (1+ k)))
            (setq best (car res) ow (sd:rot (list (cadr (car best)) (caddr (car best))) ang))
            (princ (strcat "\n[SD] Tot nhat: " (car (car best)) ", goc vien trai-duoi cua luoi tai ("
                           (sd:rtos (car ow) 0) ", " (sd:rtos (cadr ow) 0) "), goc " (sd:rtos (* 180.0 (/ ang pi)) 1)
                           " do: " (itoa (cadr (cadr best))) " vien cat, " (itoa (caddr (cadr best))) " vien cat hep. Dung diem nay lam diem bat dau trong SDRAITAM / SDGACH."))
            (if (sd:v "ve")
              (progn
                (sd:make-layer "SD-DIEMBD" 3 "Continuous" 25)
                (entmake (list '(0 . "CIRCLE") '(8 . "SD-DIEMBD") (cons 10 (list (car ow) (cadr ow) 0.0)) (cons 40 (* 3.0 sc))))
                (sd:text (sd:p+ ow 0 (* 5.0 sc)) (strcat "DIEM BAT DAU: " (car (car best))) (* 2.5 sc) "L" "SD-DIEMBD"))))
          (princ "\n[SD] Can chon polyline kin."))
        (princ "\n[SD] Chua chon."))))
  (sd:finish))

;;; --------------------------------------------------------------------------
;;;  SDKHEGIAN - Khe co gian: khe chu vi sat tuong + khe phan vung vung lat (doan lien tuc dai nhat)
;;;  SDTHOATNUOC - Diem thoat nuoc + doc san: chenh cao den cac goc, khoanh vung vien cat quanh pheu thu
;;; --------------------------------------------------------------------------
;; Khoang cach nho nhat tu diem p den cac pheu drs
(defun sd:dr-near (p drs / d)
  (foreach q drs (if (or (null d) (< (distance p q) d)) (setq d (distance p q))))
  d)

;; Pheu gan p nhat
(defun sd:dr-nearpt (p drs / b)
  (foreach q drs (if (or (null b) (< (distance p q) (distance p b))) (setq b q)))
  b)

;; Diem xa pheu nhat trong vung pts (dinh va luoi lay mau): (khoang-cach diem)
(defun sd:dr-far (pts drs step / bb x y best d ys)
  (foreach p pts
    (setq d (sd:dr-near p drs))
    (if (or (null best) (> d (car best))) (setq best (list d p))))
  (setq bb (sd:bbox pts) x (car (car bb)))
  (while (<= x (car (cadr bb)))
    (setq y (cadr (car bb)))
    (while (<= y (cadr (cadr bb)))
      (if (sd:inpoly (list x y) pts)
        (progn (setq d (sd:dr-near (list x y) drs))
               (if (> d (car best)) (setq best (list d (list x y))))))
      (setq y (+ y step)))
    (setq x (+ x step)))
  best)

;; Vi tri cac khe phan vung doc theo khoang a..b chia deu thanh cac khoang <= mx, cham vao tam mach neu co luoi vien (w + jt)
(defun sd:kg-pos (a b mx per / n i r x)
  (setq n (max 1 (fix (+ (/ (- b a) mx) 0.999999))) i 1)
  (while (< i n)
    (setq x (+ a (* i (/ (- b a) n))))
    (if (and per (> per 1.0)) (setq x (+ a (* per (fix (+ 0.5 (/ (- x a) per)))))))
    (if (and (> x (+ a 1.0)) (< x (- b 1.0)) (not (member x r))) (setq r (cons x r)))
    (setq i (1+ i)))
  (reverse r))

(defun c:SDKHEGIAN (/ r e pts hs holes i kg mx ge W jt per bb x0 y0 x1 y1 xs ys n tot o x y sg)
  (sd:begin)
  (if (sd:dlg "Khe co gian (SDKHEGIAN)"
              (list (list "kg" "Khe sat tuong - chua cach tuong (mm, 0 = khong ve)" 'real0 (sd:cfg "KG-KG" 10.0))
                    (list "mx" "Khoang cach toi da giua cac khe phan vung (mm, 0 = khong chia)" 'real0 (sd:cfg "KG-MX" 6000.0))
                    (list "ge" "Be rong khe phan vung (mm)" 'real (sd:cfg "KG-GE" 10.0))
                    (list "W" "Luoi vien de can khe vao giua ron - rong vien (mm, 0 = khong can)" 'real0 (sd:cfg "KG-W" 0.0))
                    (list "jt" "Ron (mm)" 'real0 (sd:cfg "KG-JT" 2.0))))
    (progn
      (setq kg (sd:cfg-put "KG-KG" (sd:v "kg")) mx (sd:cfg-put "KG-MX" (sd:v "mx")) ge (sd:cfg-put "KG-GE" (sd:v "ge"))
            W (sd:cfg-put "KG-W" (sd:v "W")) jt (sd:cfg-put "KG-JT" (sd:v "jt")) per (if (> W 0.0) (+ W jt)))
      (if (setq r (entsel "\nChon polyline kin la bien vung lat: "))
        (if (and (= (cdr (assoc 0 (entget (car r)))) "LWPOLYLINE") (= 1 (logand 1 (cdr (assoc 70 (entget (car r)))))))
          (progn
            (setq e (car r) pts (sd:curve-pts e))
            (princ "\nChon cac polyline kin la lo / cot <Enter = khong co>: ")
            (if (setq hs (ssget '((0 . "LWPOLYLINE") (-4 . "&") (70 . 1))))
              (progn (setq i 0)
                     (repeat (sslength hs)
                       (if (not (equal (ssname hs i) e)) (setq holes (cons (sd:curve-pts (ssname hs i)) holes)))
                       (setq i (1+ i)))))
            (sd:make-layer "SD-KHE" 6 "Continuous" 35)
            (setq tot 0.0 n 0)
            ;; khe sat tuong: bao ngoai lui vao kg
            (if (> kg 0.0)
              (if (setq o (sd:offset e kg t))
                (progn (sd:pline (sd:curve-pts o) t "SD-KHE") (setq n (1+ n) tot (+ tot (vla-get-Length (vlax-ename->vla-object o)))))
                (princ "\n[SD] Khong lui vao duoc khe sat tuong (bien qua nho hay lom).")))
            ;; khe phan vung
            (if (> mx 0.0)
              (progn
                (setq bb (sd:bbox pts) x0 (car (car bb)) y0 (cadr (car bb)) x1 (car (cadr bb)) y1 (cadr (cadr bb))
                      xs (sd:kg-pos x0 x1 mx per) ys (sd:kg-pos y0 y1 mx per))
                (foreach x xs
                  (foreach sg (sd:clip-segh (list x y0) (list x y1) pts holes)
                    (sd:plinew sg nil ge "SD-KHE") (setq n (1+ n) tot (+ tot (distance (car sg) (cadr sg))))))
                (foreach y ys
                  (foreach sg (sd:clip-segh (list x0 y) (list x1 y) pts holes)
                    (sd:plinew sg nil ge "SD-KHE") (setq n (1+ n) tot (+ tot (distance (car sg) (cadr sg))))))))
            (princ (strcat "\n[SD] SDKHEGIAN: " (itoa n) " khe, tong chieu dai " (sd:rtos (/ tot 1000.0) 2) " m"
                           (if (> mx 0.0) (strcat " (phan vung moi " (itoa (1+ (length xs))) " x " (itoa (1+ (length ys))) " o, khoang <= " (sd:num mx) ")") "") ".")))
          (princ "\n[SD] Can chon polyline kin."))
        (princ "\n[SD] Chua chon."))))
  (sd:finish))

(defun c:SDTHOATNUOC (/ r e pts drs p it rad hmax far h sc step i d)
  (sd:begin)
  (if (sd:dlg "Thoat nuoc va doc san (SDTHOATNUOC)"
              (list (list "it" "Doc san (%)" 'real (sd:cfg "TN-I" 1.0))
                    (list "rad" "Ban kinh khoanh vien cat quanh pheu thu (mm)" 'real0 (sd:cfg "TN-R" 300.0))
                    (list "hmax" "Chenh cao toi da cho phep (mm, vua lat)" 'real (sd:cfg "TN-HMAX" 30.0))))
    (progn
      (setq it (sd:cfg-put "TN-I" (sd:v "it")) rad (sd:cfg-put "TN-R" (sd:v "rad")) hmax (sd:cfg-put "TN-HMAX" (sd:v "hmax")) sc (sd:sc))
      (if (setq r (entsel "\nChon polyline kin la bien vung lat: "))
        (if (and (= (cdr (assoc 0 (entget (car r)))) "LWPOLYLINE") (= 1 (logand 1 (cdr (assoc 70 (entget (car r)))))))
          (progn
            (setq e (car r) pts (sd:curve-pts e))
            (while (setq p (getpoint "\nChon vi tri pheu thu nuoc <Enter xong>: "))
              (setq drs (cons (sd:2d p) drs)))
            (if (null drs)
              (princ "\n[SD] Chua chon pheu thu nuoc.")
              (progn
                (setq step (max 100.0 (/ (distance (car (sd:bbox pts)) (cadr (sd:bbox pts))) 40.0))
                      far (sd:dr-far pts drs step) h (* (car far) (/ it 100.0)))
                (sd:make-layer "SD-THOATNUOC" 4 "Continuous" 25)
                (foreach p drs
                  (entmake (list '(0 . "CIRCLE") '(8 . "SD-THOATNUOC") (cons 10 (list (car p) (cadr p) 0.0)) (cons 40 (* 1.5 sc))))
                  (if (> rad 0.0) (entmake (list '(0 . "CIRCLE") '(8 . "SD-THOATNUOC") (cons 10 (list (car p) (cadr p) 0.0)) (cons 40 rad))))
                  (sd:text (sd:p+ p 0 (+ rad (* 3.0 sc))) (strcat "PHEU THU, i = " (sd:num it) "%") (* 2.5 sc) "L" "SD-THOATNUOC"))
                ;; nhan do cao tai cac dinh bien, so voi mieng pheu
                (foreach q pts
                  (setq d (sd:dr-near q drs))
                  (sd:text (sd:p+ q 0 (* 2.0 sc)) (strcat "+" (sd:rtos (* d (/ it 100.0)) 0)) (* 2.0 sc) "L" "SD-THOATNUOC"))
                (sd:line (cadr far) (sd:dr-nearpt (cadr far) drs) "SD-THOATNUOC")
                (princ (strcat "\n[SD] SDTHOATNUOC: " (itoa (length drs)) " pheu thu; diem xa nhat cach pheu " (sd:rtos (/ (car far) 1000.0) 2)
                               " m, chenh cao " (sd:rtos h 1) " mm voi doc " (sd:num it) "%."))
                (if (or (< it 1.0) (> it 2.0))
                  (princ "\n[?] D\\U+1ED1c ngo\\U+00E0i 1 - 2%: TCVN 4260:2012 \\U+00A76.2.24 l\\U+1EA5y d\\U+1ED1c s\\U+00E2n quanh b\\U+1EC3 1 - 2% v\\U+1EC1 ph\\U+00EDa ph\\U+1EC5u thu (\\U+0111\\U+00E1y b\\U+1EC3 d\\U+1ED1c v\\U+1EC1 h\\U+1ED1 thu 1 - 3%, \\U+00A75.1.11)."))
                (if (> h hmax)
                  (princ (strcat "\n[!] Vuot " (sd:num hmax) " mm cho phep: them pheu thu hoac giam doc / tang lop vua. Chenh cao nay lam viec cat vien theo doc va mach khong con thang hang.")))
                (if (> rad 0.0) (princ (strcat "\n   Vong tron ban kinh " (sd:num rad) " mm quanh pheu: cac vien nam trong vong thuong cat cheo theo doc, kiem tra va chia vien rieng."))))))
          (princ "\n[SD] Can chon polyline kin."))
        (princ "\n[SD] Chua chon."))))
  (sd:finish))

;;; --------------------------------------------------------------------------
;;;  SDMOANH - Mo bien anh da: khi bien moi cua vien vuot ra ngoai anh nhung tam da con du kho, tu dich anh roi cat lai
;;; --------------------------------------------------------------------------
;; Hinh hoc anh trong WCS: (goc-trai-duoi goc-xoay rong cao)
(defun sd:im-geom (e / o)
  (setq o (vlax-ename->vla-object e))
  (list (sd:2d (vlax-safearray->list (vlax-variant-value (vla-get-Origin o)))) (vla-get-Rotation o) (vla-get-Width o) (vla-get-Height o)))

;; Vec to dich anh (WCS) de da giac pts nam tron trong anh, chua le m moi canh khi du cho; (0 0) neu da nam trong; nil neu da giac lon hon anh
(defun sd:im-fit (g pts m / o a w h lp x0 x1 y0 y1 mm dx dy)
  (setq o (car g) a (cadr g) w (caddr g) h (cadddr g)
        lp (mapcar '(lambda (q) (sd:w2l o a q)) pts)
        x0 (apply 'min (mapcar 'car lp)) x1 (apply 'max (mapcar 'car lp))
        y0 (apply 'min (mapcar 'cadr lp)) y1 (apply 'max (mapcar 'cadr lp)))
  (if (or (> (- x1 x0) (+ w 1e-6)) (> (- y1 y0) (+ h 1e-6)))
    nil
    (progn
      (setq mm (max 0.0 (min m (/ (- w (- x1 x0)) 2.0) (/ (- h (- y1 y0)) 2.0)))
            dx (cond ((< x0 mm) (- mm x0)) ((> x1 (- w mm)) (- (- w mm) x1)) (t 0.0))
            dy (cond ((< y0 mm) (- mm y0)) ((> y1 (- h mm)) (- (- h mm) y1)) (t 0.0)))
      (sd:rot (list (- dx) (- dy)) a))))

;; Anh dung tam vien nam trong da giac (SD_ANH ghi luc SDANHDA), nil neu khong co
;; Da giac cat (IMAGECLIP) cua anh theo toa do WCS; nil neu anh khong bat cat. DXF IMAGE: 10 goc, 11 / 12 vec to 1 diem anh, 14 dinh cat (pixel, tam diem anh = so nguyen)
(defun sd:im-clip-pts (e / ed ins u v r q)
  (setq ed (entget e) ins (cdr (assoc 10 ed)) u (cdr (assoc 11 ed)) v (cdr (assoc 12 ed)))
  (if (and ins u v (= 1 (cond ((cdr (assoc 280 ed))) (0))))
    (progn
      (foreach g ed (if (= (car g) 14) (setq r (cons (list (cadr g) (caddr g)) r))))
      (setq r (reverse r))
      ;; clip chu nhat luu 2 goc doi: mo ra 4 goc trong he pixel
      (if (= (length r) 2)
        (setq r (list (car r) (list (car (cadr r)) (cadr (car r))) (cadr r) (list (car (car r)) (cadr (cadr r))))))
      (if (> (length r) 2)
        (mapcar '(lambda (q)
                   (list (+ (car ins) (* (+ (car q) 0.5) (car u)) (* (+ (cadr q) 0.5) (car v)))
                         (+ (cadr ins) (* (+ (car q) 0.5) (cadr u)) (* (+ (cadr q) 0.5) (cadr v)))))
                r)))))

;; Tam duong cat cua moi anh trong ban ve: ((ename cx cy) ...); doc 1 lan, xoa bo nho (nil) khi anh bi sua / sau moi lenh SD
(defun sd:im-clips (/ ss i e pc n)
  (if (null *SD:IMCLIPS*)
    (progn
      (setq *SD:IMCLIPS* (list 'OK))
      (if (setq ss (ssget "_X" '((0 . "IMAGE"))))
        (progn
          (setq i 0)
          (repeat (sslength ss)
            (setq e (ssname ss i) i (1+ i))
            (if (setq pc (vl-catch-all-apply 'sd:im-clip-pts (list e)))
              (if (not (vl-catch-all-error-p pc))
                (setq n (float (length pc))
                      *SD:IMCLIPS* (cons (list e (/ (apply '+ (mapcar 'car pc)) n) (/ (apply '+ (mapcar 'cadr pc)) n)) *SD:IMCLIPS*)))))))))
  (cdr *SD:IMCLIPS*))

;; Anh co duong cat trung vien (tam cach tam vien <= max(15 mm, 10% ban kinh)): tim theo vi tri that, khong can SD_ANH
(defun sd:im-find-clip (cx cy rad / best d)
  (foreach c (sd:im-clips)
    (setq d (distance (list cx cy) (list (cadr c) (caddr c))))
    (if (and (<= d (max 15.0 (* 0.1 rad))) (or (null best) (< d (car best)))) (setq best (list d (car c)))))
  (cadr best))

(defun sd:im-find (pts ims / i e xd r cx cy rad d best cl)
  (setq i 0 cx (/ (apply '+ (mapcar 'car pts)) (float (length pts))) cy (/ (apply '+ (mapcar 'cadr pts)) (float (length pts)))
        rad (apply 'max (mapcar '(lambda (q) (distance (list cx cy) q)) pts))
        cl (sd:im-find-clip cx cy rad))
  (if (and (null cl) ims)
    (repeat (sslength ims)
      (setq e (ssname ims i) i (1+ i)
            xd (mapcar 'cdr (cdadr (assoc -3 (entget e '("SD_ANH"))))))
      (if (>= (length xd) 2)
        (progn
          (if (and (null r) (sd:inpoly (list (car xd) (cadr xd)) pts)) (setq r e))
          ;; du phong: bien da keo lech khoi tam cu thi lay anh co tam gan nhat trong ban kinh vien
          (setq d (distance (list cx cy) (list (car xd) (cadr xd))))
          (if (and (<= d (+ rad 50.0)) (or (null best) (< d (car best)))) (setq best (list d e)))))))
  (cond (cl) (r) ((cadr best))))

;; Goc xoay anh so voi canh dai vien (rad) da ghi luc SDANHDA, nil neu khong co hoac luoi chung (99)
(defun sd:im-delta (im / xd)
  (setq xd (mapcar 'cdr (cdadr (assoc -3 (entget im '("SD_ANH"))))))
  (if (and (>= (length xd) 3) (< (abs (nth 2 xd)) 50.0)) (nth 2 xd)))

;; Xoay anh de van giu dung huong so voi canh dai moi cua vien: oldang = goc canh dai truoc khi sua (neu anh chua co du lieu goc)
(defun sd:im-rotfix (im pts oldang / fr o cur d df)
  (setq *SD:IFRAME* nil fr (sd:tile-frame pts))
  (if (> (abs (- (cadr fr) (caddr fr))) (* 0.02 (max (cadr fr) (caddr fr))))
    (progn
      (setq o (vlax-ename->vla-object im) cur (vla-get-Rotation o)
            d (cond ((sd:im-delta im)) (oldang (- cur oldang))))
      (if d
        (progn
          (setq df (rem (- (+ (car fr) d) cur) pi))
          (cond ((> df (/ pi 2.0)) (setq df (- df pi))) ((< df (/ pi -2.0)) (setq df (+ df pi))))
          (if (> (abs df) 1e-3)
            (vla-Rotate o (vlax-3d-point (car (nth 3 fr)) (cadr (nth 3 fr)) 0.0) df))))))
  t)

;; Cat lai anh im theo da giac pts: xoay lai van neu canh dai doi huong, dich anh neu can de du kho (le m). Tra ve OK, DICH hoac KHO
(defun sd:im-turn (im pts m / o xd c dl)
  (setq o (vlax-ename->vla-object im)
        xd (mapcar 'cdr (cdadr (assoc -3 (entget im '("SD_ANH")))))
        c (list (/ (apply '+ (mapcar 'car pts)) (float (length pts))) (/ (apply '+ (mapcar 'cadr pts)) (float (length pts))) 0.0))
  (vla-Rotate o (vlax-3d-point c) (/ pi 2.0))
  (if (sd:im-fit (sd:im-geom im) pts m)
    t
    (progn (vla-Rotate o (vlax-3d-point c) (/ pi -2.0)) nil)))

;; Het kho theo chieu hien tai: thu xoay anh 90 do quanh tam vien (cfg XOAY-KHO: Hoi / Tuxoay / Tat); chi anh rieng tung vien (co goc xoay)
(defun sd:im-try-turn (im pts m / mode xd c o ok)
  (setq mode (sd:cfg "XOAY-KHO" "Hoi"))
  (if (and (/= mode "Tat") (sd:im-delta im) (sd:im-turn im pts m))
    (cond
      ((or (= mode "Tuxoay") (and (= mode "Hoi") (not *SD:RXBUSY*) (progn (initget "Co Khong")
             (= (getkword "\nHet kho theo chieu van nay, xoay van 90 do thi du kho. Xoay? [Co/Khong] <Khong>: ") "Co"))))
       (setq xd (mapcar 'cdr (cdadr (assoc -3 (entget im '("SD_ANH"))))))
       (vl-catch-all-apply 'sd:put-xd
         (list im (list -3 (list "SD_ANH" (cons 1040 (car xd)) (cons 1040 (cadr xd))
                                 (cons 1040 (rem (+ (nth 2 xd) (/ pi 2.0)) (* 2.0 pi)))))))
       (princ "\n[SD] Da xoay van 90 do cho du kho (van doi chieu so voi cac vien ke).")
       t)
      (t ;; khong dong y / khong hoi duoc: tra anh ve cu
       (setq o (vlax-ename->vla-object im)
             c (list (/ (apply '+ (mapcar 'car pts)) (float (length pts))) (/ (apply '+ (mapcar 'cadr pts)) (float (length pts))) 0.0))
       (vla-Rotate o (vlax-3d-point c) (/ pi -2.0))
       (if (and (= mode "Hoi") *SD:RXBUSY*) (setq *SD:XOAYHINT* t))
       nil))))

;; Anh chon bang tay ma chua co SD_ANH (tam da goc / anh chen chua cat): khong cat de len anh goc, tao ban sao rieng cho vien
(defun sd:im-adopt (e pts / o cp ne c pc d rad yn)
  (setq c (list (/ (apply '+ (mapcar 'car pts)) (float (length pts))) (/ (apply '+ (mapcar 'cadr pts)) (float (length pts))))
        rad (apply 'max (mapcar '(lambda (q) (distance c q)) pts)))
  ;; anh dang cat o cho khac (co the la anh cua vien khac): hoi lai, tranh keo anh vien khac ve day
  (if (and (setq pc (vl-catch-all-apply 'sd:im-clip-pts (list e))) (not (vl-catch-all-error-p pc)) pc
           (> (setq d (distance c (list (/ (apply '+ (mapcar 'car pc)) (float (length pc))) (/ (apply '+ (mapcar 'cadr pc)) (float (length pc))))))
              (max 50.0 (* 0.3 rad))))
    (progn
      (initget "Co Khong")
      (setq yn (getkword (strcat "\n[SD] Anh nay dang cat cach vien " (sd:num d) " mm (co the la anh cua vien khac). Van dung anh nay? [Co/Khong] <Khong>: ")))
      (if (/= yn "Co") (setq e nil))))
  (cond
    ((null e) nil)
    ((cdr (assoc -3 (entget e '("SD_ANH")))) e)
    (t
     (setq o (vlax-ename->vla-object e) cp (vla-Copy o) ne (vlax-vla-object->ename cp))
     (vl-catch-all-apply 'vla-put-Layer (list cp "SD-GACH-ANH"))
     (vl-catch-all-apply 'sd:put-xd
       (list ne (list -3 (list "SD_ANH" (cons 1040 (float (car c))) (cons 1040 (float (cadr c))) (cons 1040 99.0)))))
     (princ "\n[SD] Anh chon chua phai anh da cat cua vien (khong co du lieu SD_ANH, co the la tam goc): giu nguyen anh goc, tao ban sao de cat cho vien nay.")
     ne)))

(defun sd:im-reclip (im pts m oldang / g d tr os)
  (sd:im-rotfix im pts oldang)
  (setq g (sd:im-geom im) d (sd:im-fit g pts m))
  (if (and (null d) (sd:im-try-turn im pts m))
    (setq tr t g (sd:im-geom im) d (sd:im-fit g pts m)))
  (cond
    ((null d) 'KHO)
    (t
     (if (> (distance '(0.0 0.0) d) 1e-6)
       (vla-Move (vlax-ename->vla-object im) (vlax-3d-point 0.0 0.0 0.0) (vlax-3d-point (car d) (cadr d) 0.0)))
     (setq os (getvar "OSMODE")) (setvar "OSMODE" 0)
     (command "_.IMAGECLIP" im "_D")
     (command "_.IMAGECLIP" im "_N" "_P")
     (foreach q pts (command (trans (list (car q) (cadr q) 0.0) 0 1)))
     (command "")
     (setvar "OSMODE" os)
     (setq *SD:IMCLIPS* nil)
     (cond (tr 'XOAY) ((> (distance '(0.0 0.0) d) 1e-6) 'DICH) (t 'OK)))))

(defun c:SDMOANH (/ ss ims i e pts im m tay n nmv nfar nnone r st)
  (sd:begin)
  (if (sd:dlg "Mo bien anh da (SDMOANH)"
              (list (list "m" "Chua le an toan moi canh khi du kho (mm)" 'real0 (sd:cfg "MOANH-M" 10.0))
                    (list "tay" "Khong tu ghep duoc anh thi hoi chon anh bang tay" 'tog t)
                    (list "xoay" "Het kho thi xoay van 90 do quanh tam vien (SDTUDONG cung dung)" 'kw (sd:cfg "XOAY-KHO" "Hoi")
                          '(("Hoi" . "Hoi truoc khi xoay") ("Tuxoay" . "Tu xoay va bao") ("Tat" . "Khong xoay, bao het kho")))))
    (progn
      (sd:cfg-put "XOAY-KHO" (cond ((sd:v "xoay")) ("Hoi")))
      (setq m (sd:cfg-put "MOANH-M" (sd:v "m")) tay (sd:v "tay") n 0 nmv 0 nfar 0 nnone 0)
      (princ "\nChon cac polyline bien moi (da chinh) cua vien: ")
      (if (setq ss (ssget '((0 . "LWPOLYLINE") (-4 . "&") (70 . 1))))
        (progn
          (setq ims (ssget "_X" '((0 . "IMAGE") (-3 ("SD_ANH")))) i 0)
          (repeat (sslength ss)
            (setq e (ssname ss i) i (1+ i) pts (sd:curve-pts e) im (sd:im-find pts ims) n (1+ n))
            (if (and (null im) tay)
              (progn
                (princ (strcat "\nVien " (itoa n) ": khong tu ghep duoc anh."))
                (if (setq r (entsel "\nChon anh cua vien nay <bo qua>: "))
                  (if (= (cdr (assoc 0 (entget (car r)))) "IMAGE") (setq im (sd:im-adopt (car r) pts))))))
            (if (null im)
              (setq nnone (1+ nnone))
              (progn
                (setq st (sd:im-reclip im pts m nil))
                (cond ((= st 'KHO) (setq nfar (1+ nfar))
                       (princ (strcat "\nVien " (itoa n) ": bien lon hon ca tam da, khong du kho.")))
                      ((member st '(DICH XOAY)) (setq nmv (1+ nmv)))))))
          (princ (strcat "\n[SD] " (itoa (sslength ss)) " vien: cat lai theo bien moi " (itoa (- (sslength ss) nfar nnone)) ", trong do dich anh "
                         (itoa nmv) " vien; het kho " (itoa nfar) "; khong co anh " (itoa nnone) ".")))
        (princ "\n[SD] Chua chon polyline."))))
  (sd:finish))

;;; --------------------------------------------------------------------------
;;;  SDRON - Doi ron giua cac vien: thu / phong cac polyline vien tai cho, cap nhat hatch lien ket va cat lai anh, khong phai sua tay
;;; --------------------------------------------------------------------------
;; Chep dinh (va cung) cua polyline e2 vao polyline e, giu nguyen layer, du lieu SD_TILE va lien ket hatch
(defun sd:poly-vertsfrom (e e2 / a b pre post mid vs n)
  (setq a (entget e '("SD_TILE")) b (entget e2))
  (foreach g a
    (cond ((member (car g) '(10 40 41 42)) (setq mid t))
          (mid (setq post (cons g post)))
          (t (setq pre (cons g pre)))))
  (setq vs (vl-remove-if-not '(lambda (g) (member (car g) '(10 40 41 42))) b)
        n (length (vl-remove-if-not '(lambda (g) (= (car g) 10)) b))
        pre (mapcar '(lambda (g) (if (= (car g) 90) (cons 90 n) g)) (reverse pre)))
  (entmod (append pre vs (reverse post))))

(defun c:SDRON (/ ss ims hs i e pts e2 d cu moi anh hat ronanh im st n nok nfail nimg nkho nhas nhn nmiss)
  (sd:begin)
  (if (sd:dlg "Doi ron giua cac vien (SDRON)"
              (list (list "cu" "Ron hien tai giua cac vien (mm) - tu lay tu SDGACH / SDLOT / lan doi truoc" 'real0 (cond (*SD:GJ*) ((sd:cfg "RON-CU" 2.0))))
                    (list "moi" "Ron moi (mm) - bang ron hien tai thi chi dong bo anh / hatch" 'real0 (sd:cfg "RON-MOI" 4.0))
                    (list "hat" "Cap nhat hatch van da lien ket" 'tog t)
                    (list "anh" "Cat lai anh IMAGECLIP theo bien moi" 'tog t)
                    (list "ronanh" "Ron chua them trong anh (mm, nhu o Ron cua SDANHDA)" 'real0 (sd:cfg "RON-ANH" 0.0))))
    (progn
      (setq nmiss 0 cu (sd:cfg-put "RON-CU" (sd:v "cu")) moi (sd:cfg-put "RON-MOI" (sd:v "moi")) hat (sd:v "hat") anh (sd:v "anh")
            ronanh (sd:cfg-put "RON-ANH" (sd:v "ronanh")) d (/ (- moi cu) 2.0) n 0 nok 0 nfail 0 nimg 0 nkho 0)
      (princ "\nChon cac polyline vien can doi ron <Enter = tat ca vien tren layer SD-GACH / SD-GACH-CAT / SD-GACH-VIEN / SD-GACH-DOC>: ")
      (if (setq ss (cond ((ssget '((0 . "LWPOLYLINE") (-4 . "&") (70 . 1))))
                         ((ssget "_X" '((0 . "LWPOLYLINE") (8 . "SD-GACH,SD-GACH-CAT,SD-GACH-VIEN,SD-GACH-DOC") (-4 . "&") (70 . 1))))))
        (progn
          (if (< (abs d) 1e-6) (princ "\n[SD] Ron moi bang ron cu: chi dong bo anh va hatch theo bien hien tai (khong doi kich thuoc vien)."))
          (progn
            (setq ims (if anh (ssget "_X" '((0 . "IMAGE") (-3 ("SD_ANH"))))) i 0)
            (repeat (sslength ss)
              (setq e (ssname ss i) i (1+ i) n (1+ n) pts (sd:curve-pts e) im (if ims (sd:im-find pts ims))
                    e2 (if (< (abs d) 1e-6) e (sd:offset e (abs d) (> d 0.0))))
              (if e2
                (progn
                  (if (not (equal e2 e)) (sd:poly-vertsfrom e e2))
                  (setq nok (1+ nok))
                  (if im
                    (progn
                      (setq st (sd:im-reclip im (sd:inset-pts (sd:curve-pts e) (/ ronanh 2.0)) 10.0 nil))
                      (cond ((= st 'KHO) (setq nkho (1+ nkho))) (t (setq nimg (1+ nimg)))))
                    (if anh (setq nmiss (1+ nmiss)))))
                (setq nfail (1+ nfail))))
            (if hat
              (progn
                (setq hs (ssget "_X" '((0 . "HATCH") (8 . "SD-GACH-VAN"))) nhas 0 nhn 0)
                (if hs
                  (repeat (sslength hs)
                    (setq e (ssname hs nhas) nhas (1+ nhas))
                    (if (= (vla-get-AssociativeHatch (vlax-ename->vla-object e)) :vlax-true)
                      (vl-catch-all-apply 'vla-Evaluate (list (vlax-ename->vla-object e)))
                      (setq nhn (1+ nhn)))))))
            (if (> nok 0) (setq *SD:GJ* (sd:cfg-put "RON-CU" moi)))
            (princ (strcat "\n[SD] Doi ron " (sd:num cu) " -> " (sd:num moi) " mm: " (itoa nok) " / " (itoa n) " vien"
                           (if (> nfail 0) (strcat ", khong doi duoc " (itoa nfail) " vien (bien qua nho / lom)") "")
                           (if anh (strcat "; cat lai anh " (itoa nimg) " vien" (if (> nkho 0) (strcat ", het kho " (itoa nkho)) "")) "") "."))
            (if (and anh (> nmiss 0))
              (princ (strcat "\n[SD] " (itoa nmiss) " vien khong tim thay anh de cat lai (anh tao bang SDANHDA ban cu khong co du lieu SD_ANH): chay lai SDANHDA cho cac vien nay, hoac SDMOANH va chon anh bang tay.")))
            (if (and hat nhn (> nhn 0))
              (princ (strcat "\n[SD] " (itoa nhn) " hatch chua lien ket voi bien (tao tu ban cu): chay lai SDVANDA tren cac vien de hatch lien ket tu sau.")))))
        (princ "\n[SD] Chua chon polyline."))))
  (sd:finish))

;; Thu nho da giac vien vao trong d (mm) de chua ron: tra ve dinh moi, hoac chinh da giac cu neu khong thu duoc
(defun sd:inset-pts (pts d / e0 e1 r)
  (if (<= d 1e-6)
    pts
    (progn
      (sd:pline pts t "SD-GACH")
      (setq e0 (entlast) e1 (sd:offset e0 d t))
      (setq r (cond ((and e1 (>= (length (setq r (sd:curve-pts e1))) 3)) r) (t pts)))
      (entdel e0)
      r)))

;; Huong van "vien chinh": chon 1 vien nguyen (Enter = vien co khung lon nhat); tra ve goc canh dai cua vien do (rad)
(defun sd:main-ang (els / sel e pts best fr a sv)
  (princ "\nChon 1 vien chinh lam huong van (Enter = vien lon nhat trong cac vien dang cat): ")
  (setq sel (vl-catch-all-apply 'entsel nil) sv *SD:IFRAME* *SD:IFRAME* nil)
  (if (and sel (not (vl-catch-all-error-p sel)) (setq e (car sel)) (= (cdr (assoc 0 (entget e))) "LWPOLYLINE")
           (>= (length (setq pts (sd:curve-pts e))) 3))
    (setq a (car (sd:tile-frame pts)))
    (foreach e els
      (if (>= (length (setq pts (sd:curve-pts e))) 3)
        (progn (setq fr (sd:tile-frame pts))
               (if (or (null best) (> (* (cadr fr) (caddr fr)) (car best))) (setq best (list (* (cadr fr) (caddr fr)) (car fr))))))))
  (if (and (null a) best) (setq a (cadr best)))
  (setq *SD:IFRAME* sv)
  a)

(defun sd:anhda (els / mflag sw sh trim kerf chieu xep ss i e pts fr tiles imst items bases res pls nsl n k rec pl tot pt sc m ti tuanh io ctc vun cuts remn nq ron front sf win inron layerx doilay nlay)
  (setq sc (sd:sc))
  (if (sd:dlg "Cat anh da vao vien (SDANHDA)"
                   (list (list "tuanh" "Lay kich thuoc tam tu anh da chen (anh dung ti le that)" 'tog (if (member *SD:ITUANH* '(0)) nil t))
                         (list "sw" "Tam da tho - dai that (mm) (bo qua neu lay tu anh)" 'real (cond (*SD:ISW*) (3000.0)))
                         (list "sh" "Tam da tho - rong that (mm) (bo qua neu lay tu anh)" 'real (cond (*SD:ISH*) (1600.0)))
                         (list "trim" "Xen bien tam (mm)" 'real0 (cond (*SD:ITRIM*) (20.0)))
                         (list "kerf" "Be rong luoi cat (mm)" 'real0 (cond (*SD:IKERF*) (4.0)))
                         (list "chieu" "Chieu van tren vien" 'kw (cond (*SD:ICHIEU*) ("Toiuu"))
                               '(("Toiuu" . "Tu xoay 90 do de it hao") ("Doc" . "Van theo canh dai vien") ("Ngang" . "Van vuong goc canh dai") ("Chinh" . "Van theo huong vien chinh (chon 1 vien, moi vien deu 1 huong)")))
                         (list "xep" "Cach xep vien vao tam" 'kw (cond (*SD:IXEP*) ("Toiuu"))
                               '(("Toiuu" . "It hao nhat: cat xuyen, manh nho lap vao phe lieu hinh L / vun") ("Thutu" . "Theo thu tu lat (van gan nhau)")
                                 ("Duongviem" . "Chay doc duong vien (van lien tuc, vien sau ngay sau vien truoc)")))
                         (list "nq" "Do ky khi xep (cat xuyen: thu nhieu cach, chon it tam nhat)" 'kw (cond (*SD:INQ*) ("Canbang"))
                               '(("Nhanh" . "Nhanh: 1 cach xep") ("Canbang" . "Can bang: thu 30 to hop sap xep / cham diem / tach o") ("Ky" . "Ky: them leo doi hoan doi thu tu (toi da ~6 giay)"))
                               '("xep" "Toiuu"))
                         (list "win" "Thu tu lat: moi tam nhin truoc bao nhieu vien de lap cho trong (1 = dung thu tu tuyet doi)" 'int (cond (*SD:IWIN*) (6))
                               nil '("xep" "Thutu" "Duongviem"))
                         (list "ctc" "Ve thu tu duong cat + phe lieu (cat xuyen, cho che do It hao)" 'tog t)
                         (list "vun" "Phe lieu ghi nhan khi ca 2 canh >= (mm)" 'real0 (cond (*SD:IVUN*) (150.0)))
                         (list "ron" "Khe chua them trong anh (mm, mac dinh 0: chi dung ron that cua vien; chi tang neu muon khe trang hon ron)" 'real0 (cond (*SD:IRON*) (0.0)))
                         (list "inron" "Tu dat mau ron de in (trang tren da toi, nhu SDRONIN)" 'tog (cond (*SD:IINRON*) (t)))
                         (list "doilay" "Doi polyline vien (VD boundary tu hatch) sang layer SD-GACH-DOC de co ron khi in (SDRONIN / SDIN tac dong)" 'tog (sd:cfg "ANHDA-DOILAY" t))
                         (list "layerx" "Bo qua cac layer (VD *STAIR*,*THANG*,*MUI*; cach nhau dau phay; trong = khong bo)" 'str (sd:cfg "LAYERX" ""))
                         (list "front" "Dua duong vien (polyline) len tren anh de thay ron khi in" 'tog (cond (*SD:IFRONT*) (t)))))
   (progn
  (setq sw (sd:v "sw") sh (sd:v "sh") trim (sd:v "trim") kerf (sd:v "kerf") chieu (sd:v "chieu") xep (sd:v "xep")
        tuanh (sd:v "tuanh") *SD:ITUANH* (if tuanh 1 0) ctc (sd:v "ctc") vun (sd:v "vun") *SD:IVUN* vun
        win (cond ((sd:v "win")) (6)) *SD:IWIN* win
        ron (cond ((sd:v "ron")) (0.0)) *SD:IRON* ron front (sd:v "front") *SD:IFRONT* front
        doilay (sd:cfg-put "ANHDA-DOILAY" (sd:v "doilay"))
        inron (sd:v "inron") *SD:IINRON* inron layerx (sd:cfg-put "LAYERX" (cond ((sd:v "layerx")) ("")))
        nq (cond ((sd:v "nq")) ("Canbang")) *SD:INQ* nq
        *SD:ITRIM* trim *SD:IKERF* kerf *SD:ICHIEU* chieu *SD:IXEP* xep)
  (princ "\nChon anh tam da tho (nhieu anh cung kich thuoc that = nhieu tam khac van): ")
  (if (null (setq ss (ssget '((0 . "IMAGE")))))
    (princ "\n[SD] Chua chon anh.")
    (progn
      (if tuanh
        (progn
          (setq io (vlax-ename->vla-object (ssname ss 0)) sw (vla-get-Width io) sh (vla-get-Height io))
          (princ (strcat "\n[SD] Kich thuoc tam lay tu anh: " (sd:num sw) " x " (sd:num sh) " mm")))
        (setq *SD:ISW* sw *SD:ISH* sh))
      (setq i 0)
      (repeat (sslength ss) (setq imst (cons (sd:img-master (ssname ss i) sw sh) imst) i (1+ i)))
      (setq imst (reverse imst))
      (if (null els)
        (progn
          (princ "\nQuet chon cac polyline kin la vien da can cat anh: ")
          (if (setq ss (ssget '((0 . "LWPOLYLINE") (-4 . "&") (70 . 1))))
            (progn (setq i 0)
                   (repeat (sslength ss) (setq els (cons (ssname ss i) els) i (1+ i)))))))
      (if (and els layerx (/= layerx ""))
        (progn
          (setq n (length els)
                els (vl-remove-if '(lambda (e) (wcmatch (strcase (cdr (assoc 8 (entget e)))) (strcase layerx))) els))
          (if (< (length els) n)
            (princ (strcat "\n[SD] Bo qua " (itoa (- n (length els))) " polyline tren layer " layerx ".")))))
      (if (null els)
        (princ "\n[SD] Chua chon vien nao.")
        (progn
          (if (and (= chieu "Chinh") (not *SD:IFRAME*))
            (if (setq fr (sd:main-ang els))
              (setq *SD:IFRAME* fr mflag t)
              (setq chieu "Doc")))
          (setvar "OSMODE" 0)
          (foreach e els
            (if (>= (length (setq pts (sd:curve-pts e))) 3)
              (progn
                (setq fr (sd:tile-frame pts))
                (setq tiles (cons (list "" pts (car fr) (cadr fr) (caddr fr) (cadddr fr)) tiles)))
              (princ "\n[SD] Bo qua 1 polyline khong doc duoc dinh (loi hoac <3 dinh).")))
          (if (null tiles) (progn (princ "\n[SD] Khong co vien hop le de cat anh.") (if mflag (setq *SD:IFRAME* nil)) (exit)))
          (setq tiles (if (= xep "Duongviem") (sd:tile-chain (reverse tiles)) (sd:tile-order (reverse tiles))) i 0)
          (setq tiles (mapcar '(lambda (r) (setq i (1+ i)) (cons (strcat "T" (itoa i)) (cddr r))) tiles))
          ;; moi vien: (id pts ang tw th cw); kich thuoc dua vao xep + goc nen
          (foreach r tiles
            (cond
              ;; luoi rai co khung chung: Doc = van theo canh dai tam luoi cho moi vien, Ngang = vuong goc, Toiuu = duoc xoay 90
              ((and *SD:IFRAME* (= chieu "Ngang"))
               (setq items (cons (list (car r) (nth 4 r) (nth 3 r)) items) bases (cons (cons (car r) (+ (nth 2 r) (/ pi 2.0))) bases)))
              (*SD:IFRAME*
               (setq items (cons (list (car r) (nth 3 r) (nth 4 r)) items) bases (cons (cons (car r) (nth 2 r)) bases)))
              ((= chieu "Doc")
               (if (>= (nth 3 r) (nth 4 r))
                 (setq items (cons (list (car r) (nth 3 r) (nth 4 r)) items) bases (cons (cons (car r) (nth 2 r)) bases))
                 (setq items (cons (list (car r) (nth 4 r) (nth 3 r)) items) bases (cons (cons (car r) (+ (nth 2 r) (/ pi 2.0))) bases))))
              ((= chieu "Ngang")
               (if (>= (nth 3 r) (nth 4 r))
                 (setq items (cons (list (car r) (nth 4 r) (nth 3 r)) items) bases (cons (cons (car r) (+ (nth 2 r) (/ pi 2.0))) bases))
                 (setq items (cons (list (car r) (nth 3 r) (nth 4 r)) items) bases (cons (cons (car r) (nth 2 r)) bases))))
              (t (setq items (cons (list (car r) (nth 3 r) (nth 4 r)) items) bases (cons (cons (car r) (nth 2 r)) bases)))))
          (setq items (reverse items)
                res (if (= xep "Toiuu")
                      (sd:nest-g items sw sh trim kerf (= chieu "Toiuu") vun (cond ((= nq "Nhanh") 0) ((= nq "Ky") 2) (t 1)))
                      (sd:nest-w items sw sh trim kerf (and (= chieu "Toiuu") (/= xep "Duongviem")) vun win))
                pls (car res) nsl (cadr res) cuts (caddr res) remn (cadddr res) n 0 tot 0.0)
          (foreach pl pls
            (setq rec (assoc (car pl) tiles))
            (if (cadr pl)
              (progn
                (sd:img-place (nth (rem (cadr pl) (length imst)) imst) pl (cdr (assoc (car pl) bases)) (nth 5 rec) (sd:inset-pts (nth 1 rec) (/ ron 2.0)))
                (setq n (1+ n) tot (+ tot (* (nth 3 rec) (nth 4 rec)))))
              (princ (strcat "\n[SD] Vien " (car pl) " (" (sd:num (nth 3 rec)) " x " (sd:num (nth 4 rec)) ") lon hon tam da: khong cat duoc."
                             (if (and (<= (nth 4 rec) sw) (<= (nth 3 rec) sh)) " (xoay 90 do thi vua: doi Chieu van sang Toi uu / Ngang, hoac chon lai vien chinh)" "")))))
          (if front
            (progn
              (foreach e els (if (entget e) (setq sf (cond (sf) ((ssadd))) sf (ssadd e sf))))
              (if sf (command "_.DRAWORDER" sf "" "_F"))))
          (if doilay
            (progn
              (sd:make-layer "SD-GACH-DOC" 3 "Continuous" 13)
              (setq nlay 0)
              (foreach e els
                (if (and (entget e) (not (member (strcase (cdr (assoc 8 (entget e)))) *SD:RONLAY*))
                         (not (vl-catch-all-error-p (vl-catch-all-apply 'vla-put-Layer (list (vlax-ename->vla-object e) "SD-GACH-DOC")))))
                  (setq nlay (1+ nlay))))
              (if (> nlay 0) (princ (strcat "\n[SD] Da doi " (itoa nlay) " polyline vien sang layer SD-GACH-DOC (co ron khi in).")))))
          (sd:ron-extra-add els)
          (if inron
            (sd:ronin-apply (cond ((/= (sd:cfg "RONIN-MAU" "Trang") "Khoiphuc") (sd:cfg "RONIN-MAU" "Trang")) ("Trang"))
                            (sd:cfg "RONIN-LW" 0.25) (sd:cfg "RONIN-MAP" "") t))
          (vlax-ldata-put "SD" "ANHDA"
            (mapcar '(lambda (pl) (list (car pl) (car (nth 5 (assoc (car pl) tiles))) (cadr (nth 5 (assoc (car pl) tiles))) (cadr pl)
                                        (nth 2 pl) (nth 3 pl) (nth 4 pl) (nth 5 pl)
                                        (if (cadr pl) (+ (cdr (assoc (car pl) bases)) (if (nth 6 pl) (/ pi 2.0) 0.0)))))
                    pls))
          (if (setq pt (sd:getpt "\nDiem chen so do cat tam da <bo qua>: " nil))
            (if (and ctc cuts) (sd:img-diagram2 pls nsl sw sh pt sc cuts remn) (sd:img-diagram pls nsl sw sh pt sc)))
          (foreach m imst (vl-catch-all-apply 'vla-Delete (list (car m))))
          (if mflag (setq *SD:IFRAME* nil))
          (princ (strcat "\n[SD] Da cat " (itoa n) " / " (itoa (length tiles)) " vien tu anh; can " (itoa nsl) " tam da " (sd:num sw) " x " (sd:num sh)
                         (if (> nsl 0) (strcat ", hao " (sd:num (* 100.0 (- 1.0 (/ tot (* nsl sw sh))))) "%") "")
                         (if (and (> nsl 1) (= (length imst) 1)) " (cac tam dung chung 1 anh nen van giong nhau; chon nhieu anh de doi van)" "")
                         "."))))))))
  (princ))

;; ---- Xep CAT XUYEN (guillotine) cho may cat da cau: danh sach o trong, uu tien manh lon, vien nho lap vao phe lieu hinh L / vun
;; Ghi lai duong cat kem cap (cap 0 = cat tach lon truoc, cap sau = cat manh nho sau cung) de danh so thu tu cat.
;; Tra ve (placements so-tam cuts phe-lieu): placement = (id tam x y rong cao xoay); cut = (tam x1 y1 x2 y2 cap); phe-lieu = (tam x y rong cao)
;; Mot luot xep cat xuyen: items da sap thu tu san; fm = cach cham diem o trong (0 it thua canh ngan nhat, 1 it thua canh dai nhat, 2 it thua dien tich);
;; sm = cach tach o trong (0 theo canh thua ngan, 1 theo canh thua dai, 2 giu o lon nhat, 3 luon ngang truoc, 4 luon dung truoc)
(defun sd:nest-g1 (items SW SH trim kerf rotok vun fm sm / uw1 uh1 slabs pl cuts best it o cw ch si fr j f sc fx fy fw fh dep pw ph wf hf nf k rm hfirst lw lh)
  (setq uw1 (+ (- SW (* 2.0 trim)) kerf) uh1 (+ (- SH (* 2.0 trim)) kerf))
  (foreach it items
    (setq best nil)
    (foreach o (if rotok (list nil t) (list nil))
      (setq cw (+ kerf (if o (caddr it) (cadr it))) ch (+ kerf (if o (cadr it) (caddr it))) si 0)
      (foreach fr slabs
        (setq j 0)
        (foreach f fr
          (if (and (<= cw (+ (nth 2 f) 1e-6)) (<= ch (+ (nth 3 f) 1e-6)))
            (progn
              (setq lw (- (nth 2 f) cw) lh (- (nth 3 f) ch)
                    sc (cond ((= fm 1) (+ (* 1000.0 (max lw lh)) (/ (* (nth 2 f) (nth 3 f)) 1e6)))
                             ((= fm 2) (- (* (nth 2 f) (nth 3 f)) (* cw ch)))
                             (t (+ (* 1000.0 (min lw lh)) (/ (* (nth 2 f) (nth 3 f)) 1e6)))))
              ;; vua khit 1 canh: cat duoc ca dai, it duong cat, it vun -> uu tien manh
              (if (or (< lw 1.0) (< lh 1.0)) (setq sc (- sc 1e8)))
              (if (or (null best) (< sc (car best))) (setq best (list sc si j o cw ch nil)))))
          (setq j (1+ j)))
        (setq si (1+ si)))
      (if (and (<= cw (+ uw1 1e-6)) (<= ch (+ uh1 1e-6)))
        (progn
          (setq sc (+ 1e9 (* 1000.0 (min (- uw1 cw) (- uh1 ch)))))
          (if (or (null best) (< sc (car best))) (setq best (list sc (length slabs) 0 o cw ch t))))))
    (if best
      (progn
        (setq si (nth 1 best) j (nth 2 best) cw (nth 4 best) ch (nth 5 best))
        (if (nth 6 best) (setq slabs (append slabs (list (list (list trim trim uw1 uh1 0))))))
        (setq fr (nth si slabs) f (nth j fr)
              fx (car f) fy (cadr f) fw (caddr f) fh (cadddr f) dep (nth 4 f)
              pw (- cw kerf) ph (- ch kerf) wf (- fw cw) hf (- fh ch) nf nil
              hfirst (cond ((= sm 1) (> wf hf))
                           ((= sm 2) (>= (max (* fw hf) (* wf ch)) (max (* wf fh) (* cw hf))))
                           ((= sm 3) t)
                           ((= sm 4) nil)
                           (t (<= wf hf))))
        (cond
          (hfirst
           (if (> hf 1.0)
             (progn (setq nf (cons (list fx (+ fy ch) fw hf (1+ dep)) nf))
                    (setq cuts (cons (list si fx (+ fy ph) (+ fx fw -1.0) (+ fy ph) dep) cuts))))
           (if (> wf 1.0)
             (progn (setq nf (cons (list (+ fx cw) fy wf ch (1+ dep)) nf))
                    (setq cuts (cons (list si (+ fx pw) fy (+ fx pw) (+ fy ph) (1+ dep)) cuts)))))
          (t
           (if (> wf 1.0)
             (progn (setq nf (cons (list (+ fx cw) fy wf fh (1+ dep)) nf))
                    (setq cuts (cons (list si (+ fx pw) fy (+ fx pw) (+ fy fh -1.0) dep) cuts))))
           (if (> hf 1.0)
             (progn (setq nf (cons (list fx (+ fy ch) cw hf (1+ dep)) nf))
                    (setq cuts (cons (list si fx (+ fy ph) (+ fx pw) (+ fy ph) (1+ dep)) cuts))))))
        (setq slabs (sd:lset slabs si (append (sd:remove-nth j fr) nf)))
        (setq pl (cons (list (car it) si fx fy pw ph (nth 3 best)) pl)))
      (setq pl (cons (list (car it) nil nil nil nil nil nil) pl))))
  ;; phe lieu con lai (o trong du lon): vien nho ve sau co the dung lam ban nhap / van vun
  (setq k 0)
  (foreach fr slabs
    (foreach f fr
      (if (and (>= (- (nth 2 f) kerf) vun) (>= (- (nth 3 f) kerf) vun))
        (setq rm (cons (list k (car f) (cadr f) (- (nth 2 f) kerf) (- (nth 3 f) kerf)) rm))))
    (setq k (1+ k)))
  (list (reverse pl) (length slabs) (reverse cuts) (reverse rm)))

;; ---- ABF-style: nhieu cach sap xep / cham diem / tach o, chon ket qua tot nhat; do ky = leo doi (hoan doi thu tu) ----
;; Khoa so sanh ket qua: (so-vien-khong-xep so-tam dien-tich-dung-o-tam-cuoi so-duong-cat); nho hon la tot hon
(defun sd:ng-key (res / un lastu pl ns)
  (setq pl (car res) ns (cadr res) un 0 lastu 0.0)
  (foreach p pl
    (if (null (cadr p))
      (setq un (1+ un))
      (if (= (cadr p) (1- ns)) (setq lastu (+ lastu (* (nth 4 p) (nth 5 p)))))))
  (list un ns lastu (length (caddr res))))
(defun sd:ng-less (a b)
  (cond ((/= (car a) (car b)) (< (car a) (car b)))
        ((/= (cadr a) (cadr b)) (< (cadr a) (cadr b)))
        ((> (abs (- (caddr a) (caddr b))) 40000.0) (< (caddr a) (caddr b)))
        (t (< (cadddr a) (cadddr b)))))

;; Thu tu sap xep manh: 0 dien tich, 1 canh dai, 2 rong, 3 cao, 4 chu vi, 5 canh ngan
(defun sd:ng-sort (items m)
  (sd:sort items
    (cond ((= m 1) '(lambda (a b) (if (= (max (cadr a) (caddr a)) (max (cadr b) (caddr b)))
                                    (> (min (cadr a) (caddr a)) (min (cadr b) (caddr b)))
                                    (> (max (cadr a) (caddr a)) (max (cadr b) (caddr b))))))
          ((= m 2) '(lambda (a b) (if (= (cadr a) (cadr b)) (> (caddr a) (caddr b)) (> (cadr a) (cadr b)))))
          ((= m 3) '(lambda (a b) (if (= (caddr a) (caddr b)) (> (cadr a) (cadr b)) (> (caddr a) (caddr b)))))
          ((= m 4) '(lambda (a b) (> (+ (cadr a) (caddr a)) (+ (cadr b) (caddr b)))))
          ((= m 5) '(lambda (a b) (if (= (min (cadr a) (caddr a)) (min (cadr b) (caddr b)))
                                    (> (max (cadr a) (caddr a)) (max (cadr b) (caddr b)))
                                    (> (min (cadr a) (caddr a)) (min (cadr b) (caddr b))))))
          (t '(lambda (a b) (> (* (cadr a) (caddr a)) (* (cadr b) (caddr b))))))))

;; q: 0 nhanh (1 cach: dien tich giam dan, it thua canh ngan, tach theo canh thua ngan), 1 can bang (30 to hop sap xep x cham diem x tach o), 2 ky (them leo doi trong gioi han thoi gian)
;; Thu nghiem 12 bo: tach theo canh thua dai (sm 1) thang nhieu nhat; sap theo canh dai / cao truoc; fm 0 va 2
(defun sd:nest-g (items SW SH trim kerf rotok vun q / sorts fms sms best bk res k s fm sm ord n cur curk seed i j a b nb iter t0 bs bfm bsm bord)
  (setq q (cond (q) (0))
        sorts (if (= q 0) '(0) '(1 3 0 2 5))
        fms (if (= q 0) '(0) '(0 2))
        sms (if (= q 0) '(0) '(1 2 0)))
  (foreach s sorts
    (setq ord (sd:ng-sort items s))
    (foreach fm fms
      (foreach sm sms
        (setq res (sd:nest-g1 ord SW SH trim kerf rotok vun fm sm) k (sd:ng-key res))
        (if (or (null bk) (sd:ng-less k bk)) (setq best res bk k bord ord bfm fm bsm sm)))))
  ;; leo doi: hoan doi 2 manh trong thu tu tot nhat, nhan neu khong te hon
  (if (and (>= q 2) (> (length items) 3) (> (car (cdr bk)) 1))
    (progn
      (setq seed 12345.0 n (length bord) cur bord curk bk iter 0 t0 (getvar "MILLISECS"))
      (while (and (< iter 800) (< (- (getvar "MILLISECS") t0) 6000.0) (> (car (cdr bk)) 1))
        (setq seed (rem (+ (* seed 1664525.0) 1013904223.0) 4294967296.0) i (fix (* n (/ seed 4294967296.0)))
              seed (rem (+ (* seed 1664525.0) 1013904223.0) 4294967296.0) j (fix (* n (/ seed 4294967296.0)))
              iter (1+ iter))
        (if (/= i j)
          (progn
            (setq a (nth i cur) b (nth j cur) nb (sd:lset (sd:lset cur i b) j a)
                  res (sd:nest-g1 nb SW SH trim kerf rotok vun bfm bsm) k (sd:ng-key res))
            (if (not (sd:ng-less curk k))
              (progn (setq cur nb curk k)
                     (if (sd:ng-less k bk) (setq best res bk k))))))))
    )
  best)

;; So thu tu duong cat theo tung tam: cap nho (cat tach lon) truoc, manh nho cat sau cung
(defun sd:cut-seq (cuts)
  (sd:sort cuts '(lambda (a b)
                   (cond ((/= (car a) (car b)) (< (car a) (car b)))
                         ((/= (nth 5 a) (nth 5 b)) (< (nth 5 a) (nth 5 b)))
                         ((/= (cadr a) (cadr b)) (< (cadr a) (cadr b)))
                         (t (< (caddr a) (caddr b)))))))

;; So do cat: khung tam + vien + duong cat danh so thu tu + phe lieu
(defun sd:img-diagram2 (pls nsl SW SH pt sc cuts remn) (sd:dg-draw pls nsl SW SH pt sc cuts remn))

;; Xep + cat toan bo vien; ipcs = ((id rong cao x y da-giac) ...)
(defun sd:img-run (ipcs imst SW SH trim kerf rotok pt sc / res pls nsl n rec tot m)
  (setq res (sd:nest (mapcar '(lambda (r) (list (car r) (cadr r) (caddr r))) ipcs) SW SH trim kerf rotok)
        pls (car res) nsl (cadr res) n 0 tot 0.0)
  (foreach pl pls
    (setq rec (assoc (car pl) ipcs))
    (if (cadr pl)
      (progn
        (sd:img-piece (nth (rem (cadr pl) (length imst)) imst) pl (nth 3 rec) (nth 4 rec) (cadr rec) (caddr rec) (nth 5 rec))
        (setq n (1+ n) tot (+ tot (* (cadr rec) (caddr rec)))))
      (princ (strcat "\n[SD] Vien " (car pl) " (" (sd:num (cadr rec)) " x " (sd:num (caddr rec)) ") lon hon tam da: khong cat duoc."))))
  (if pt (sd:img-diagram pls nsl SW SH pt sc))
  (foreach m imst (vl-catch-all-apply 'vla-Delete (list (car m))))
  (princ (strcat "\n[SD] Da cat " (itoa n) " / " (itoa (length ipcs)) " vien tu anh; can " (itoa nsl) " tam da " (sd:num SW) " x " (sd:num SH)
                 (if (> nsl 0) (strcat ", hao " (sd:num (* 100.0 (- 1.0 (/ tot (* nsl SW SH))))) "%") "")
                 (if (> (length imst) 1) "" (if (> nsl 1) " (cac tam dung chung 1 anh nen van giong nhau; chon nhieu anh de doi van)" ""))
                 ".")))

(defun c:SDRAITAM (/ mode kho stk0 stk std W H jt hu van mat name thk idt sc ss i polys rooms holes room
                     outer lps loops edges R tr bb x0 y0 px py nx ny ci cj ii cx cy cs lcs cls cl gx gy gw gh
                     fit used bom pt nfull ncut ntim atim nroom pieces seq vd vp lvp rc rows n fn f rw pe vph vps
                     ang fa fo kieu off shf lo lb lx0 lx1 ly0 ly1 wg ianh e0 p0)
  (sd:begin)
  (setq sc (sd:sc) e0 (entlast))
  (if (not (sd:dlg "Rai panel / da lat theo kho (SDRAITAM)"
                   (list (list "mode" "Che do" 'kw (cond (*SD:RTMODE*) ("Panel"))
                               '(("Panel" . "Panel (kho tam + go bu INFILL-TIMBER)") ("Da" . "Da / gach lat (vien cat + huong van)")))
                         (list "kho" "Kho tam: RxD:so-luong, ... (0 / bo trong = khong han che)" 'str
                               (cond (*SD:RTKHO*) ("600x1200,450x1200,400x1200,300x1200,200x1200")))
                         (list "hu" "Canh dai cua tam song song truc" 'kw (cond (*SD:RTHU*) ("Y")) '(("Y" . "Y (tam dung)") ("X" . "X (tam nam)")))
                         (list "jt" "Mach / khe giua cac tam (mm)" 'real0 (cond (*SD:RTJT*) (0.0)))
                         (list "ang" "Goc xoay luoi rai (do)" 'real0 (cond (*SD:RTANG*) (0.0)))
                         (list "kieu" "Kieu rai" 'kw (cond (*SD:RTKIEU*) ("Thang"))
                               '(("Thang" . "Thang hang (luoi vuong)") ("Sole" . "So le theo hang (kieu gach xay)")))
                         (list "off" "Do so le (0.5 = 1/2 tam)" 'real (cond (*SD:RTOFF*) (0.5)) nil '("kieu" "Sole"))
                         (list "chieu" "Chieu van tren vien (cat anh tam da)" 'kw (cond (*SD:ICHIEU*) ("Toiuu"))
                               '(("Toiuu" . "Tu xoay 90 do de it hao") ("Doc" . "Van theo canh dai vien") ("Ngang" . "Van vuong goc canh dai") ("Chinh" . "Van theo huong vien chinh (chon 1 vien, moi vien deu 1 huong)"))
                               '("mode" "Da"))
                         (list "xep" "Cach xep vien vao tam da (cat anh)" 'kw (cond (*SD:IXEP*) ("Toiuu"))
                               '(("Toiuu" . "It hao nhat: cat xuyen, manh nho lap vao phe lieu") ("Thutu" . "Theo thu tu lat (van gan nhau)")
                                 ("Duongviem" . "Chay doc duong vien (van lien tuc)"))
                               '("mode" "Da"))
                         (list "van" "Huong van da" 'kw (cond (*SD:RTVAN*) ("Tiepnoi"))
                               '(("Khong" . "Khong ve van") ("Tiepnoi" . "Tiep noi (cung huong)") ("Doiguong" . "Doi guong (book-match)") ("Xoay4" . "Xoay 4 chieu") ("Ngaunhien" . "Ngau nhien"))
                               '("mode" "Da"))
                         (list "vp" "Hatch van da tu file .pat" 'kw (cond (*SD:VPH2*) ("Khong"))
                               '(("Khong" . "Khong hatch (chi ve duong van)") ("Platinus" . "Platinus - nen xam sang, van toi") ("DaSocDua" . "Da Soc Dua 300x600")
                                 ("ViaLactea" . "Via Lactea - nen den") ("DaVanGoXam" . "Da Van Go Xam") ("DaVanGoCo" . "Da Van Go Co") ("Khac" . "Ten pattern khac"))
                               '("mode" "Da"))
                         (list "vpn" "Ten pattern khac (file .pat trong Support Path)" 'str "" nil '("vp" "Khac"))
                         (list "vsc" "Ti le hatch (0 = khuyen nghi theo pattern)" 'real0 0.0 nil '("mode" "Da"))
                         (list "anh" "Cat anh tam da that vao cac vien (khai bao nhu SDANHDA)" 'tog nil nil '("mode" "Da"))
                         (list "mat" "Ma vat lieu da" 'str (cond (*SD:GCODE*) ("D1")) nil '("mode" "Da"))
                         (list "name" "Ten vat lieu da" 'str (cond (*SD:GNAME*) ("Granite")) nil '("mode" "Da"))
                         (list "thk" "Chieu day da (mm)" 'real (cond (*SD:GT*) (20.0)) nil '("mode" "Da"))
                         (list "idt" "Ghi so hieu tam / vien" 'tog t)
                         (list "sc" "Ty le ve 1/" 'int (fix sc)))))
    (exit))
  (setq mode (sd:v "mode") kho (sd:v "kho") hu (sd:v "hu") jt (sd:v "jt") van (sd:v "van")
        ang (sd:v "ang") kieu (sd:v "kieu") off (sd:v "off")
        mat (sd:v "mat") name (sd:v "name") thk (sd:v "thk") idt (sd:v "idt") sc (float (sd:v "sc"))
        ianh (and (= mode "Da") (sd:v "anh"))
        fa (* pi (/ ang 180.0)) *SD:RTAOFF* ang
        *SD:RTMODE* mode *SD:RTKHO* kho *SD:RTHU* hu *SD:RTJT* jt *SD:RTVAN* van *SD:RTANG* ang *SD:RTKIEU* kieu
        *SD:ICHIEU* (cond ((sd:v "chieu")) ("Toiuu")) *SD:IXEP* (cond ((sd:v "xep")) ("Toiuu")))
  (if (> (sd:v "off") 0.0) (setq *SD:RTOFF* (sd:v "off")))
  (setq vph (if (= mode "Da") (sd:v "vp")) *SD:VPH2* vph)
  (if (equal vph "Khong") (setq vph nil))
  (if (equal vph "Khac") (setq vph (sd:v "vpn")))
  (if vph (setq vps (if (> (sd:v "vsc") 0.0) (sd:v "vsc") (cadr (sd:vp-pre vph)))))
  (if (= mode "Da") (setq *SD:GCODE* mat *SD:GNAME* name *SD:GT* thk))
  (setq stk0 (sd:rt-parse kho))
  (if (null stk0) (progn (princ "\n[SD] Kho tam sai dinh dang (VD 600x1200,400x1200:20).") (exit)))
  ;; tam tieu chuan = dien tich lon nhat, dat theo huong canh dai
  (setq std (car (sd:sort stk0 '(lambda (a b) (> (* (car a) (cadr a)) (* (car b) (cadr b))))))
        W (if (= hu "Y") (min (car std) (cadr std)) (max (car std) (cadr std)))
        H (if (= hu "Y") (max (car std) (cadr std)) (min (car std) (cadr std)))
        stk (sd:rt-orient stk0))
  (princ (strcat "\nTam tieu chuan " (sd:num W) " x " (sd:num H) " - rai tu goc (X, Y nho nhat) cua tung o"
                 (if (/= ang 0.0) (strcat ", luoi xoay " (sd:num ang) " do") "") (if (= kieu "Sole") ", so le theo hang" "") "."))
  (princ "\nChon cac polyline kin la o / phong can rai (polyline nam trong o khac = lo / cot): ")
  (if (setq ss (ssget '((0 . "LWPOLYLINE") (-4 . "&") (70 . 1))))
    (progn
      (setq i 0)
      (repeat (sslength ss) (setq polys (cons (sd:rt-poly-of (ssname ss i)) polys) i (1+ i)))
      ;; phan loai: polyline nam trong polyline khac lon hon -> lo cua o do
      (foreach p polys
        (if (vl-some '(lambda (q) (and (not (eq (car q) (car p))) (> (caddr q) (caddr p)) (sd:inpoly (car (cadr p)) (cadr q)))) polys)
          nil
          (setq rooms (cons p rooms))))
      (setq p0 (sd:getpt "\nDiem bat dau rai tam (luoi tam di qua diem nay) <goc X, Y nho nhat cua o>: " nil))
      (if (= mode "Panel") (setq pt (sd:getpt "\nDiem chen bang thong ke <bo qua>: " nil)))
      (setq used nil bom nil nroom 0 nfull 0 ncut 0 ntim 0 atim 0.0)
      (foreach room (reverse rooms)
        (setq nroom (1+ nroom) outer (cadr room) holes nil)
        (foreach p polys
          (if (and (not (eq (car p) (car room))) (< (caddr p) (caddr room)) (sd:inpoly (car (cadr p)) outer))
            (setq holes (cons p holes))))
        (setq lps (mapcar 'cadr holes) loops (cons outer lps) edges (sd:edges loops)
              R (sd:region (car room)))
        (if (null R)
          (princ (strcat "\n[SD] O " (itoa nroom) ": khong tao duoc region (polyline tu cat nhau?), bo qua."))
          (progn
            (foreach hp holes (if (setq tr (sd:region (car hp))) (vla-Boolean R 2 tr)))
            ;; khung toa do cuc bo xoay goc fa quanh goc bbox; luoi rai bat dau tu goc X, Y nho nhat trong khung do
            (setq bb (sd:bbox outer) fo (if p0 (list (car p0) (cadr p0)) (list (caar bb) (cadar bb)))
                  x0 (car fo) y0 (cadr fo)
                  lo (mapcar '(lambda (q) (sd:w2l fo fa q)) outer)
                  lb (sd:bbox lo) lx0 (caar lb) ly0 (cadar lb) lx1 (car (cadr lb)) ly1 (cadr (cadr lb))
                  px (+ W jt) py (+ H jt))
            ;; co diem bat dau: luoi tam di qua diem do (can ve o luoi gan nhat phia duoi-trai bbox)
            (if p0
              (setq lx0 (* px (- (fix (/ lx0 px)) 1)) ly0 (* py (- (fix (/ ly0 py)) 1))))
            (setq nx (+ 3 (fix (/ (- lx1 lx0) px))) ny (+ 2 (fix (/ (- ly1 ly0) py))) seq 0 pieces nil cj 0)
            (repeat ny
              (setq ci 0 shf (if (= kieu "Sole") (* px (rem (* cj off) 1.0)) 0.0))
              (repeat nx
                (setq ii (if (= (rem cj 2) 0) ci (- nx 1 ci))
                      cx (+ lx0 (if (> shf 1e-6) (- shf px) 0.0) (* ii px)) cy (+ ly0 (* cj py))
                      lcs (list (list cx cy) (list (+ cx W) cy) (list (+ cx W) (+ cy H)) (list cx (+ cy H)))
                      cs (mapcar '(lambda (q) (sd:l2w fo fa q)) lcs)
                      cls (sd:tile-class cs outer lps loops edges) cl nil)
                (if (= cls "P")
                  (progn
                    (setq cl (sd:rt-clip R cs (if (= mode "Da") "SD-GACH-CAT" "INFILL-TIMBER")))
                    (cond ((null cl) (setq cls nil))
                          ((>= (car cl) (* 0.99999 W H)) (foreach x (cadr cl) (entdel x)) (setq cls "F" cl nil)))))
                (cond
                  ;; ---- vien nguyen
                  ((= cls "F")
                   (setq seq (1+ seq))
                   (if (= mode "Panel")
                     (progn
                       (setq fit (sd:rt-fit W H stk used) used (caddr fit))
                       (sd:rt-put-panels (car fit) cx cy stk0 sc idt fo fa)
                       (foreach p (car fit) (setq bom (sd:al-add bom (sd:rt-code (caddr p) (cadddr p)) 1) nfull (1+ nfull)))
                       (sd:rt-put-timber (cadr fit) cx cy sc fo fa)
                       (foreach p (cadr fit) (setq ntim (1+ ntim) atim (+ atim (* (caddr p) (cadddr p))) bom (sd:al-add bom "GO-BU" 1))))
                     (progn
                       (sd:mk-tile-poly "SD-GACH" cs
                                      (sd:tile-xd mat "F" mat W H (* W H) 0 name W H fa thk "R"))
                       (setq nfull (1+ nfull) pe (entlast) vd (sd:rt-vein van ii cj))
                       (if vph (sd:rt-vh (list pe) vph vps van vd (car (car cs)) (cadr (car cs)) x0 y0)
                         (if vd (sd:pline (mapcar '(lambda (q) (sd:l2w fo fa q)) (sd:rt-vpts vd cx cy W H)) nil "SD-GACH-VAN")))
                       (if idt (sd:text (sd:l2w fo fa (list (+ cx (/ W 2.0)) (+ cy (/ H 2.0)))) (strcat (itoa nroom) "." (itoa seq))
                                        (sd:tile-th W H sc) "MC" "SD-CHU")))))
                  ;; ---- o bi cat boi bien / lo
                  ((and cl (= cls "P"))
                   (setq vp (caddr cl) lvp (mapcar '(lambda (q) (sd:w2l fo fa q)) vp)
                         gx (apply 'min (mapcar 'car lvp)) gy (apply 'min (mapcar 'cadr lvp))
                         gw (- (apply 'max (mapcar 'car lvp)) gx) gh (- (apply 'max (mapcar 'cadr lvp)) gy)
                         wg (sd:l2w fo fa (list gx gy)))
                   (if (>= (car cl) (* 0.999999 gw gh))
                     (progn
                       ;; phan thieu hut hinh chu nhat (trong khung xoay)
                       (foreach x (cadr cl) (entdel x))
                       (if (= mode "Panel")
                         (progn
                           (setq fit (sd:rt-fit gw gh stk used) used (caddr fit))
                           (sd:rt-put-panels (car fit) gx gy stk0 sc idt fo fa)
                           (foreach p (car fit) (setq bom (sd:al-add bom (sd:rt-code (caddr p) (cadddr p)) 1) nfull (1+ nfull)))
                           (sd:rt-put-timber (cadr fit) gx gy sc fo fa)
                           (foreach p (cadr fit) (setq ntim (1+ ntim) atim (+ atim (* (caddr p) (cadddr p))) bom (sd:al-add bom "GO-BU" 1))))
                         (progn
                           (sd:pline (mapcar '(lambda (q) (sd:l2w fo fa q))
                                             (list (list gx gy) (list (+ gx gw) gy) (list (+ gx gw) (+ gy gh)) (list gx (+ gy gh))))
                                     t "SD-GACH-CAT")
                           (setq pe (entlast))
                           (if vph (sd:rt-vh (list pe) vph vps van (sd:rt-vein van ii cj) (car wg) (cadr wg) x0 y0))
                           (setq seq (1+ seq)
                                 pieces (cons (list (list pe) gw gh (car cl) (sd:rect-typ gw gh (car cl) nil)
                                                    (sd:centroid vp) (list gx gy) (list 0.0 0.0 0.0) fa) pieces)))))
                     ;; hinh bat ky (cat boi duong cheo / lo): khong rai tam duoc
                     (progn
                       (setq seq (1+ seq))
                       (if (= mode "Panel")
                         (progn (setq ntim (1+ ntim) atim (+ atim (car cl)) bom (sd:al-add bom "GO-BU" 1))
                                (sd:text (sd:centroid vp) "GO" (* 1.6 sc) "MC" "SD-CHU"))
                         (progn (if vph (sd:rt-vh (cadr cl) vph vps van (sd:rt-vein van ii cj) (car wg) (cadr wg) x0 y0))
                                (setq pieces (cons (list (cadr cl) gw gh (car cl) "D" (sd:centroid vp) (list gx gy) (list 0.0 0.0 0.0) fa) pieces))))))))
                (setq ci (1+ ci)))
              (setq cj (1+ cj)))
            (if (and (= mode "Da") pieces)
              (progn (setq rc (sd:code-pieces (reverse pieces) mat name W H thk nil sc))
                     (setq ncut (+ ncut (length pieces)))))
            (vla-Delete R))))
      (if (= mode "Panel")
        (progn
          (princ (strcat "\n[SD] " (itoa nroom) " o: " (itoa nfull) " tam (" (itoa (length (vl-remove "GO-BU" (mapcar 'car bom)))) " loai); go bu "
                         (itoa ntim) " manh, " (sd:rtos (/ atim 1e6) 2) " m2 (layer INFILL-TIMBER)."))
          (if (and pt bom)
            (progn
              (setq bom (sd:al-sorted bom) rows nil n 0)
              (foreach b bom
                (setq n (1+ n)
                      rows (cons (list "R" (list (itoa n) (car b) (if (= (car b) "GO-BU") "Go bu mep bien (INFILL-TIMBER)" "Tam rai theo kho") (itoa (cdr b))) nil) rows)))
              (sd:table2 pt "THONG KE RAI TAM" '(("STT" 10) ("MA TAM" 34) ("LOAI" 52) ("SL" 14)) (reverse rows) -1 sc)
              (if (setq f (sd:open (setq fn (sd:csv-name "_RaiTam.csv")) "w"))
                (progn (write-line "STT,Ma tam,Loai,So luong" f)
                       (foreach rw rows (write-line (sd:join (cadr rw) ",") f))
                       (princ (strcat "\n[SD] Da xuat: " (sd:close f))))))))
        (princ (strcat "\n[SD] " (itoa nroom) " o: " (itoa nfull) " vien nguyen, " (itoa ncut) " vien cat"
                       ". Dung SDGACHTK / SDTKDA de thong ke, SDDATHO cat tu da tho, SDGIACONG ve gia cong.")))
      (setq *SD:RTAOFF* 0.0)
      (if ianh (progn (setq *SD:IFRAME* (if (>= W H) fa (+ fa (/ pi 2.0)))) (sd:anhda (sd:gach-new e0)) (setq *SD:IFRAME* nil))))
    (princ "\n[SD] Chua chon o nao."))
  (setq *SD:RTAOFF* 0.0)
  (sd:finish))

;; 4 dinh (toa do that) cua hinh chu nhat trong khung cuc bo (fo, fa): goc (ox + x, oy + y), rong w, cao h
(defun sd:rt-lw (fo fa ox oy x y w h)
  (mapcar '(lambda (p) (sd:l2w fo fa p))
          (list (list (+ ox x) (+ oy y)) (list (+ ox x w) (+ oy y)) (list (+ ox x w) (+ oy y h)) (list (+ ox x) (+ oy y h)))))

;; Ve tam (x y rong cao tuong doi goc ox oy trong khung cuc bo)
(defun sd:rt-put-panels (pan ox oy stk0 sc idt fo fa / code)
  (foreach p pan
    (setq code (sd:rt-code (caddr p) (cadddr p)))
    (sd:pline (sd:rt-lw fo fa ox oy (car p) (cadr p) (caddr p) (cadddr p)) t "SD-PANEL")
    (sd:col-last (sd:rt-color code stk0))
    (if idt (sd:text (sd:l2w fo fa (list (+ ox (car p) (/ (caddr p) 2.0)) (+ oy (cadr p) (/ (cadddr p) 2.0))))
                     (sd:num (min (caddr p) (cadddr p))) (sd:tile-th (caddr p) (cadddr p) sc) "MC" "SD-CHU"))))

;; Ve go bu: khung + duong cheo tren layer INFILL-TIMBER
(defun sd:rt-put-timber (tim ox oy sc fo fa)
  (foreach p tim
    (sd:pline (sd:rt-lw fo fa ox oy (car p) (cadr p) (caddr p) (cadddr p)) t "INFILL-TIMBER")
    (sd:line (sd:l2w fo fa (list (+ ox (car p)) (+ oy (cadr p))))
             (sd:l2w fo fa (list (+ ox (car p) (caddr p)) (+ oy (cadr p) (cadddr p)))) "INFILL-TIMBER")))

;;; --------------------------------------------------------------------------
;;;  SDKIEMTRA - Tac tu kiem tra ban ve (theo luat, chi doc, khong sua ban ve)
;;;  Gom ket qua kiem tra thep (so hieu, ky hieu trung / mo coi, chu sua tay, bang thong ke), mat bang <-> khai trien,
;;;  chuan layer, kich thuoc ghi tay, Xref mat; xep theo muc uu tien, goi y lenh chay tiep.
;;;  Xuat them file .json de tac tu AI ben ngoai (LLM) doc va dien giai.
;;; --------------------------------------------------------------------------
(defun sd:ag-dups (/ ss i tag xd g o r)
  (if (setq ss (ssget "_X" '((0 . "CIRCLE") (-3 ("SD_REBAR")))))
    (progn
      (setq i 0)
      (repeat (sslength ss)
        (setq tag (ssname ss i) i (1+ i) xd (mapcar 'cdr (cdadr (assoc -3 (entget tag '("SD_REBAR"))))))
        (if (and (= (nth 8 xd) "TM") (/= (nth 9 xd) ""))
          (if (setq o (assoc (nth 9 xd) g))
            (setq g (subst (append o (list (nth 0 xd))) o g))
            (setq g (cons (list (nth 9 xd) (nth 0 xd)) g)))))
      (foreach x g
        (if (cddr x)
          (setq r (cons (strcat "1 thanh co " (itoa (length (cdr x))) " ky hieu: " (sd:join (cdr x) ", ")) r))))))
  (reverse r))

;; So ky hieu thep co chu sua tay lech du lieu (so hieu, o, so thanh) - chay thu, khong ghi
(defun sd:ag-sync-diff (/ ss i tag ed xd tx te mk lb n)
  (setq tx (sd:bt-texts) n 0 i 0)
  (if (setq ss (ssget "_X" '((0 . "CIRCLE") (-3 ("SD_REBAR")))))
    (repeat (sslength ss)
      (setq tag (ssname ss i) i (1+ i) ed (entget tag '("SD_REBAR")) xd (mapcar 'cdr (cdadr (assoc -3 ed))))
      (if (or (and (setq te (cdr (assoc (sd:bt-pkey (cond ((cdr (assoc 410 ed))) ("Model")) (cdr (assoc 10 ed))) tx)))
                   (setq mk (vl-string-trim " " (cdr (assoc 1 (entget te)))))
                   (/= mk "") (/= mk (nth 0 xd)))
              (and (= (nth 8 xd) "TM") (setq te (sd:ent-ok (nth 10 xd)))
                   (setq lb (sd:tag-parse (cdr (assoc 1 (entget te)))))
                   (or (not (equal (cadr lb) (nth 2 xd) 1e-6))
                       (and (/= (car lb) (nth 1 xd)) (= (nth 11 xd) 0)))))
        (setq n (1+ n)))))
  n)

(defun sd:ag-orphans (/ ss i xd n)
  (setq n 0 i 0)
  (if (setq ss (ssget "_X" '((0 . "CIRCLE") (-3 ("SD_REBAR")))))
    (repeat (sslength ss)
      (setq xd (mapcar 'cdr (cdadr (assoc -3 (entget (ssname ss i) '("SD_REBAR"))))) i (1+ i))
      (if (sd:tm-orphan-p xd) (setq n (1+ n)))))
  n)

;; Bang thong ke tu cap nhat da lac hau so voi thep tren ban ve?
(defun sd:ag-tk-stale (/ a)
  (setq a (vlax-ldata-get "SD" "TKAUTO"))
  (and a (= (caddr a) (getvar "CTAB")) (/= (sd:tk-sig (sd:tk-all)) (nth 4 a))))

;; Mat bang <-> khai trien theo cau hinh SDLIENKET da luu: (ten-co-tren-MB-chua-KT ... ) (ten-KT-khong-co-tren-MB ...) hoac nil neu chua cau hinh
(defun sd:ag-lk (/ old lay pat tang ss i ed s nm plan det o a b)
  (setq old (vlax-ldata-get "SD" "LKT")
        lay (vl-string-trim " " (cond ((cdr (assoc "lay" old))) (""))))
  (if (and old (/= lay ""))
    (progn
      (setq pat (strcase (cond ((cdr (assoc "pat" old))) ("@*#*")))
            tang (strcase (vl-string-trim " " (cond ((cdr (assoc "tang" old))) ("")))))
      (if (setq ss (ssget "_X" (list '(0 . "TEXT,MTEXT") (cons 8 lay))))
        (progn
          (setq i 0)
          (repeat (sslength ss)
            (setq ed (entget (ssname ss i)) i (1+ i)
                  s (if (= (cdr (assoc 0 ed)) "MTEXT")
                      (sd:mt-plain (vla-get-TextString (vlax-ename->vla-object (cdr (assoc -1 ed)))))
                      (cdr (assoc 1 ed)))
                  nm (strcase (sd:lk-name s)))
            (if (and (/= nm "") (wcmatch nm pat)) (if (not (member nm plan)) (setq plan (cons nm plan)))))))
      (if (setq ss (ssget "_X" '((-3 ("SD_KL")))))
        (progn
          (setq i 0)
          (repeat (sslength ss)
            (setq o (mapcar 'cdr (cdadr (assoc -3 (entget (ssname ss i) '("SD_KL"))))) i (1+ i))
            (if (or (= tang "") (= (strcase (cond ((nth 6 o)) (""))) tang))
              (if (not (member (strcase (car o)) det)) (setq det (cons (strcase (car o)) det)))))))
      (list (sd:sort (vl-remove-if '(lambda (x) (member x det)) plan) 'sd:fl<)
            (sd:sort (vl-remove-if '(lambda (x) (member x plan)) det) 'sd:fl<)))))

;; Layer SD lech chuan (mau / net / be rong net): danh sach chuoi
(defun sd:ag-layers (/ r d)
  (foreach l *SD:LAYERS*
    (if (tblsearch "LAYER" (car l))
      (if (and (setq d (sd:lay-dev l)) (/= d '("chua co")))
        (setq r (cons (strcat (car l) " (" (sd:join d ", ") ")") r)))))
  (reverse r))

;; Kich thuoc ghi tay: (so-ghi-tay so-lech-so-do)
(defun sd:ag-dims (/ ss i ed s m v n nl)
  (setq n 0 nl 0 i 0)
  (if (setq ss (ssget "_X" '((0 . "DIMENSION"))))
    (repeat (sslength ss)
      (setq ed (entget (ssname ss i)) i (1+ i))
      (if (sd:dim-hand-p ed)
        (progn
          (setq n (1+ n) s (cdr (assoc 1 ed)) m (cdr (assoc 42 ed)) v (sd:dim-num s))
          (if (and v m (> (abs (- v m)) 1.0)) (setq nl (1+ nl)))))))
  (list n nl))

(defun sd:ag-xref (/ r i)
  (vlax-for b (vla-get-Blocks (sd:doc))
    (if (= (vla-get-IsXRef b) :vlax-true)
      (progn (setq i (sd:xr-info b))
             (if (null (caddr i)) (setq r (cons (car i) r))))))
  (reverse r))

(defun sd:jesc (s / r c)
  (setq r "")
  (foreach ch (vl-string->list s)
    (setq c (cond ((= ch 92) "\\\\") ((= ch 34) "\\\"") ((< ch 32) " ") (t (chr ch))))
    (setq r (strcat r c)))
  r)

(defun sd:ag-limit (lst n) (if (> (length lst) n) (append (sd:head n lst) (list (strcat "... va " (itoa (- (length lst) n)) " muc nua"))) lst))

;; Mot ket qua: (muc-do khu-vuc mo-ta lenh chi-tiet...)
(defun c:SDKIEMTRA (/ ct fs ntag tags chk1 chk2 m1 m2 dup sy orph lk lay dm xr z0 nz f rank cmds sev out fn fl js first)
  (sd:begin)
  (if (not (sd:dlg "Tac tu kiem tra ban ve (SDKIEMTRA)"
                   (list (list "note" "Chi doc, khong sua ban ve: tong hop loi, xep uu tien, goi y lenh chay tiep" 'note nil)
                         (list "luu" "Luu bao cao (.md va .json) canh file ban ve" 'tog t)
                         (list "ct" "So dong chi tiet moi muc" 'int 5))))
    (exit))
  (setq ct (max 1 (sd:v "ct")) fs nil)
  ;; ---- thep
  (setq tags (sd:bt-tags) ntag (length tags))
  (if tags
    (progn
      (setq m1 (car (sd:bt-check tags nil)) m2 (car (sd:bt-check tags t)))
      (cond (m2 (setq fs (cons (append (list "Cao" "Thep" (strcat (itoa (length m2)) " so hieu thep lech quy cach (tinh theo tung cau kien)") "SDBONGTHEP") m2) fs)))
            (m1 (setq fs (cons (append (list "Thap" "Thep" (strcat (itoa (length m1)) " so hieu / quy cach dung chung giua cac cau kien (dung neu danh so toan ban ve)") "SDBONGTHEP") m1) fs))))
      (if (setq dup (sd:ag-dups))
        (setq fs (cons (append (list "Cao" "Thep" (strcat (itoa (length dup)) " thanh thep co nhieu ky hieu (bi tinh trung khoi luong)") "SDTHEPTM") dup) fs)))
      (if (> (setq sy (sd:ag-sync-diff)) 0)
        (setq fs (cons (list "TB" "Thep" (strcat (itoa sy) " ky hieu co chu sua tay lech du lieu thep (bang thong ke chua theo)") "SDTKTHEP") fs)))
      (if (> (setq orph (sd:ag-orphans)) 0)
        (setq fs (cons (list "TB" "Thep" (strcat (itoa orph) " ky hieu thep mo coi (thanh thep da bi xoa)") "SDTHEPTM") fs)))
      (if (sd:ag-tk-stale)
        (setq fs (cons (list "TB" "Thep" "Bang thong ke tu cap nhat chua khop thep tren ban ve" "SDTKTHEP") fs)))))
  ;; ---- mat bang <-> khai trien
  (if (setq lk (sd:ag-lk))
    (progn
      (if (car lk) (setq fs (cons (append (list "Cao" "Mat bang" (strcat (itoa (length (car lk))) " cau kien co tren mat bang nhung chua khai trien") "SDLIENKET") (car lk)) fs)))
      (if (cadr lk) (setq fs (cons (append (list "TB" "Mat bang" (strcat (itoa (length (cadr lk))) " cau kien da khai trien nhung khong thay tren mat bang") "SDLIENKET") (cadr lk)) fs))))
    (if (ssget "_X" '((-3 ("SD_KL"))))
      (setq fs (cons (list "Thap" "Mat bang" "Chua cau hinh doi chieu mat bang - khai trien (chay SDLIENKET mot lan)" "SDLIENKET") fs))))
  ;; ---- chuan ban ve
  (if (setq lay (sd:ag-layers))
    (setq fs (cons (append (list "TB" "Chuan" (strcat (itoa (length lay)) " layer SD lech chuan (mau / net / be rong net)") "SDCHUAN") lay) fs)))
  (setq nz (if (setq z0 (ssget "_X" '((8 . "0")))) (sslength z0) 0))
  (if (> nz 0) (setq fs (cons (list "Thap" "Chuan" (strcat (itoa nz) " doi tuong nam tren layer 0") "SDCHUAN") fs)))
  ;; ---- kich thuoc ghi tay
  (setq dm (sd:ag-dims))
  (cond ((> (cadr dm) 0) (setq fs (cons (list "TB" "Kich thuoc" (strcat (itoa (cadr dm)) " kich thuoc ghi tay lech so do that (tren " (itoa (car dm)) " kich thuoc ghi tay)") "SDDIMTAY") fs)))
        ((> (car dm) 0) (setq fs (cons (list "Thap" "Kich thuoc" (strcat (itoa (car dm)) " kich thuoc ghi tay (khong lech so do)") "SDDIMTAY") fs))))
  ;; ---- xref
  (if (setq xr (sd:ag-xref))
    (setq fs (cons (append (list "Cao" "Xref" (strcat (itoa (length xr)) " Xref mat duong dan / khong tim thay file") "SDXREF") xr) fs)))
  ;; ---- sap xep theo muc uu tien, in bao cao
  (setq rank '(("Cao" . 0) ("TB" . 1) ("Thap" . 2))
        fs (sd:sort (reverse fs) '(lambda (a b) (< (cdr (assoc (car a) rank)) (cdr (assoc (car b) rank))))))
  (setq out (list (strcat "TAC TU KIEM TRA BAN VE (SDKIEMTRA, ShopDrawing v" *SD:VER* ")")
                  (strcat "Ky hieu thep: " (itoa ntag) " | Kich thuoc ghi tay: " (itoa (car dm)) " | Vi pham: " (itoa (length fs)))))
  (if (null fs)
    (setq out (append out (list "Khong phat hien van de trong cac muc da kiem tra.")))
    (progn
      (foreach f fs
        (setq out (append out (list (strcat "[" (car f) "] " (cadr f) ": " (caddr f) "  -> " (cadddr f)))
                          (mapcar '(lambda (x) (strcat "      - " x)) (sd:ag-limit (nthcdr 4 f) ct)))))
      (setq cmds nil)
      (foreach f fs (if (not (member (cadddr f) cmds)) (setq cmds (append cmds (list (cadddr f))))))
      (setq out (append out (list "GOI Y CHAY TIEP (theo thu tu uu tien): " (sd:join cmds "  ->  "))))))
  (textscr)
  (foreach l out (princ (strcat "\n" l)))
  ;; ---- luu bao cao
  (if (sd:v "luu")
    (progn
      (if (setq fl (sd:open (setq fn (sd:csv-name "_KiemTra.md")) "w"))
        (progn (write-line "# Bao cao kiem tra ban ve" fl)
               (foreach l (cdr out) (write-line (strcat "- " l) fl))
               (princ (strcat "\n[SD] Da luu bao cao: " (sd:close fl)))))
      (if (setq fl (sd:open (setq fn (sd:csv-name "_KiemTra.json")) "w"))
        (progn
          (write-line (strcat "{\"version\":\"" *SD:VER* "\",\"rebar_tags\":" (itoa ntag) ",\"findings\":[") fl)
          (setq first t)
          (foreach f fs
            (write-line (strcat (if first "" ",") "{\"severity\":\"" (sd:jesc (car f)) "\",\"area\":\"" (sd:jesc (cadr f))
                                "\",\"message\":\"" (sd:jesc (caddr f)) "\",\"command\":\"" (cadddr f) "\",\"details\":["
                                (cond ((sd:join (mapcar '(lambda (x) (strcat "\"" (sd:jesc x) "\"")) (nthcdr 4 f)) ",")) ("")) "]}") fl)
            (setq first nil))
          (write-line "]}" fl)
          (princ (strcat "\n[SD] Da luu du lieu cho tac tu AI: " (sd:close fl)))))))
  (sd:finish))

;;; --------------------------------------------------------------------------
;;;  SDQUYTRINH - Hop thoai DCL thong minh: quy trinh da lat, ra lenh lien hoan
;;;  Doc trang thai ban ve (so vien, anh tam da, anh da cat, hatch van), goi y buoc tiep theo, chay tung buoc hoac
;;;  chay lien hoan cac buoc da chon; sau moi buoc quay lai hop thoai.
;;; --------------------------------------------------------------------------
(setq *SD:QTSTEPS*
  '(("SDRAITAM" "Chia vien / rai tam theo kho (Panel hoac Da, vien cat mep, go bu)" "Chon Da: vien nguyen + vien cat, so hieu theo thu tu lat. Panel: tam tieu chuan + tam di hinh + go bu.")
    ("SDGACH"   "Chia vien op lat cho 1 vung (thang / so le / xuong ca / chevron, vien vien)" "Dung khi chi can 1 vung, hoac can kieu lat xuong ca / chevron.")
    ("SDDOCDA"  "Doc mat bang op lat (net roi) -> dung o kin, bang CSV / JSON, ma vat lieu, khoet lo / cot, ve polyline" "Quet chon net mat bang; soat bang trong Excel; Ve de tao polyline kin roi SDANHDA (khong can ve lai polyline).")
    ("SDANHDA"  "Cat anh tam da tho vao cac vien (IMAGECLIP, xep cat xuyen, thu tu cat)" "Chen anh tam da (IMAGEATTACH) truoc. Quet chon polyline vien; chon chieu van va cach xep.")
    ("SDVANDA"  "Hatch van da tu file .pat len vien (khi khong co anh that)" "Chon pattern Platinus / DaSocDua / ViaLactea / DaVanGoXam / DaVanGoCo; Tiepnoi de van chay lien tuc.")
    ("SDGACHTK" "Thong ke vien + du tru so vien dat hang" "Bang ma vien, loai, kich thuoc, so luong, dien tich + dong dat hang.")
    ("SDDATHO"  "So do cat vien tu da tho (kho tam, hao phi)" "Dung khi mua da tho: tinh so tam va ve so do cat.")
    ("SDGIACONG" "Ban ve gia cong tung ma vien gui xuong" "Moi ma vien mot the gia cong kem kich thuoc.")
    ("SDTKDA"   "Quet polyline vien da cat -> bang thong ke nhom kich thuoc + chi tiet tung vien" "Bang ma V1..., kich thuoc, SL, dien tich, canh mai; chi tiet tung vien kem ma T.. va tam da so (sau SDANHDA).")
    ("SDDOCDATK" "Thong ke vien da sau SDDOCDA kieu SDGACHTK: bang nhom kich thuoc + dat tam da" "Nhap kho tam da, hao hut %; bang V1.. + dong dat hang + CSV.")
    ("SDANHDATK" "Thong ke tam da sau SDANHDA kieu SDGACHTK: so vien, hao hut tung tam + dat tam" "Nhap kho tam da, hao hut %; bang theo tam da so + dong dat hang + CSV.")
    ("SDKIEMTRA" "Tac tu kiem tra ban ve (chi doc), goi y lenh chay tiep" "Tong hop loi thep / mat bang / chuan / dim / Xref theo muc uu tien.")))

(defun sd:qt-cnt (flt / ss) (if (setq ss (ssget "_X" flt)) (sslength ss) 0))
;; Trang thai ban ve: (so-vien so-anh-tam so-anh-da-cat so-hatch-van)
(defun sd:qt-state ()
  (list (sd:qt-cnt '((0 . "LWPOLYLINE") (8 . "SD-GACH,SD-GACH-CAT,SD-GACH-DOC")))
        (sd:qt-cnt '((0 . "IMAGE")))
        (sd:qt-cnt '((8 . "SD-GACH-ANH")))
        (sd:qt-cnt '((0 . "HATCH") (8 . "SD-GACH-VAN")))))
;; Buoc goi y tiep theo (chi so trong *SD:QTSTEPS*)
(defun sd:qt-next (st)
  (cond ((= (car st) 0) 0)
        ((and (> (cadr st) 0) (= (caddr st) 0)) 3)
        ((and (= (caddr st) 0) (= (cadddr st) 0)) 4)
        (t 5)))

(defun sd:qt-run (cmd / r)
  (princ (strcat "\n[SD] === Chay " cmd " ==="))
  (setq r (vl-catch-all-apply '(lambda () (apply (read (strcat "c:" cmd)) nil)) nil))
  (if (vl-catch-all-error-p r) (princ (strcat "\n[SD] " cmd " dung: " (vl-catch-all-error-message r)))))

(defun sd:qt-dcl (fn / f)
  (if (setq f (open fn "w"))
    (progn
      (foreach l '("sdqt : dialog { label = \"Quy trinh da lat - ra lenh lien hoan (SDQUYTRINH)\";"
                   "  : text { key = \"info\"; width = 84; }"
                   "  : list_box { key = \"lst\"; multiple_select = true; width = 84; height = 10; allow_accept = false; }"
                   "  : text { key = \"hint\"; width = 84; }"
                   "  : text { label = \"Chon 1 buoc de chay, hoac tich nhieu buoc (Ctrl / Shift) roi bam Chay lien hoan.\"; }"
                   "  : row {"
                   "    : button { key = \"run\"; label = \"Chay buoc chon\"; width = 20; is_default = true; }"
                   "    : button { key = \"chain\"; label = \"Chay lien hoan\"; width = 20; }"
                   "    : button { key = \"help\"; label = \"Huong dan\"; width = 14; }"
                   "    : cancel_button { label = \"Dong\"; width = 12; }"
                   "  }"
                   "}")
        (write-line l f))
      (close f)
      fn)))

(defun sd:qt-idx (s / r)
  (foreach x (sd:split (vl-string-trim " " s) " ") (if (/= x "") (setq r (cons (atoi x) r))))
  (reverse r))

(defun c:SDQUYTRINH (/ fn id res st rec sel more idxs)
  (setq fn (vl-filename-mktemp "sdqt" nil ".dcl") more t sel nil)
  (if (not (sd:qt-dcl fn))
    (princ "\n[SD] Khong tao duoc hop thoai (DCL). Chay lan luot: SDRAITAM, SDANHDA, SDVANDA, SDGACHTK.")
    (while more
      (setq st (sd:qt-state) rec (sd:qt-next st))
      (if (and (setq id (load_dialog fn)) (> id 0) (new_dialog "sdqt" id))
        (progn
          (set_tile "info" (strcat "Hien co: " (itoa (car st)) " vien | " (itoa (cadr st)) " anh | " (itoa (caddr st)) " anh da cat | "
                                   (itoa (cadddr st)) " hatch van.   Goi y: " (car (nth rec *SD:QTSTEPS*))))
          (start_list "lst")
          (setq idxs 0)
          (foreach s *SD:QTSTEPS*
            (add_list (strcat (itoa (1+ idxs)) ".  " (sd:pad (car s) 11) (cadr s) (if (= idxs rec) "   <== goi y" "")))
            (setq idxs (1+ idxs)))
          (end_list)
          (set_tile "lst" (cond (sel) ((itoa rec))))
          (set_tile "hint" (caddr (nth rec *SD:QTSTEPS*)))
          (action_tile "lst" "(setq *SD:QTSEL* $value) (set_tile \"hint\" (caddr (nth (car (sd:qt-idx $value)) *SD:QTSTEPS*)))")
          (action_tile "run" "(setq *SD:QTSEL* (get_tile \"lst\")) (done_dialog 2)")
          (action_tile "chain" "(setq *SD:QTSEL* (get_tile \"lst\")) (done_dialog 3)")
          (action_tile "help" "(alert (strcat \"QUY TRINH DA LAT:\\n1. SDRAITAM / SDGACH: chia vien tren cac vung.\\n2. SDANHDA: chen anh tam da roi cat anh vao vien (hoac SDVANDA hatch van).\\n3. SDGACHTK / SDDATHO / SDGIACONG: thong ke, so do cat, ban ve gia cong.\\n4. SDKIEMTRA: kiem tra truoc khi phat hanh.\\nXem them HuongDanQuyTrinhDa.md trong thu muc cai dat.\"))")
          (action_tile "cancel" "(done_dialog 0)")
          (setq res (start_dialog))
          (unload_dialog id)
          (cond
            ((member res '(2 3))
             (setq sel *SD:QTSEL* idxs (sd:qt-idx (cond (sel) ("")))
                   idxs (if (= res 2) (list (cond ((car idxs)) (rec))) (if idxs idxs (list rec))))
             (foreach i idxs (sd:qt-run (car (nth i *SD:QTSTEPS*)))))
            (t (setq more nil))))
        (progn (princ "\n[SD] Khong mo duoc hop thoai.") (setq more nil)))))
  (vl-file-delete fn)
  (princ))

;;; --------------------------------------------------------------------------
;;;  SDTKDA - Quet polyline vien da cat -> bang thong ke (nhom theo kich thuoc, chi tiet tung vien, tam da, CSV)
;;;  Doc truc tiep hinh hoc polyline (khong can du lieu SD_TILE): kich thuoc theo canh dai nhat, dien tich, chu vi (canh mai),
;;;  hinh dang (chu nhat / da giac vat); neu da chay SDANHDA thi them cot ma vien T.. va tam da so.
;;; --------------------------------------------------------------------------
(defun sd:tk-meas (e / pts fr ar pe lg sh)
  (setq pts (sd:curve-pts e) fr (sd:tile-frame pts) ar (abs (sd:area pts))
        pe (vlax-curve-getDistAtParam e (vlax-curve-getEndParam e))
        lg (max (cadr fr) (caddr fr)) sh (min (cadr fr) (caddr fr)))
  ;; (dai rong dien-tich chu-vi hinh tam-vien)
  (list lg sh ar pe (if (< (abs (- ar (* lg sh))) (* 0.005 lg sh)) "CN" "DG") (cadddr fr)))

;; Tim thong tin SDANHDA (ma vien, tam) theo tam vien gan nhat (sai so 2 mm)
(defun sd:tk-link (cw lk / r)
  (foreach x lk
    (if (and (null r) (< (distance cw (list (cadr x) (caddr x))) 2.0)) (setq r x)))
  r)

(defun sd:tk-key (m tol) (list (fix (+ 0.5 (/ (car m) tol))) (fix (+ 0.5 (/ (cadr m) tol))) (nth 4 m) (nth 7 m)))

;; Hatch trong ban ve: ((min max dien-tich-bbox loai) ...); loai = ten pattern, hatch SOLID thi M<mau> hoac ten layer
(defun sd:tk-hatches (/ ss i e ed bb r ty)
  (if (setq ss (ssget "_X" '((0 . "HATCH"))))
    (progn
      (setq i 0)
      (repeat (sslength ss)
        (setq e (ssname ss i) i (1+ i) ed (entget e))
        (if (setq bb (sd:nb-bbox (list e)))
          (setq ty (if (/= (strcase (cdr (assoc 2 ed))) "SOLID") (cdr (assoc 2 ed))
                     (if (assoc 62 ed) (strcat "M" (itoa (cdr (assoc 62 ed)))) (cdr (assoc 8 ed))))
                r (cons (list (car bb) (cadr bb) (* (- (car (cadr bb)) (car (car bb))) (- (cadr (cadr bb)) (cadr (car bb)))) ty
                              (/= (strcase (cdr (assoc 2 ed))) "SOLID"))
                        r))))))
  r)
;; Loai hatch tai diem c: uu tien hatch co pattern (khong SOLID), roi hatch nho nhat chua diem; nhieu hatch chong nhau chi tinh 1 loai
(defun sd:tk-htype (c hl / best)
  (foreach h hl
    (if (and (>= (car c) (car (car h))) (<= (car c) (car (cadr h))) (>= (cadr c) (cadr (car h))) (<= (cadr c) (cadr (cadr h))))
      (if (or (null best)
              (and (nth 4 h) (not (nth 4 best)))
              (and (eq (nth 4 h) (nth 4 best)) (< (caddr h) (caddr best))))
        (setq best h))))
  (if best (nth 3 best) "-"))

(defun c:SDTKDA (/ ss i e ms tol nm g grp key o rows drows ti dt lk tot ar pe n pt sc fn f lines k lkx tam mm hl seen cell dup)
  (sd:begin)
  (setq sc (sd:sc))
  (if (not (sd:dlg "Thong ke vien da cat (SDTKDA)"
                   (list (list "pv" "Pham vi" 'kw (cond (*SD:TKDPV*) ("Chon"))
                               '(("Chon" . "Quet chon cac polyline vien da") ("Tatca" . "Tat ca polyline kin tren layer SD-GACH / SD-GACH-CAT / SD-GACH-VIEN / SD-GACH-DOC")))
                         (list "tol" "Dung sai gom nhom kich thuoc (mm)" 'real (cond (*SD:TKDTOL*) (2.0)))
                         (list "ht" "Chia theo loai hatch da (pattern / mau)" 'tog t)
                         (list "dd" "Bo vien chong len nhau (trung tam, trung dien tich)" 'tog t)
                         (list "ct" "Them bang chi tiet tung vien (ma, tam da)" 'tog t)
                         (list "csv" "Xuat file CSV canh file ban ve" 'tog t))))
    (exit))
  (setq tol (max 0.5 (sd:v "tol")) *SD:TKDTOL* tol *SD:TKDPV* (sd:v "pv"))
  (setq ss (if (= (sd:v "pv") "Tatca")
             (ssget "_X" '((0 . "LWPOLYLINE") (8 . "SD-GACH,SD-GACH-CAT,SD-GACH-VIEN,SD-GACH-DOC") (-4 . "&") (70 . 1)))
             (progn (princ "\nQuet chon cac polyline kin la vien da: ") (ssget '((0 . "LWPOLYLINE") (-4 . "&") (70 . 1))))))
  (if (null ss)
    (princ "\n[SD] Khong co polyline vien nao.")
    (progn
      (setq lk (vlax-ldata-get "SD" "ANHDA") i 0 dup 0)
      (if (sd:v "ht") (setq hl (sd:tk-hatches)))
      (repeat (sslength ss)
        (setq e (ssname ss i) i (1+ i) ms (sd:tk-meas e)
              ms (append ms (list (sd:tk-link (nth 5 ms) lk) (if (sd:v "ht") (sd:tk-htype (nth 5 ms) hl) "-"))))
        ;; vien chong len nhau: cung tam (sai so ~2 mm), dien tich lech < 0.5% -> chi tinh 1 lan
        (setq cell (list (fix (/ (car (nth 5 ms)) 4.0)) (fix (/ (cadr (nth 5 ms)) 4.0))) o nil)
        (if (sd:v "dd")
          (progn
            (foreach x (cdr (assoc cell seen))
              (if (and (< (distance (car x) (nth 5 ms)) 2.0) (< (abs (- (cadr x) (caddr ms))) (* 0.005 (caddr ms)))) (setq o t)))
            (if o (setq dup (1+ dup))
              (setq seen (if (assoc cell seen)
                           (subst (cons cell (cons (list (nth 5 ms) (caddr ms)) (cdr (assoc cell seen)))) (assoc cell seen) seen)
                           (cons (list cell (list (nth 5 ms) (caddr ms))) seen))))))
        (if (not o)
          (progn
            (setq key (sd:tk-key ms tol))
            (if (setq g (assoc key grp))
              (setq grp (subst (append g (list ms)) g grp))
              (setq grp (cons (list key ms) grp))))))
      (if (> dup 0) (princ (strcat "\n[SD] Bo " (itoa dup) " polyline chong len nhau (trung vi tri va dien tich).")))
      ;; nhom: dien tich 1 vien giam dan -> ma V1, V2...
      (setq grp (sd:sort grp '(lambda (a b) (> (* (car (cadr a)) (cadr (cadr a))) (* (car (cadr b)) (cadr (cadr b)))))) n 0 tot (list 0 0.0 0.0) rows nil)
      (foreach g grp
        (setq n (1+ n) o (cadr g)
              ar (/ (apply '+ (mapcar 'caddr (cdr g))) (length (cdr g))) pe (/ (apply '+ (mapcar 'cadddr (cdr g))) (length (cdr g))))
        (setq rows (cons (list "R" (list (strcat "V" (itoa n))
                                         (strcat (sd:rtos (car o) 0) " x " (sd:rtos (cadr o) 0))
                                         (if (= (nth 4 o) "CN") "Chu nhat" "Vat / da giac")
                                         (nth 7 o)
                                         (itoa (length (cdr g)))
                                         (sd:rtos (/ ar 1e6) 3)
                                         (sd:rtos (/ (* ar (length (cdr g))) 1e6) 2)
                                         (sd:rtos (/ (* pe (length (cdr g))) 1000.0) 1))
                               nil)
                         rows))
        (setq tot (list (+ (car tot) (length (cdr g))) (+ (cadr tot) (* ar (length (cdr g)))) (+ (caddr tot) (* pe (length (cdr g)))))))
      (setq rows (append (reverse rows)
                         (list (list "S" (strcat "TONG CONG: " (itoa (car tot)) " vien, " (itoa (length grp)) " nhom kich thuoc")
                                     (strcat (sd:rtos (/ (cadr tot) 1e6) 2) " m2 - canh mai " (sd:rtos (/ (caddr tot) 1000.0) 1) " m")))))
      (princ (strcat "\n[SD] " (itoa (car tot)) " vien, " (itoa (length grp)) " nhom kich thuoc, tong " (sd:rtos (/ (cadr tot) 1e6) 2) " m2, canh mai "
                     (sd:rtos (/ (caddr tot) 1000.0) 1) " m."))
      (foreach r (vl-remove-if-not '(lambda (x) (= (car x) "R")) rows)
        (princ (strcat "\n  " (nth 0 (cadr r)) "  " (nth 1 (cadr r)) "  x" (nth 4 (cadr r)) "  (" (nth 2 (cadr r)) ", hatch " (nth 3 (cadr r)) ")")))
      ;; chi tiet tung vien
      (if (sd:v "ct")
        (progn
          (setq ti 0)
          (foreach g grp
            (foreach m (cdr g)
              (setq ti (1+ ti) lkx (nth 6 m))
              (setq drows (cons (list "R" (list (if lkx (car lkx) (itoa ti))
                                                (strcat "V" (itoa (1+ (vl-position g grp))))
                                                (strcat (sd:rtos (car m) 0) " x " (sd:rtos (cadr m) 0))
                                                (sd:rtos (/ (caddr m) 1e6) 3)
                                                (if (and lkx (nth 3 lkx)) (itoa (1+ (nth 3 lkx))) "-"))
                                      nil)
                                drows)))))
        )
      (if (setq pt (sd:getpt "\nDiem chen bang thong ke <bo qua>: " nil))
        (progn
          (sd:table2 pt "BANG THONG KE VIEN DA CAT"
                     '(("MA" 14) ("KICH THUOC (mm)" 34) ("HINH DANG" 28) ("LOAI HATCH" 26) ("SL" 12) ("DT 1 VIEN (m2)" 24) ("TONG DT (m2)" 24) ("CANH MAI (m)" 24))
                     rows -1 sc)
          (if (and (sd:v "ct") drows)
            (sd:table2 (sd:p+ pt 0 (* -10.0 sc (+ 4 (length rows))))
                       "CHI TIET TUNG VIEN"
                       '(("VIEN" 18) ("NHOM" 16) ("KICH THUOC (mm)" 34) ("DT (m2)" 22) ("TAM DA" 18))
                       (sd:sort (reverse drows) '(lambda (a b) (sd:fl< (car (cadr a)) (car (cadr b))))) -1 sc))))
      (if (sd:v "csv")
        (if (setq f (sd:open (setq fn (sd:csv-name "_ThongKeDa.csv")) "w"))
          (progn
            (write-line "Ma,Kich thuoc dai,Kich thuoc rong,Hinh dang,Loai hatch,So luong,Dien tich 1 vien m2,Tong dien tich m2,Canh mai m" f)
            (foreach g grp
              (setq o (cadr g) n (length (cdr g))
                    ar (/ (apply '+ (mapcar 'caddr (cdr g))) n) pe (/ (apply '+ (mapcar 'cadddr (cdr g))) n))
              (write-line (sd:join (list (strcat "V" (itoa (1+ (vl-position g grp)))) (sd:rtos (car o) 0) (sd:rtos (cadr o) 0)
                                         (nth 4 o) (nth 7 o) (itoa n) (sd:rtos (/ ar 1e6) 3) (sd:rtos (/ (* ar n) 1e6) 2) (sd:rtos (/ (* pe n) 1000.0) 1)) ",") f))
            (princ (strcat "\n[SD] Da xuat: " (sd:close f))))))))
  (sd:finish))

;;; --------------------------------------------------------------------------
;;;  SDDOCDATK / SDANHDATK - Thong ke da kieu SDGACHTK: bang + du tru dat tam da + CSV
;;;  SDDOCDATK: theo nhom kich thuoc (viec sau SDDOCDA); SDANHDATK: theo tung tam da (sau SDANHDA)
;;;  Doc truc tiep hinh hoc polyline nen khong can du lieu SD_TILE.
;;; --------------------------------------------------------------------------
(defun sd:tkx (che / ss i e ms tol grp key g n sw sh loss ar tot rows lk lkx pt sc fn f slabs sl used ord nsl tarea)
  (setq sc (sd:sc))
  (if (not (sd:dlg (if (= che "ANH") "Thong ke tam da sau SDANHDA (SDANHDATK)" "Thong ke vien da sau SDDOCDA (SDDOCDATK)")
                   (list (list "sw" "Tam da: dai (mm)" 'real (cond (*SD:TKXW*) (2450.0)))
                         (list "sh" "Tam da: rong (mm)" 'real (cond (*SD:TKXH*) (1170.0)))
                         (list "loss" "Hao hut van chuyen / vo (%)" 'real0 (cond (*SD:TKXL*) (3.0)))
                         (list "tol" "Dung sai gom nhom kich thuoc (mm)" 'real (cond (*SD:TKDTOL*) (2.0))))))
    (exit))
  (setq sw (sd:v "sw") sh (sd:v "sh") loss (sd:v "loss") tol (max 0.5 (sd:v "tol"))
        *SD:TKXW* sw *SD:TKXH* sh *SD:TKXL* loss *SD:TKDTOL* tol)
  (princ "\nChon cac polyline vien da <Enter = tat ca tren layer SD-GACH / SD-GACH-CAT / SD-GACH-VIEN / SD-GACH-DOC>: ")
  (setq ss (cond ((ssget '((0 . "LWPOLYLINE") (-4 . "&") (70 . 1))))
                 ((ssget "_X" '((0 . "LWPOLYLINE") (8 . "SD-GACH,SD-GACH-CAT,SD-GACH-VIEN,SD-GACH-DOC") (-4 . "&") (70 . 1))))))
  (if (null ss)
    (princ "\n[SD] Khong co polyline vien nao.")
    (progn
      (setq lk (vlax-ldata-get "SD" "ANHDA") i 0 tot 0.0)
      (repeat (sslength ss)
        (setq e (ssname ss i) i (1+ i) ms (sd:tk-meas e)
              ms (append ms (list (sd:tk-link (nth 5 ms) lk)))
              tot (+ tot (caddr ms)))
        (setq key (if (= che "ANH") (list (cond ((and (nth 6 ms) (nth 3 (nth 6 ms))) (nth 3 (nth 6 ms))) (-1))) (sd:tk-key ms tol)))
        (if (setq g (assoc key grp))
          (setq grp (subst (append g (list ms)) g grp))
          (setq grp (cons (list key ms) grp))))
      (setq n 0)
      (if (= che "ANH")
        (progn
          (setq grp (sd:sort grp '(lambda (a b) (< (car (car a)) (car (car b))))) used 0)
          (foreach g grp
            (setq ar (apply '+ (mapcar 'caddr (cdr g))))
            (if (>= (car (car g)) 0) (setq used (1+ used)))
            (setq rows (cons (list "R" (list (if (>= (car (car g)) 0) (itoa (1+ (car (car g)))) "chua gan")
                                             (itoa (length (cdr g)))
                                             (sd:rtos (/ ar 1e6) 2)
                                             (if (>= (car (car g)) 0) (strcat (sd:rtos (* 100.0 (- 1.0 (/ ar (* sw sh)))) 1) " %") "-"))
                                   nil)
                             rows)))
          (setq nsl used ord (fix (+ (* nsl (+ 1.0 (/ loss 100.0))) 0.999999))
                rows (append (reverse rows)
                             (list (list "S" (strcat "TONG: " (itoa (sslength ss)) " vien, " (itoa nsl) " tam da dung") (strcat (sd:rtos (/ tot 1e6) 2) " m2"))
                                   (list "W" (strcat "   Dat hang tam " (sd:num sw) "x" (sd:num sh) ": " (itoa nsl) " + hao hut " (sd:num loss) "% = " (itoa ord) " tam"))))))
        (progn
          (setq grp (sd:sort grp '(lambda (a b) (> (* (car (cadr a)) (cadr (cadr a))) (* (car (cadr b)) (cadr (cadr b)))))))
          (foreach g grp
            (setq n (1+ n) e (cadr g) ar (/ (apply '+ (mapcar 'caddr (cdr g))) (length (cdr g))))
            (setq rows (cons (list "R" (list (strcat "V" (itoa n)) (strcat (sd:rtos (car e) 0) " x " (sd:rtos (cadr e) 0))
                                             (itoa (length (cdr g))) (sd:rtos (/ ar 1e6) 3)
                                             (sd:rtos (/ (* ar (length (cdr g))) 1e6) 2))
                                   nil)
                             rows)))
          (setq nsl (fix (+ (/ tot (* sw sh)) 0.999999)) ord (fix (+ (* (/ tot (* sw sh)) (+ 1.0 (/ loss 100.0))) 0.999999))
                rows (append (reverse rows)
                             (list (list "S" (strcat "TONG: " (itoa (sslength ss)) " vien, " (itoa (length grp)) " nhom") (strcat (sd:rtos (/ tot 1e6) 2) " m2"))
                                   (list "W" (strcat "   Dat hang tam " (sd:num sw) "x" (sd:num sh) ": " (sd:rtos (/ tot (* sw sh)) 2) " tam + hao hut " (sd:num loss) "% = " (itoa ord) " tam (uoc tinh theo dien tich, chua tinh xep cat)")))))))
      (princ (strcat "\n[SD] " (itoa (sslength ss)) " vien, " (sd:rtos (/ tot 1e6) 2) " m2 -> dat " (itoa ord) " tam "
                     (sd:num sw) "x" (sd:num sh) " (da gom hao hut " (sd:num loss) "%)."))
      (if (setq pt (sd:getpt "\nDiem chen bang thong ke <bo qua>: " nil))
        (if (= che "ANH")
          (sd:table2 pt "BANG THONG KE TAM DA" '(("TAM DA SO" 24) ("SO VIEN" 18) ("DT VIEN (m2)" 24) ("HAO HUT TAM" 26)) rows -1 sc)
          (sd:table2 pt "BANG THONG KE VIEN DA" '(("MA" 14) ("KICH THUOC (mm)" 34) ("SL" 12) ("DT 1 VIEN (m2)" 24) ("TONG DT (m2)" 24)) rows -1 sc)))
      (if (setq f (sd:open (setq fn (sd:csv-name (if (= che "ANH") "_ThongKeTamDa.csv" "_ThongKeVienDa.csv"))) "w"))
        (progn
          (write-line (if (= che "ANH") "Tam da so;So vien;DT vien m2;Hao hut tam %" "Ma;Dai;Rong;SL;DT 1 vien m2;Tong DT m2") f)
          (foreach r (vl-remove-if-not '(lambda (x) (= (car x) "R")) rows) (write-line (sd:join (cadr r) ";") f))
          (write-line (strcat "Dat hang;" (itoa ord) ";tam " (sd:num sw) "x" (sd:num sh)) f)
          (princ (strcat "\n[SD] Da xuat: " (sd:close f)))))))
  (sd:finish))
(defun c:SDDOCDATK () (sd:begin) (sd:tkx "DOC"))
(defun c:SDANHDATK () (sd:begin) (sd:tkx "ANH"))

;;; --------------------------------------------------------------------------
;;;  SDNHAPBANG - Nhap bang cau kien (CSV / Excel) -> ve khai trien hang loat
;;;  Moi dong 1 cau kien; cot = khoa truong trong hop thoai cua lenh ve (name, b, h, sp, top...).
;;;  Lenh ve chay o che do lo: sd:dlg lay gia tri tu dong bang (o trong = mac dinh), sd:getpt lay diem chen;
;;;  ve xong, khung bao cac doi tuong moi duoc doi vao luoi (moi hang toi da n cau kien, cach deu).
;;; --------------------------------------------------------------------------
(setq *SD:NBTYPES*
  '(("DAMDUNG" c:SDDAMDUNG "Mat dung thep dam lien tuc (SDDAMDUNG)")
    ("COTTHEP" c:SDCOTTHEP "Khai trien thep cot 1 tang (SDCOTTHEP)")
    ("MONG" c:SDMONGTHEP "Khai trien thep mong don (SDMONGTHEP)")
    ("MONGBANG" c:SDMONGBANG "Khai trien thep mong bang (SDMONGBANG)")
    ("DAICOC" c:SDDAICOC "Khai trien thep dai coc (SDDAICOC)")
    ("SAN" c:SDSANTHEP "Khai trien thep o san (SDSANTHEP)")
    ("THANG" c:SDTHANGTHEP "Khai trien thep cau thang (SDTHANGTHEP)")
    ("DAM" c:SDDAM "Mat cat dam (SDDAM)")
    ("COT" c:SDCOT "Mat cat cot (SDCOT)")))

;; Loai cau kien theo o dau dong: ten ngan (DAMDUNG) hoac ten lenh (SDDAMDUNG)
(defun sd:nb-type (s)
  (setq s (strcase s))
  (cond ((assoc s *SD:NBTYPES*))
        ((vl-some '(lambda (x) (if (= (strcat "C:" s) (strcase (vl-symbol-name (cadr x)))) x)) *SD:NBTYPES*))))

(defun sd:nb-warn (f s) (setq *SD:NBWARN* (cons (strcat (car f) "=" s " (sai, dung mac dinh)") *SD:NBWARN*)))

;; Gia tri 1 truong tu chuoi trong bang (s nil / "" = mac dinh)
(defun sd:nb-val (f s / tp d r)
  (setq tp (nth 2 f) d (nth 3 f))
  (cond
    ((= tp 'note) nil)
    ((or (null s) (= s "")) (if (= tp 'bar) (sd:parse-bar d) d))
    ((member tp '(real real0))
     (cond ((distof (vl-string-translate "," "." s) 2)) (t (sd:nb-warn f s) d)))
    ((member tp '(int int0))
     (if (setq r (distof (vl-string-translate "," "." s) 2)) (fix (+ r (if (< r 0) -0.5 0.5))) (progn (sd:nb-warn f s) d)))
    ((= tp 'tog) (if (member (strcase s) '("1" "CO" "C" "X" "Y" "YES" "TRUE" "T")) t nil))
    ((= tp 'kw)
     (setq r (vl-some '(lambda (c) (if (or (= (strcase (sd:kv c)) (strcase s)) (= (strcase (sd:kl c)) (strcase s))) (sd:kv c)))
                      (nth 4 f)))
     (if r r (progn (sd:nb-warn f s) d)))
    ((= tp 'bar) (cond ((sd:parse-bar s)) (t (sd:nb-warn f s) (sd:parse-bar d))))
    ((= s "-") "")
    (t s)))

;; Danh sach truong + cap (KHOA . chuoi) cua 1 dong -> gia tri nhu hop thoai tra ve (*SD:FV*)
(defun sd:nb-fv (fields ov / r x)
  (foreach f fields
    (if (car f)
      (setq x (assoc (strcase (car f)) ov) ov (vl-remove x ov)
            r (cons (cons (car f) (sd:nb-val f (cdr x))) r))))
  (foreach x ov
    (if (and (car x) (/= (cdr x) "")) (setq *SD:NBWARN* (cons (strcat "cot " (car x) " khong co trong lenh nay (bo qua)") *SD:NBWARN*))))
  (reverse r))

;; Tach 1 dong CSV (co ngoac kep "a;b", "" = dau ngoac kep)
(defun sd:csv-split (s sep / i c q cur r)
  (setq i 1 cur "")
  (while (<= i (strlen s))
    (setq c (substr s i 1))
    (cond
      ((and q (= c "\"") (= (substr s (1+ i) 1) "\"")) (setq cur (strcat cur "\"") i (1+ i)))
      ((= c "\"") (setq q (not q)))
      ((and (not q) (= c sep)) (setq r (cons (vl-string-trim " \t" cur) r) cur ""))
      (t (setq cur (strcat cur c))))
    (setq i (1+ i)))
  (reverse (cons (vl-string-trim " \t" cur) r)))

;; Doc file bang -> ((so-dong LOAI ((KHOA . chuoi) ...)) ...). Dong "Loai;khoa1;khoa2..." = tieu de cho cac dong sau;
;; dong / o dau bat dau "#" = ghi chu; "sep=;" (Excel) chon dau phan cach, khong co thi tu nhan ; / tab / ,
(defun sd:nb-read (fn / f ln sep hdr cells rows n)
  (if (setq f (sd:open fn "r"))
    (progn
      (setq n 0)
      (while (setq ln (read-line f))
        (setq n (1+ n) ln (vl-string-trim " \t\r" ln))
        (if (and (= n 1) (>= (strlen ln) 3) (= (ascii ln) 239)) (setq ln (substr ln 4))) ; BOM UTF-8
        (cond
          ((= ln ""))
          ((wcmatch (strcase ln) "SEP=*") (setq sep (substr ln 5 1)))
          (t
           (if (null sep) (setq sep (cond ((vl-string-search ";" ln) ";") ((vl-string-search "\t" ln) "\t") (","))))
           (setq cells (sd:csv-split ln sep))
           (cond
             ((or (= (car cells) "") (= (substr (car cells) 1 1) "#")))
             ((= (strcase (car cells)) "LOAI") (setq hdr (mapcar 'strcase (cdr cells))))
             ((null hdr) (princ (strcat "\n[SD] Dong " (itoa n) ": chua co dong tieu de (Loai;name;...) phia tren, bo qua.")))
             (t (setq rows (cons (list n (strcase (car cells)) (vl-remove-if '(lambda (x) (= (car x) "")) (mapcar 'cons hdr (cdr cells))))
                                 rows)))))))
      (sd:close f)
      (reverse rows))))

;; Cac doi tuong do hoa tao sau e0 (bo VERTEX / ATTRIB / SEQEND - di theo doi tuong chu)
(defun sd:nb-new (e0 / e r ed)
  (setq e (if e0 (entnext e0) (entnext)))
  (while e
    (if (and (setq ed (entget e)) (not (member (cdr (assoc 0 ed)) '("VERTEX" "ATTRIB" "SEQEND"))))
      (setq r (cons e r)))
    (setq e (entnext e)))
  r)

;; Khung bao ((x0 y0) (x1 y1)) cua danh sach doi tuong
(defun sd:nb-bbox (ents / o a b mn mx x0 y0 x1 y1)
  (foreach e ents
    (setq o (vlax-ename->vla-object e))
    (if (not (vl-catch-all-error-p (vl-catch-all-apply 'vla-GetBoundingBox (list o 'a 'b))))
      (setq mn (vlax-safearray->list a) mx (vlax-safearray->list b)
            x0 (if x0 (min x0 (car mn)) (car mn)) y0 (if y0 (min y0 (cadr mn)) (cadr mn))
            x1 (if x1 (max x1 (car mx)) (car mx)) y1 (if y1 (max y1 (cadr mx)) (cadr mx)))))
  (if x0 (list (list x0 y0) (list x1 y1))))

(defun sd:nb-move (ents dx dy / p0 p1)
  (setq p0 (vlax-3d-point '(0.0 0.0 0.0)) p1 (vlax-3d-point (list dx dy 0.0)))
  (foreach e ents (vl-catch-all-apply 'vla-Move (list (vlax-ename->vla-object e) p0 p1))))

;; Danh sach truong hop thoai cua 1 lenh ve (chay lenh o che do SCHEMA, lenh dung ngay sau hop thoai)
(defun sd:nb-schema (fn / r)
  (setq *SD:BATCH* 'SCHEMA *SD:SCHEMA* nil)
  (setq r (vl-catch-all-apply fn nil))
  (if (vl-catch-all-error-p r) (sd:finish))
  (setq *SD:BATCH* nil)
  *SD:SCHEMA*)

;; O CSV: gia tri / nhan an toan voi dau ;
(defun sd:nb-cell (s)
  (setq s (vl-string-translate "\"" "'" (cond (s) (""))))
  (if (vl-string-search ";" s) (strcat "\"" s "\"") s))

(defun sd:nb-fstr (f / tp d)
  (setq tp (nth 2 f) d (nth 3 f))
  (cond ((member tp '(real real0)) (sd:num d))
        ((member tp '(int int0)) (if (= (car f) "mk") "" (itoa d))) ; so hieu thep: de trong -> tu noi tiep
        ((= tp 'tog) (if d "1" "0"))
        ((= (type d) 'STR) d)
        ("")))

(defun sd:nb-label (f)
  (strcat (nth 1 f)
          (cond ((= (nth 2 f) 'kw) (strcat " [" (sd:join (mapcar 'sd:kv (nth 4 f)) "/") "]"))
                ((= (nth 2 f) 'tog) " [1/0]")
                (""))))

;; Ghi file mau: moi loai 1 khoi (ghi chu, tieu de, nhan tieng Viet, 1 dong vi du = gia tri mac dinh)
(defun sd:nb-template (fn / f sch fl)
  (if (setq f (sd:open fn "w"))
    (progn
      (write-line "sep=;" f)
      (write-line "# FILE NHAP CAU KIEN CHO SDNHAPBANG - moi khoi: dong tieu de (Loai;khoa...), dong nhan (#), cac dong cau kien" f)
      (write-line "# O trong = gia tri mac dinh; cot chu muon de trong ghi dau -; Co/Khong ghi 1/0; lua chon ghi dung chu trong [ ]" f)
      (write-line "# Xoa cac khoi khong dung; them dong cau kien ngay duoi dong nhan cua khoi. mk trong = so hieu thep tu noi tiep" f)
      (foreach ty *SD:NBTYPES*
        (if (setq sch (sd:nb-schema (cadr ty)))
          (progn
            (setq fl (vl-remove-if '(lambda (x) (or (null (car x)) (= (nth 2 x) 'note))) (cadr sch)))
            (write-line "#" f)
            (write-line (strcat "# " (car ty) " - " (caddr ty)) f)
            (write-line (sd:join (cons "Loai" (mapcar 'car fl)) ";") f)
            (write-line (sd:join (cons "#" (mapcar '(lambda (x) (sd:nb-cell (sd:nb-label x))) fl)) ";") f)
            (write-line (sd:join (cons (car ty) (mapcar '(lambda (x) (sd:nb-cell (sd:nb-fstr x))) fl)) ";") f))))
      (sd:close f))))

(defun c:SDNHAPBANG (/ fn rows gap per hang x0 cx top rowh ncol lastty ty e0 res msg ents bb nok bad stop pt row nm w hgt)
  (if (sd:dlg "Nhap bang cau kien -> ve khai trien hang loat (SDNHAPBANG)"
              (list (list "che" "Che do" 'kw (cond (*SD:NBCHE*) ("Ve"))
                          '(("Ve" . "Ve hang loat tu file CSV (luu tu Excel)") ("Mau" . "Tao file mau CSV (mo bang Excel de dien)")))
                    (list "gap" "Khoang cach giua cac cau kien (mm)" 'real (cond (*SD:NBGAP*) (2000.0)) nil '("che" "Ve"))
                    (list "per" "So cau kien toi da moi hang" 'int (cond (*SD:NBPER*) (4)) nil '("che" "Ve"))
                    (list "hang" "Moi loai cau kien bat dau hang moi" 'tog t nil '("che" "Ve"))))
    (progn
      (setq *SD:NBCHE* (sd:v "che") gap (sd:v "gap") per (max 1 (sd:v "per")) hang (sd:v "hang") *SD:NBGAP* gap *SD:NBPER* per)
      (cond
        ((= *SD:NBCHE* "Mau")
         (if (setq fn (sd:nb-template (sd:csv-name "_MauNhapBang.csv")))
           (progn
             (princ (strcat "\n[SD] Da tao file mau: " fn
                            "\n     Mo bang Excel, dien cau kien (moi dong 1 cau kien), luu dang CSV roi chay SDNHAPBANG > Ve."))
             (vl-catch-all-apply 'startapp (list "explorer" (strcat "\"" fn "\""))))
           (princ "\n[SD] Khong ghi duoc file mau.")))
        ((null (setq fn (getfiled "Chon file bang cau kien (CSV)" (getvar "DWGPREFIX") "csv" 0))))
        ((null (setq rows (sd:nb-read fn))) (princ "\n[SD] File khong co dong cau kien nao."))
        ((null (setq pt (sd:getpt (strcat "\nGoc tren - trai vung ve " (itoa (length rows)) " cau kien: ") nil))))
        (t
         (setq x0 (car pt) cx x0 top (cadr pt) rowh 0.0 ncol 0 nok 0 *SD:NBRUN* t)
         (foreach row rows
           (setq nm (cond ((cdr (assoc "NAME" (caddr row)))) ("")) ty (sd:nb-type (cadr row)))
           (cond
             (stop)
             ((null ty)
              (setq bad (cons (strcat "dong " (itoa (car row)) ": loai " (cadr row) " khong ho tro") bad)))
             (t
              (if (and (> ncol 0) (or (>= ncol per) (and hang (/= (car ty) lastty))))
                (setq top (- top rowh gap) cx x0 rowh 0.0 ncol 0))
              (setq e0 (entlast) *SD:NBWARN* nil *SD:BATCH* (caddr row) *SD:BPT* (list cx top 0.0)
                    res (vl-catch-all-apply (cadr ty) nil) *SD:BATCH* nil *SD:BPT* nil msg nil)
              (if (vl-catch-all-error-p res)
                (progn
                  (setq msg (vl-catch-all-error-message res))
                  (if (wcmatch (strcase msg t) "*cancel*,*break*") (setq stop t))
                  (sd:finish)))
              (foreach x (reverse *SD:NBWARN*) (princ (strcat "\n[SD]   dong " (itoa (car row)) " " nm ": " x)))
              (if (and (setq ents (sd:nb-new e0)) (setq bb (sd:nb-bbox ents)))
                (progn
                  (setq w (- (car (cadr bb)) (car (car bb))) hgt (- (cadr (cadr bb)) (cadr (car bb))))
                  (sd:nb-move ents (- cx (car (car bb))) (- top (cadr (cadr bb))))
                  (setq cx (+ cx w gap) rowh (max rowh hgt) ncol (1+ ncol) nok (1+ nok) lastty (car ty))
                  (if (and msg (not stop))
                    (setq bad (cons (strcat "dong " (itoa (car row)) " " (car ty) " " nm ": ve chua het, loi " msg) bad))))
                (setq bad (cons (strcat "dong " (itoa (car row)) " " (car ty) " " nm ": khong ve duoc"
                                        (if (and msg (not stop)) (strcat " (" msg ")") ""))
                                bad))))))
         (setq *SD:NBRUN* nil *SD:BATCH* nil *SD:BPT* nil)
         (if (vlax-ldata-get "SD" "TKAUTO") (vl-catch-all-apply 'sd:tk-refresh '(nil)))
         (princ (strcat "\n[SD] Da ve " (itoa nok) " / " (itoa (length rows)) " cau kien tu " (vl-filename-base fn)
                        (if stop " (dung giua chung theo yeu cau)" "") "."))
         (foreach x (reverse bad) (princ (strcat "\n[SD]   Loi " x)))
         (if (> nok 0) (princ "\n[SD] Tiep theo: SDTKTHEP (bang thong ke thep), SDKL (khoi luong), SDTAOLAYOUT (dan trang)."))))))
  (setq *SD:BATCH* nil *SD:BPT* nil *SD:NBRUN* nil)
  (princ))

;;; --------------------------------------------------------------------------
;;;  SDDOCDA - Doc mat bang op lat da: dung lai cac o kin tu cac net roi (LINE / polyline mo hoac kin)
;;;  -> bang viec (CSV, cung dinh dang SDNHAPBANG: Loai;khoa...) de soat / bo sung o thieu -> ve polyline kin -> SDANHDA
;;;  Dung o kin = tach net tai giao diem va cho T, noi dau mut ho nho (dung sai), tim cac mat cua do thi phang.
;;; --------------------------------------------------------------------------
;; Bang bam (ky hieu): luu cac danh sach tam bang symbol, don bang sd:dm-clear
(setq *SD:DMKEYS* nil)
(defun sd:dm-hset (k v) (setq *SD:DMKEYS* (cons k *SD:DMKEYS*)) (set (read (strcat "SDDM_" k)) v))
(defun sd:dm-hget (k) (eval (read (strcat "SDDM_" k))))
(defun sd:dm-clear () (foreach k *SD:DMKEYS* (set (read (strcat "SDDM_" k)) nil)) (setq *SD:DMKEYS* nil))

;; Cac doan thang cua LINE / LWPOLYLINE (cung duoc chia nho nhu polyline): ((p q) ...)
(defun sd:dm-segs (ents / e ed ty pts cl a b r cv)
  (foreach e ents
    (setq ed (entget e) ty (cdr (assoc 0 ed)))
    (cond
      ((= ty "LINE") (setq r (cons (list (sd:2d (cdr (assoc 10 ed))) (sd:2d (cdr (assoc 11 ed)))) r)))
      ((= ty "LWPOLYLINE")
       (setq pts (sd:curve-pts e) cl (= 1 (logand 1 (cdr (assoc 70 ed)))))
       (if cl (setq pts (append pts (list (car pts)))))
       (setq a (car pts))
       (foreach b (cdr pts) (setq r (cons (list a b) r) a b)))
      ((member ty '("ARC" "CIRCLE" "SPLINE" "ELLIPSE"))
       (setq cv (sd:dm-curve e ty ed) pts (car cv) cl (cadr cv))
       (if cl (setq pts (append pts (list (car pts)))))
       (setq a (car pts))
       (foreach b (cdr pts) (setq r (cons (list a b) r) a b)))))
  (vl-remove-if '(lambda (s) (< (distance (car s) (cadr s)) 1e-6)) (reverse r)))

;; Hinh chieu diem p len doan a-b: (t . khoang-cach)
(defun sd:dm-proj (p a b / dx dy l2)
  (setq dx (- (car b) (car a)) dy (- (cadr b) (cadr a)) l2 (+ (* dx dx) (* dy dy)))
  (cons (/ (+ (* (- (car p) (car a)) dx) (* (- (cadr p) (cadr a)) dy)) l2)
        (/ (abs (- (* dx (- (cadr p) (cadr a))) (* dy (- (car p) (car a))))) (sqrt l2))))

;; Cac diem cat / cham cua moi doan: (so-doan x y uu-tien). Tu dong "snap" nhu OSNAP:
;;   uu-tien 3 = GIAO DIEM (that, hoac giao diem keo dai khi hai net ho / vuot nhau <= tol) -> dinh chinh xac
;;   uu-tien 2 = DAU MUT cua net
;;   uu-tien 1 = hinh chieu dau mut len doan khac (chi khi khong tinh duoc giao diem, vd 2 net gan song song)
(defun sd:dm-snap-add (pts a b q tol / p)
  ;; q = dau mut cua doan b nam gan doan a: lay giao diem (keo dai) cua 2 duong thang neu no cach q <= tol
  (if (and (setq p (inters (cadr a) (caddr a) (cadr b) (caddr b) nil))
           (<= (distance p q) tol))
    (cons (list (car a) (car p) (cadr p) 3) (cons (list (car b) (car p) (cadr p) 3) pts))
    (cons (list (car a) (car q) (cadr q) 1) pts)))

(defun sd:dm-points (recs tol / pts rest a b p q r qa qb)
  (foreach a recs
    (setq pts (cons (list (car a) (car (cadr a)) (cadr (cadr a)) 2) pts)
          pts (cons (list (car a) (car (caddr a)) (cadr (caddr a)) 2) pts)))
  (setq rest recs)
  (while rest
    (setq a (car rest) rest (cdr rest))
    (foreach b rest
      (if (and (<= (nth 3 b) (+ (nth 5 a) tol)) (>= (nth 5 b) (- (nth 3 a) tol))
               (<= (nth 4 b) (+ (nth 6 a) tol)) (>= (nth 6 b) (- (nth 4 a) tol)))
        (progn
          ;; giao diem that cua 2 doan
          (if (setq p (inters (cadr a) (caddr a) (cadr b) (caddr b) t))
            (setq pts (cons (list (car a) (car p) (cadr p) 3) (cons (list (car b) (car p) (cadr p) 3) pts))))
          ;; dau mut doan nay cham / gan giua doan kia (chu T): snap vao giao diem keo dai
          (foreach q (list (cadr b) (caddr b))
            (setq r (sd:dm-proj q (cadr a) (caddr a)))
            (if (and (> (car r) 0.0) (< (car r) 1.0) (<= (cdr r) tol))
              (setq pts (sd:dm-snap-add pts a b q tol))))
          (foreach q (list (cadr a) (caddr a))
            (setq r (sd:dm-proj q (cadr b) (caddr b)))
            (if (and (> (car r) 0.0) (< (car r) 1.0) (<= (cdr r) tol))
              (setq pts (sd:dm-snap-add pts b a q tol))))
          ;; 2 dau mut gan nhau nhung khong chua nhau (goc ho hoac vuot nhe): snap vao giao diem keo dai cua 2 duong
          (foreach qa (list (cadr a) (caddr a))
            (foreach qb (list (cadr b) (caddr b))
              (if (and (> (distance qa qb) 1e-6) (<= (distance qa qb) tol)
                       (setq p (inters (cadr a) (caddr a) (cadr b) (caddr b) nil))
                       (<= (distance p qa) tol) (<= (distance p qb) tol))
                (setq pts (cons (list (car a) (car p) (cadr p) 3) (cons (list (car b) (car p) (cadr p) 3) pts))))))))))
  pts)

;; Gop cac diem trong dung sai thanh nut (quet theo x): tra ve (so-nut (so-doan nut) ...) va luu toa do nut vao bang "P<nut>"
;; Toa do nut = giao diem (neu co) > dau mut > hinh chieu; nhieu diem cung uu-tien thi lay trung binh (khong lay diem dau tien theo x)
(defun sd:dm-cluster (pts tol / win nid x hit res k lst bp sx sy n)
  (setq nid 0)
  (foreach pt (sd:sort pts '(lambda (a b) (< (cadr a) (cadr b))))
    (setq x (cadr pt)
          win (vl-remove-if '(lambda (n) (< (cadr n) (- x tol))) win)
          hit (vl-some '(lambda (n) (if (<= (distance (cdr n) (cdr pt)) tol) (car n))) win))
    (if (null hit)
      (progn (setq hit nid nid (1+ nid)
                   win (cons (list hit (cadr pt) (caddr pt)) win))
             (sd:dm-hset (strcat "P" (itoa hit)) (list (cadr pt) (caddr pt)))
             (sd:dm-hset (strcat "M" (itoa hit)) nil)))
    ;; ghi nho cac diem thanh vien cua nut (set truc tiep, khong dang ky khoa lai)
    (set (read (strcat "SDDM_M" (itoa hit)))
         (cons (list (cadr pt) (caddr pt) (nth 3 pt)) (eval (read (strcat "SDDM_M" (itoa hit))))))
    (setq res (cons (list (car pt) hit) res)))
  ;; chot toa do tung nut theo thu tu uu-tien snap
  (setq k 0)
  (while (< k nid)
    (setq lst (eval (read (strcat "SDDM_M" (itoa k)))) bp 0 sx 0.0 sy 0.0 n 0)
    (foreach m lst (if (> (nth 2 m) bp) (setq bp (nth 2 m))))
    (foreach m lst
      (if (= (nth 2 m) bp) (setq sx (+ sx (car m)) sy (+ sy (cadr m)) n (1+ n))))
    (if (> n 0) (set (read (strcat "SDDM_P" (itoa k))) (list (/ sx n) (/ sy n))))
    (set (read (strcat "SDDM_M" (itoa k))) nil)
    (setq k (1+ k)))
  (cons nid res))

;; Canh (nut-nho . nut-lon), khong trung: noi cac nut lien tiep doc moi doan theo thu tu tham so
(defun sd:dm-edges (asg / rows sg pp pr r el out e)
  (foreach x asg
    (setq sg (sd:dm-hget (strcat "S" (itoa (car x)))) pp (sd:dm-hget (strcat "P" (itoa (cadr x)))))
    (setq rows (cons (list (car x) (car (sd:dm-proj pp (car sg) (cadr sg))) (cadr x)) rows)))
  (setq rows (sd:sort rows '(lambda (a b) (if (= (car a) (car b)) (< (cadr a) (cadr b)) (< (car a) (car b)))))
        pr (car rows))
  (foreach r (cdr rows)
    (if (and (= (car r) (car pr)) (/= (caddr r) (caddr pr)))
      (setq el (cons (if (< (caddr pr) (caddr r)) (cons (caddr pr) (caddr r)) (cons (caddr r) (caddr pr))) el)))
    (setq pr r))
  (setq el (sd:sort el '(lambda (a b) (if (= (car a) (car b)) (< (cdr a) (cdr b)) (< (car a) (car b))))) pr nil)
  (foreach e el
    (if (not (equal e pr)) (setq out (cons e out)))
    (setq pr e))
  out)

;; Danh sach ke "A<nut>" tu canh; bo nut cut (canh treo) lap di lap lai; sap ke theo goc nguoc chieu kim dong ho
(defun sd:dm-adj (edges n / e k v nd)
  (foreach e edges
    (foreach k (list (cons (car e) (cdr e)) (cons (cdr e) (car e)))
      (sd:dm-hset (strcat "A" (itoa (car k))) (cons (cdr k) (sd:dm-hget (strcat "A" (itoa (car k))))))))
  (setq nd 0 e nil)
  (while (< nd n)
    (if (<= (length (sd:dm-hget (strcat "A" (itoa nd)))) 1) (setq e (cons nd e)))
    (setq nd (1+ nd)))
  (while e
    (setq k (car e) e (cdr e))
    (foreach v (sd:dm-hget (strcat "A" (itoa k)))
      (sd:dm-hset (strcat "A" (itoa v)) (vl-remove k (sd:dm-hget (strcat "A" (itoa v)))))
      (if (= (length (sd:dm-hget (strcat "A" (itoa v)))) 1) (setq e (cons v e))))
    (sd:dm-hset (strcat "A" (itoa k)) nil))
  (setq nd 0)
  (while (< nd n)
    (setq k (strcat "A" (itoa nd)))
    (if (sd:dm-hget k)
      (sd:dm-hset k (mapcar 'cdr
                      (sd:sort (mapcar '(lambda (v) (cons (angle (sd:dm-hget (strcat "P" (itoa nd))) (sd:dm-hget (strcat "P" (itoa v)))) v))
                                       (sd:dm-hget k))
                               '(lambda (a b) (< (car a) (car b)))))))
    (setq nd (1+ nd))))

;; Cac mat (vong kin) cua do thi: danh sach vong nut, moi vong di nguoc chieu kim dong ho (mat trong) hoac cung chieu (vong ngoai)
(defun sd:dm-walk (n / res u v1 cyc cur nxt nb idx cnt nd)
  (setq nd 0)
  (while (< nd n)
    (setq u nd)
    (foreach v1 (sd:dm-hget (strcat "A" (itoa u)))
      (if (not (sd:dm-hget (strcat "V" (itoa u) "_" (itoa v1))))
        (progn
          (setq cyc nil cur u nxt v1 cnt 0)
          (while (and (not (sd:dm-hget (strcat "V" (itoa cur) "_" (itoa nxt)))) (< cnt 200000))
            (sd:dm-hset (strcat "V" (itoa cur) "_" (itoa nxt)) T)
            (setq cyc (cons cur cyc) cnt (1+ cnt)
                  nb (sd:dm-hget (strcat "A" (itoa nxt))) idx (vl-position cur nb)
                  cur nxt nxt (nth (rem (+ idx (length nb) -1) (length nb)) nb)))
          (setq res (cons (reverse cyc) res)))))
    (setq nd (1+ nd)))
  res)

(defun sd:dm-sarea (pts / s a b)
  (setq s 0.0 a (last pts))
  (foreach b pts (setq s (+ s (- (* (car a) (cadr b)) (* (car b) (cadr a)))) a b))
  (/ s 2.0))

;; Bo dinh thang hang (T giua canh, dinh thua): dinh lech <= 0.2 mm luon bo; dinh lech toi dung sai tol chi bo khi hai canh ke deu dai (T bi lech do noi ho),
;; de khong mat dinh cua cung nho
(defun sd:dm-simp (pts tol) (sd:dm-simp2 pts tol nil))

;; keeps = danh sach song song voi pts: T = dinh la nut giao (>= 3 canh) phai giu de cac polyline ke nhau trung dinh
(defun sd:dm-simp2 (pts tol keeps / n i a b c r dv)
  (setq n (length pts) i 0)
  (foreach b pts
    (setq a (nth (rem (+ i n -1) n) pts) c (nth (rem (1+ i) n) pts)
          dv (/ (abs (- (* (- (car c) (car a)) (- (cadr b) (cadr a))) (* (- (cadr c) (cadr a)) (- (car b) (car a)))))
                (max 1e-9 (distance a c))))
    (if (or (> dv tol) (nth i keeps)
            (and (> dv 0.2) (or (< (distance a b) 150.0) (< (distance b c) 150.0))))
      (setq r (cons b r)))
    (setq i (1+ i)))
  (reverse r))

;; Bo cac khung bao (khung phong, vien chua noi) la mat rat lon chua tu 3 o khac tro len; o co 1 - 2 cot ben trong van giu
(defun sd:dm-drop (polys / ars med big cnt res)
  (setq *SD:DMDROP* 0)
  (if (> (length polys) 3)
    (progn
      (setq ars (sd:sort (mapcar 'sd:dm-sarea polys) '<) med (nth (/ (length ars) 2) ars))
      (foreach p polys
        (setq big (> (sd:dm-sarea p) (* 2.5 med)) cnt 0)
        (if big
          (foreach q polys
            (if (and (< (sd:dm-sarea q) (sd:dm-sarea p)) (sd:inpoly (sd:centroid q) p)) (setq cnt (1+ cnt)))))
        (if (and big (>= cnt 3))
          (setq *SD:DMDROP* (1+ *SD:DMDROP*))
          (setq res (cons p res))))
      (reverse res))
    polys))

;; Cac mat trong (da giac, nguoc chieu kim dong ho, dien tich > amin mm2) tu cac doan thang: ((p1 p2 ...) ...)
(defun sd:dm-faces (segs tol amin / recs i s n pts cl asg edges polys cyc p)
  (sd:dm-clear)
  (setq i 0)
  (foreach s segs
    (sd:dm-hset (strcat "S" (itoa i)) s)
    (setq recs (cons (list i (car s) (cadr s) (min (car (car s)) (car (cadr s))) (min (cadr (car s)) (cadr (cadr s)))
                           (max (car (car s)) (car (cadr s))) (max (cadr (car s)) (cadr (cadr s))))
                     recs)
          i (1+ i)))
  (setq recs (reverse recs)
        pts (sd:dm-points recs tol)
        cl (sd:dm-cluster pts tol)
        n (car cl) asg (cdr cl)
        edges (sd:dm-edges asg))
  (sd:dm-adj edges n)
  (foreach cyc (sd:dm-walk n)
    (if (> (length cyc) 2)
      (progn
        (setq p (sd:dm-simp2 (mapcar '(lambda (k) (sd:dm-hget (strcat "P" (itoa k)))) cyc) tol
                             (mapcar '(lambda (k) (> (length (sd:dm-hget (strcat "A" (itoa k)))) 2)) cyc)))
        (if (and (> (length p) 2) (> (sd:dm-sarea p) amin))
          (setq polys (cons p polys))))))
  (sd:dm-clear)
  (sd:dm-drop (reverse polys)))

;; Hinh chu nhat? (4 dinh, moi goc vuong)
(defun sd:dm-rect-p (pts / i a b c ux uy vx vy ok)
  ;; dinh nut chu T nam tren canh (thang hang) khong lam o mat tinh chu nhat
  (if (> (length pts) 4) (setq pts (sd:dm-simp pts 0.3)))
  (if (= (length pts) 4)
    (progn
      (setq ok t i 0)
      (repeat 4
        (setq a (nth i pts) b (nth (rem (1+ i) 4) pts) c (nth (rem (+ i 2) 4) pts)
              ux (- (car a) (car b)) uy (- (cadr a) (cadr b)) vx (- (car c) (car b)) vy (- (cadr c) (cadr b)))
        (if (> (abs (/ (+ (* ux vx) (* uy vy)) (max 1e-9 (* (distance a b) (distance c b))))) 0.02) (setq ok nil))
        (setq i (1+ i)))
      ok)))

;; Cac o -> ban ghi (ma pts goc dai rong tam) theo thu tu lat ngoang nghoeo
(defun sd:dm-tiles (polys / tiles fr i)
  (foreach p polys
    (setq fr (sd:tile-frame p))
    (setq tiles (cons (list "" p (car fr) (cadr fr) (caddr fr) (cadddr fr)) tiles)))
  (setq i 0)
  (if tiles
    (mapcar '(lambda (r) (setq i (1+ i)) (cons (strcat "T" (itoa i)) (cddr r))) (sd:tile-order (reverse tiles)))))

;; Huong luoi chung cua cac o chu nhat (rad) neu >= 80% cung huong, nguoc lai nil -> SDANHDA tu xet tung vien
(defun sd:dm-frame (tiles / ks k best bn rects)
  (foreach r tiles
    (if (sd:dm-rect-p (cadr r))
      (progn (setq rects (1+ (cond (rects) (0))))
             (setq k (/ (fix (+ 0.5 (* 2.0 (rem (* 180.0 (/ (nth 2 r) pi)) (if (< (abs (- (nth 3 r) (nth 4 r))) 2.0) 90.0 180.0)))))
                        2.0))
             (if (assoc k ks) (setq ks (subst (cons k (1+ (cdr (assoc k ks)))) (assoc k ks) ks)) (setq ks (cons (cons k 1) ks))))))
  (foreach x ks (if (or (null best) (> (cdr x) bn)) (setq best (car x) bn (cdr x))))
  (if (and best (>= (* 1.0 bn) (* 0.8 rects))) (* pi (/ best 180.0))))

;; So -> chuoi (khong bi anh huong DIMZIN); chuoi -> so (nhan dau phay thap phan cua Excel)
(defun sd:dm-n (x p) (sd:rtos x p))
(defun sd:dm-num (s) (if (and s (/= s "")) (distof (vl-string-translate "," "." s) 2)))

;; ---------------- Cung / vong tron / spline -> da giac (chia nho), nhan lai cung khi ve ----------------
;; Diem doc theo cung / vong tron / spline / ellipse: (pts closed). Buoc 5 do (cung, tron), spline theo chieu dai
(defun sd:dm-curve (e ty ed / c r a0 a1 sw n i pts ln)
  (cond
    ((= ty "CIRCLE")
     (setq c (sd:2d (cdr (assoc 10 ed))) r (cdr (assoc 40 ed)) i 0)
     (repeat 72
       (setq pts (cons (polar c (* i (/ pi 36.0)) r) pts) i (1+ i)))
     (list (reverse pts) t))
    ((= ty "ARC")
     (setq c (sd:2d (cdr (assoc 10 ed))) r (cdr (assoc 40 ed)) a0 (cdr (assoc 50 ed)) a1 (cdr (assoc 51 ed))
           sw (- a1 a0))
     (if (<= sw 0.0) (setq sw (+ sw (* 2.0 pi))))
     (setq n (max 4 (fix (+ 1.0 (/ sw (/ pi 36.0))))) i 0)
     (repeat (1+ n)
       (setq pts (cons (polar c (+ a0 (* sw (/ i (float n)))) r) pts) i (1+ i)))
     (list (reverse pts) nil))
    (t
     (setq ln (vlax-curve-getDistAtParam e (vlax-curve-getEndParam e))
           n (max 12 (min 300 (+ 8 (fix (/ ln 25.0))))) i 0)
     (repeat (1+ n)
       (setq pts (cons (sd:2d (vlax-curve-getPointAtDist e (* ln (/ i (float n))))) pts) i (1+ i)))
     (list (reverse pts) (equal (vlax-curve-getPointAtParam e 0.0) (vlax-curve-getPointAtParam e (vlax-curve-getEndParam e)) 1e-6)))))

;; Goc re (rad, -pi..pi) tai dinh b khi di a -> b -> c
(defun sd:dm-turn (a b c / d)
  (setq d (- (angle b c) (angle a b)))
  (cond ((> d pi) (- d (* 2.0 pi))) ((< d (- pi)) (+ d (* 2.0 pi))) (t d)))

;; Do phinh cung (bulge) cua cung co goc ban kinh th (rad), chieu sg (+1 nguoc kim dong ho)
(defun sd:dm-bulge (th sg) (* sg (/ (sin (/ th 4.0)) (cos (/ th 4.0)))))

;; Nhan lai cung tu da giac: day dinh deu nhau, re deu cung chieu -> 1 cung. Tra ve ((x y bulge) ...)
(defun sd:dm-arcify (pts / n i ts ls fl tv a0 m k start runs run len j out al th sg)
  (setq n (length pts) i 0)
  (if (< n 6)
    (mapcar '(lambda (p) (list (car p) (cadr p) 0.0)) pts)
    (progn
      (foreach p pts
        (setq ts (cons (sd:dm-turn (nth (rem (+ i n -1) n) pts) p (nth (rem (1+ i) n) pts)) ts)
              ls (cons (distance p (nth (rem (1+ i) n) pts)) ls)
              i (1+ i)))
      (setq ts (reverse ts) ls (reverse ls) i 0)
      ;; dinh "trong cung": re 0.6 - 16 do, trung voi re dinh ke truoc hoac sau (+-12%), canh ke nhau xap xi
      (foreach tv ts
        (setq a0 (abs tv) m (nth (rem (+ i n -1) n) ts) k (nth (rem (1+ i) n) ts)
              fl (cons (if (and (> a0 0.0105) (< a0 0.28)
                                (or (and (> (* tv m) 0.0) (< (abs (- (abs m) a0)) (* 0.12 a0)))
                                    (and (> (* tv k) 0.0) (< (abs (- (abs k) a0)) (* 0.12 a0))))
                                (< (abs (- (nth (rem (+ i n -1) n) ls) (nth i ls))) (* 0.12 (nth i ls))))
                         t)
                       fl)
              i (1+ i)))
      (setq fl (reverse fl))
      (cond
        ((not (member nil fl))                      ; ca da giac la vong tron
         (if (= (rem n 2) 0)
           (progn
             (setq th (* (/ n 2) (/ (apply '+ (mapcar 'abs ts)) n)) sg (if (> (car ts) 0.0) 1.0 -1.0))
             (list (list (car (car pts)) (cadr (car pts)) (sd:dm-bulge th sg))
                   (list (car (nth (/ n 2) pts)) (cadr (nth (/ n 2) pts)) (sd:dm-bulge th sg))))
           (mapcar '(lambda (p) (list (car p) (cadr p) 0.0)) pts)))
        (t
         ;; dinh dau tien khong thuoc cung; bo cac day dinh cung ngan hon 2 dinh
         (setq start (vl-position nil fl)
               pts (append (sd:tail start pts) (sd:head start pts))
               ts (append (sd:tail start ts) (sd:head start ts))
               fl (append (sd:tail start fl) (sd:head start fl)) i 0)
         (while (< i n)
           (if (nth i fl)
             (progn (setq run 0 j i)
                    (while (and (< j n) (nth j fl)) (setq run (1+ run) j (1+ j)))
                    (if (< run 2) (setq fl (sd:dm-nilrun i run fl)))
                    (setq i j))
             (setq i (1+ i))))
         (setq i 0)
         (while (< i n)
           (setq len 0 j (1+ i))
           (while (and (< j n) (nth j fl)) (setq len (1+ len) j (1+ j)))
           (if (>= len 2)
             (progn
               (setq al (/ (apply '+ (mapcar 'abs (sd:head len (sd:tail (1+ i) ts)))) len)
                     th (* (1+ len) al) sg (if (> (nth (1+ i) ts) 0.0) 1.0 -1.0)
                     out (cons (list (car (nth i pts)) (cadr (nth i pts)) (sd:dm-bulge th sg)) out)
                     i (+ i len 1)))
             (setq out (cons (list (car (nth i pts)) (cadr (nth i pts)) 0.0) out)
                   i (1+ i))))
         (reverse out))))))

;; Thay k phan tu lien tiep bat dau tu i trong lst bang nil
(defun sd:dm-nilrun (i k lst / r j)
  (setq j 0)
  (foreach x lst
    (setq r (cons (if (and (>= j i) (< j (+ i k))) nil x) r) j (1+ j)))
  (reverse r))

;; ---------------- O co lo / cot ben trong: khoet, tach thanh cac vien lom (chu U / L) ----------------
;; Cat da giac loi theo nua mat phang x >= x0 (dir = 1) hoac x <= x0 (dir = -1); bo dinh trung
(defun sd:dm-clipx (poly x0 dir / out a b ina inb t0)
  (setq a (last poly) ina (>= (* dir (- (car a) x0)) -1e-9))
  (foreach b poly
    (setq inb (>= (* dir (- (car b) x0)) -1e-9))
    (cond
      ((and inb ina) (setq out (cons b out)))
      (inb (setq t0 (/ (- x0 (car a)) (- (car b) (car a)))
                 out (cons b (cons (list x0 (+ (cadr a) (* t0 (- (cadr b) (cadr a))))) out))))
      (ina (setq t0 (/ (- x0 (car a)) (- (car b) (car a)))
                 out (cons (list x0 (+ (cadr a) (* t0 (- (cadr b) (cadr a))))) out))))
    (setq a b ina inb))
  (setq out (reverse out) a nil)
  (vl-remove-if '(lambda (p) (if (and a (< (distance a p) 1e-6)) t (progn (setq a p) nil))) out))

(defun sd:dm-convex-p (pts / n i s c pos neg)
  (setq n (length pts) i 0)
  (repeat n
    (setq c (- (* (- (car (nth (rem (1+ i) n) pts)) (car (nth i pts))) (- (cadr (nth (rem (+ i 2) n) pts)) (cadr (nth (rem (1+ i) n) pts))))
               (* (- (cadr (nth (rem (1+ i) n) pts)) (cadr (nth i pts))) (- (car (nth (rem (+ i 2) n) pts)) (car (nth (rem (1+ i) n) pts))))))
    (if (> c 1e-6) (setq pos t))
    (if (< c -1e-6) (setq neg t))
    (setq i (1+ i)))
  (not (and pos neg)))

;; Vien lom: phan x >= cx (dir 1) hoac x <= cx (dir -1) cua outer, khoet phan lo hole cung phia (lo bi duong x = cx cat ngang)
(defun sd:dm-hole-piece (outer hole cx dir / p nh n k ch c1 c2 i j m pa pb p1 p2 out)
  (setq p (sd:dm-clipx outer cx dir) nh (sd:dm-clipx hole cx dir) n (length nh))
  (if (and (> (length p) 2) (> n 2))
    (progn
      ;; chuoi dinh cua lo khong nam tren duong cat, theo thu tu quanh lo: c1 -> ch -> c2
      (setq k 0)
      (while (and (< k n) (not (and (< (abs (- (car (nth k nh)) cx)) 1e-4)
                                    (>= (abs (- (car (nth (rem (1+ k) n) nh)) cx)) 1e-4))))
        (setq k (1+ k)))
      (if (< k n)
        (progn
          (setq c1 (nth k nh) j (rem (1+ k) n))
          (while (>= (abs (- (car (nth j nh)) cx)) 1e-4)
            (setq ch (cons (nth j nh) ch) j (rem (1+ j) n)))
          (setq ch (reverse ch) c2 (nth j nh) m (length p) i 0)
          ;; canh cua vien nam tren duong cat
          (while (and (< i m) (not (and (< (abs (- (car (nth i p)) cx)) 1e-4)
                                        (< (abs (- (car (nth (rem (1+ i) m) p)) cx)) 1e-4))))
            (setq i (1+ i)))
          (if (and ch (< i m))
            (progn
              (setq pa (nth i p) pb (nth (rem (1+ i) m) p))
              (if (<= (distance pa c1) (distance pa c2))
                (setq p1 c1 p2 c2)
                (setq p1 c2 p2 c1 ch (reverse ch)))
              (if (and (> (distance pa p1) 1e-3) (> (distance p2 pb) 1e-3))
                (progn
                  (setq j 0)
                  (foreach q p
                    (setq out (cons q out))
                    (if (= j i) (setq out (append (reverse (append (list p1) ch (list p2))) out)))
                    (setq j (1+ j)))
                  (reverse out))))))))))

;; Tach o outer (loi) co cac lo trong (holes, moi lo loi, khong chong nhau theo x) thanh cac vien lom, trong khung cuc bo; nil neu khong tach duoc
(defun sd:dm-split-hole (outer holes / hs n i h x0 x1 strip cx hb hc res bad)
  (setq hs (sd:sort holes '(lambda (a b) (< (apply 'min (mapcar 'car a)) (apply 'min (mapcar 'car b)))))
        n (length hs) i 0)
  (if (and (sd:dm-convex-p outer) (not (vl-some '(lambda (q) (not (sd:dm-convex-p q))) hs)))
    (progn
      (foreach h hs
        (setq x1 (if (< (1+ i) n) (/ (+ (apply 'max (mapcar 'car h)) (apply 'min (mapcar 'car (nth (1+ i) hs)))) 2.0))
              strip outer)
        (if (and x1 (>= (apply 'max (mapcar 'car h)) (apply 'min (mapcar 'car (nth (1+ i) hs))))) (setq bad t))
        (if x0 (setq strip (sd:dm-clipx strip x0 1)))
        (if x1 (setq strip (sd:dm-clipx strip x1 -1)))
        (setq cx (/ (+ (apply 'min (mapcar 'car h)) (apply 'max (mapcar 'car h))) 2.0)
              hb (sd:dm-hole-piece strip h cx -1) hc (sd:dm-hole-piece strip h cx 1))
        (if (and hb hc) (setq res (append res (list hb hc))) (setq bad t))
        (setq x0 x1 i (1+ i)))
      (if (not bad) res))))

;; Tim cac lo (o nam gon trong o khac, khong cham bien) va khoet: o chua lo thanh cac vien lom, o lo van giu (la o rieng hoac cot -> bo = 1)
;; Tra ve (cac-o so-lo so-vien so-o-khong-tach)
(defun sd:dm-holes (polys / recs i q r best isl nh np nf out hl fr c a lp pcs)
  (setq i 0)
  (foreach p polys
    (setq recs (cons (list i p (abs (sd:dm-sarea p)) (apply 'min (mapcar 'car p)) (apply 'min (mapcar 'cadr p))
                           (apply 'max (mapcar 'car p)) (apply 'max (mapcar 'cadr p)))
                     recs)
          i (1+ i)))
  (setq recs (reverse recs) nh 0 np 0 nf 0)
  (foreach q recs
    (setq best nil)
    (foreach r recs
      (if (and (/= (car r) (car q)) (> (nth 2 r) (nth 2 q))
               (<= (nth 3 r) (nth 3 q)) (<= (nth 4 r) (nth 4 q)) (>= (nth 5 r) (nth 5 q)) (>= (nth 6 r) (nth 6 q))
               (or (null best) (< (nth 2 r) (nth 2 best)))
               (not (vl-some '(lambda (v) (not (sd:inpoly v (cadr r)))) (cadr q))))
        (setq best r)))
    (if best (setq isl (cons (cons (car best) (car q)) isl))))
  (foreach r recs
    (setq hl (mapcar '(lambda (x) (cadr (nth (cdr x) recs))) (vl-remove-if-not '(lambda (x) (= (car x) (car r))) isl)))
    (if hl
      (progn
        (setq fr (sd:tile-frame (cadr r)) a (car fr) c (cadddr fr)
              pcs (sd:dm-split-hole (mapcar '(lambda (p) (sd:w2l c a p)) (cadr r))
                                    (mapcar '(lambda (h) (mapcar '(lambda (p) (sd:w2l c a p)) h)) hl)))
        (if pcs
          (progn
            (setq nh (+ nh (length hl)) np (+ np (length pcs)))
            (foreach q pcs
              (setq out (cons (sd:dm-simp (mapcar '(lambda (p) (sd:l2w c a p)) q) 0.3) out))))
          (setq nf (1+ nf) out (cons (cadr r) out))))
      (setq out (cons (cadr r) out))))
  (list (reverse out) nh np nf))

;; ---------------- JSON: xuat bang cho AI ngoai doc / dien, doc lai bang do AI dien ----------------
(defun sd:dm-json-write (fn tiles / f n pts)
  (if (setq f (sd:open fn "w"))
    (progn
      (write-line "{" f)
      (write-line "  \"dinh_dang\": \"SDDOCDA-1\"," f)
      (write-line "  \"don_vi\": \"mm\"," f)
      (write-line "  \"huong_dan\": [" f)
      (write-line "    \"Toa do tinh bang mm trong he toa do ban ve (goc 0,0; truc Y huong len). AI doc mat bang tu PDF / anh can quy ve toa do thuc dua vao mot kich thuoc da biet.\"," f)
      (write-line "    \"Moi vien la mot phan tu trong vien: hinh = CN (chu nhat, ve theo tam cx,cy + dai + rong + goc canh dai so voi truc X, do) hoac DAGIAC (da giac / hinh co cung: cac dinh trong pts dang x:y x:y ...; co the ghi pts la mang [[x,y],...]).\"," f)
      (write-line "    \"mavl = ma vat lieu (VD D1, G2); bo = 1 neu khong ve (cot, lo, o thua); ma = ma vien bat ky. Sau khi dien xong chay SDDOCDA, che do Ve, chon file nay.\"" f)
      (write-line "  ]," f)
      (write-line "  \"vien\": [" f)
      (setq n 0)
      (foreach r tiles
        (setq n (1+ n) pts (cadr r))
        (write-line
          (strcat "    {\"ma\": \"" (sd:jesc (car r)) "\", \"hinh\": \"" (if (sd:dm-rect-p pts) "CN" "DAGIAC") "\", \"dai\": " (sd:dm-n (nth 3 r) 1)
                  ", \"rong\": " (sd:dm-n (nth 4 r) 1)
                  ", \"goc\": " (sd:dm-n (rem (+ 360.0 (* 180.0 (/ (nth 2 r) pi))) (if (< (abs (- (nth 3 r) (nth 4 r))) 2.0) 90.0 180.0)) 2)
                  ", \"cx\": " (sd:dm-n (car (nth 5 r)) 1) ", \"cy\": " (sd:dm-n (cadr (nth 5 r)) 1)
                  ", \"pts\": \""
                  (if (sd:dm-rect-p pts) ""
                    (sd:join (mapcar '(lambda (q) (strcat (sd:dm-n (car q) 1) ":" (sd:dm-n (cadr q) 1))) pts) " "))
                  "\", \"mavl\": \"" (sd:jesc (cond ((nth 6 r)) (""))) "\", \"bo\": 0}"
                  (if (< n (length tiles)) "," ""))
          f))
      (write-line "  ]" f)
      (write-line "}" f)
      (sd:close f))))

;; Chuoi JSON bat dau tai ky tu i (la dau ngoac kep mo): tra ve (chuoi . vi-tri-sau-dau-dong)
(defun sd:dm-jstr (s i / r c n)
  (setq i (1+ i) r "" n (strlen s))
  (while (and (<= i n) (/= (setq c (substr s i 1)) "\""))
    (if (= c "\\")
      (progn (setq i (1+ i) c (substr s i 1))
             (setq r (strcat r (cond ((member c '("n" "t" "r")) " ") (t c)))))
      (setq r (strcat r c)))
    (setq i (1+ i)))
  (cons r (1+ i)))

(defun sd:dm-numch (c ext) (vl-string-search c (if ext "0123456789-.+eE" "0123456789-.")))

;; Mot doi tuong JSON phang (khoa: gia-tri, ...) -> ((KHOA . chuoi) ...); mang so -> dang x:y x:y; true -> 1; null / false -> trong
(defun sd:dm-jobj (s / i n c k v r tok nums dp)
  (setq i 1 n (strlen s))
  (while (<= i n)
    (setq c (substr s i 1))
    (cond
      ((= c "\"")
       (setq v (sd:dm-jstr s i) k (car v) i (cdr v))
       (while (and (<= i n) (member (substr s i 1) '(" " ":" "\t"))) (setq i (1+ i)))
       (setq c (substr s i 1))
       (cond
         ((= c "\"")
          (setq v (sd:dm-jstr s i) r (cons (cons (strcase k) (car v)) r) i (cdr v)))
         ((= c "[")
          (setq nums nil dp 1 i (1+ i))
          (while (and (<= i n) (> dp 0))
            (setq c (substr s i 1))
            (cond
              ((= c "[") (setq dp (1+ dp) i (1+ i)))
              ((= c "]") (setq dp (1- dp) i (1+ i)))
              ((sd:dm-numch c nil)
               (setq tok "")
               (while (and (<= i n) (sd:dm-numch (substr s i 1) t))
                 (setq tok (strcat tok (substr s i 1)) i (1+ i)))
               (setq nums (cons tok nums)))
              (t (setq i (1+ i)))))
          (setq nums (reverse nums) tok "")
          (while (cdr nums)
            (setq tok (strcat tok (if (= tok "") "" " ") (car nums) ":" (cadr nums)) nums (cddr nums)))
          (setq r (cons (cons (strcase k) tok) r)))
         (t
          (setq tok "")
          (while (and (<= i n) (not (member (substr s i 1) '("," "}" " " "\t"))))
            (setq tok (strcat tok (substr s i 1)) i (1+ i)))
          (setq r (cons (cons (strcase k) (cond ((= tok "true") "1") ((member tok '("false" "null")) "") (t tok))) r)))))
      (t (setq i (1+ i)))))
  (reverse r))

;; Doc file JSON -> cac dong nhu sd:nb-read: ((so-thu-tu "VIENDA" ((KHOA . chuoi) ...)) ...)
(defun sd:dm-json-rows (fn / f ln txt i n c depth st tgt items inq esc k res)
  (if (setq f (sd:open fn "r"))
    (progn
      (setq txt "")
      (while (setq ln (read-line f)) (setq txt (strcat txt " " ln)))
      (sd:close f)
      (setq i 1 n (strlen txt) depth 0
            tgt (if (= (substr (vl-string-left-trim " \t" txt) 1 1) "[") 1 2))
      (while (<= i n)
        (setq c (substr txt i 1))
        (cond
          (inq (cond (esc (setq esc nil)) ((= c "\\") (setq esc t)) ((= c "\"") (setq inq nil))))
          ((= c "\"") (setq inq t))
          ((= c "{") (setq depth (1+ depth)) (if (= depth tgt) (setq st i)))
          ((= c "}")
           (if (and (= depth tgt) st)
             (setq items (cons (substr txt st (1+ (- i st))) items) st nil))
           (setq depth (1- depth))))
        (setq i (1+ i)))
      (setq k 0)
      (foreach obj (reverse items)
        (setq k (1+ k) res (cons (list k "VIENDA" (sd:dm-jobj obj)) res)))
      (reverse res))))

(defun sd:dm-json-p (fn / e) (and (setq e (vl-filename-extension fn)) (= (strcase e) ".JSON")))

;; Polyline kin tu da giac; nhan lai cung (bulge) neu co day dinh deu
(defun sd:dm-pl (pts lay / vs)
  (setq vs (sd:dm-arcify pts))
  (if (vl-some '(lambda (v) (/= (caddr v) 0.0)) vs)
    (entmake (append (list '(0 . "LWPOLYLINE") '(100 . "AcDbEntity") (cons 8 lay) '(100 . "AcDbPolyline") (cons 90 (length vs)) '(70 . 1))
                     (apply 'append (mapcar '(lambda (v) (list (list 10 (car v) (cadr v)) (cons 42 (caddr v)))) vs))))
    (sd:pline pts t lay)))

;; Ma vat lieu cua tung o tu chu (TEXT / MTEXT) hoac hatch nam trong o: tra ve danh sach ma cung thu tu o (nil = khong co)
;; nguon "Chu" | "Hatch"; lochu = cac tien to chu cho phep, cach nhau dau phay (trong = moi chu)
(defun sd:dm-items (nguon lochu bb / ss i e ed r cd ty pre ok c)
  (if (and bb (setq ss (ssget "_W" (car bb) (cadr bb) (list (cons 0 (if (= nguon "Hatch") "HATCH" "TEXT,MTEXT"))))))
    (progn
      (setq i 0 pre (vl-remove "" (mapcar '(lambda (x) (strcase (vl-string-trim " " x))) (sd:split (cond (lochu) ("")) ","))))
      (repeat (sslength ss)
        (setq e (ssname ss i) i (1+ i) ed (entget e) ty (cdr (assoc 0 ed)) cd nil)
        (cond
          ((= ty "HATCH")
           (setq cd (cond ((/= (strcase (cdr (assoc 2 ed))) "SOLID") (cdr (assoc 2 ed)))
                          ((assoc 62 ed) (strcat "M" (itoa (cdr (assoc 62 ed)))))
                          (t (cdr (assoc 8 ed))))))
          ((= ty "MTEXT") (setq cd (sd:mt-plain (strcat (apply 'strcat (mapcar 'cdr (vl-remove-if-not '(lambda (g) (= (car g) 3)) ed))) (cdr (assoc 1 ed))))))
          (t (setq cd (cdr (assoc 1 ed)))))
        (if cd (setq cd (vl-string-trim " \t" cd)))
        (if (and cd (/= cd "")
                 (or (null pre) (vl-some '(lambda (x) (wcmatch (strcase cd) (strcat x "*"))) pre)))
          (if (setq c (sd:nb-bbox (list e)))
            (setq r (cons (cons (list (/ (+ (car (car c)) (car (cadr c))) 2.0) (/ (+ (cadr (car c)) (cadr (cadr c))) 2.0)) cd) r))))))
    nil)
  r)

(defun sd:dm-codes (tiles nguon lochu / items bb pts mn mx code res)
  (if (and (member nguon '("Chu" "Hatch")) tiles)
    (progn
      (setq pts (apply 'append (mapcar 'cadr tiles))
            bb (list (list (- (apply 'min (mapcar 'car pts)) 1.0) (- (apply 'min (mapcar 'cadr pts)) 1.0))
                     (list (+ (apply 'max (mapcar 'car pts)) 1.0) (+ (apply 'max (mapcar 'cadr pts)) 1.0)))
            items (sd:dm-items nguon lochu bb))
      (foreach r tiles
        ;; nhieu chu trong 1 o: lay chu ngan nhat (ma vat lieu ngan, ghi chu thi dai)
        (setq code nil)
        (foreach it items
          (if (and (or (null code) (< (strlen (cdr it)) (strlen code))) (sd:inpoly (car it) (cadr r)))
            (setq code (cdr it))))
        (setq res (cons code res)))
      (reverse res))
    (mapcar '(lambda (r) nil) tiles)))

;; Gan them ma vao ban ghi o: (ma pts goc dai rong tam ma-vl)
(defun sd:dm-attach (tiles codes / i)
  (setq i -1)
  (mapcar '(lambda (r) (setq i (1+ i)) (append r (list (nth i codes)))) tiles))

;; Gan du lieu SD_TILE (ma VL, vien nguyen / cat, ma vien cat) cho cac polyline vua ve -> SDGACHTK / SDDATHO / SDGIACONG dung duoc
(defun sd:dm-tag (tiles els mat0 ten thk sc / i grp mat g fulls full pieces r n)
  (setq i 0)
  (foreach r tiles
    (setq mat (cond ((and (nth 6 r) (/= (nth 6 r) "")) (nth 6 r)) ((and mat0 (/= mat0 "")) mat0)))
    (if mat
      (if (setq g (assoc mat grp))
        (setq grp (subst (cons mat (cons (cons (nth i els) r) (cdr g))) g grp))
        (setq grp (cons (list mat (cons (nth i els) r)) grp))))
    (setq i (1+ i)))
  (setq n 0)
  (foreach g grp
    ;; kich thuoc vien nguyen = kich thuoc chu nhat hay gap nhat cua ma do
    (setq fulls nil)
    (foreach x (cdr g)
      (setq r (cdr x))
      (if (sd:dm-rect-p (cadr r))
        (setq full (list (fix (+ 0.5 (max (nth 3 r) (nth 4 r)))) (fix (+ 0.5 (min (nth 3 r) (nth 4 r)))))
              fulls (if (assoc full fulls) (subst (cons full (1+ (cdr (assoc full fulls)))) (assoc full fulls) fulls) (cons (cons full 1) fulls)))))
    (setq full nil)
    (foreach f fulls (if (or (null full) (> (cdr f) (cdr full))) (setq full f)))
    (setq full (if full (mapcar 'float (car full)) (list 0.0 0.0)) pieces nil)
    (foreach x (reverse (cdr g))
      (setq r (cdr x)
            pieces (cons (list (list (car x)) (nth 3 r) (nth 4 r) (abs (sd:dm-sarea (cadr r)))
                               (sd:rect-typ (nth 3 r) (nth 4 r) (abs (sd:dm-sarea (cadr r))) full)
                               (nth 5 r) (list 0.0 0.0) (list 0.0 0.0 0.0) (nth 2 r))
                         pieces)))
    (sd:code-pieces (reverse pieces) (car g) (cond ((and ten (/= ten "")) ten) ((car g))) (car full) (cadr full) thk nil sc)
    (setq n (+ n (length pieces))))
  n)

;; Ve cac o: (ma pts goc dai rong tam) -> polyline kin tren layer, tra ve danh sach ename
(defun sd:dm-draw (tiles dn sc / r els)
  (foreach r tiles
    (sd:dm-pl (cadr r) "SD-GACH-DOC")
    (setq els (cons (entlast) els))
    (if dn (sd:text (nth 5 r) (car r) (sd:tile-th (nth 3 r) (nth 4 r) sc) "MC" "SD-CHU")))
  (reverse els))

;; Ghi bang CSV (cung dinh dang SDNHAPBANG): moi o 1 dong VIENDA
(defun sd:dm-write (fn tiles / f r pts)
  (if (setq f (sd:open fn "w"))
    (progn
      (write-line "sep=;" f)
      (write-line "# BANG VIEN DA tu SDDOCDA - soat, sua, bo sung roi chay SDDOCDA > Ve (hoac SDANHDA tren cac polyline vua ve)" f)
      (write-line "# CN = chu nhat: ve theo tam (cx;cy) + dai + rong + goc; DAGIAC: ve theo cot pts (x:y x:y ...). Them o thieu = them dong CN co cx;cy;dai;rong;goc" f)
      (write-line "# bo = 1: khong ve dong do (cot, lo, o thua). Goc la goc canh dai so voi truc X (do)" f)
      (write-line "Loai;ma;hinh;dai;rong;goc;cx;cy;dtich;pts;mavl;bo;ghichu" f)
      (write-line "#;Ma vien;Hinh [CN/DAGIAC];Dai (mm);Rong (mm);Goc canh dai (do);Tam X;Tam Y;Dien tich (m2);Dinh DAGIAC (x:y x:y);Ma vat lieu (D1, G2...);Bo qua [1];Ghi chu" f)
      (foreach r tiles
        (setq pts (cadr r))
        (write-line
          (sd:join (list "VIENDA" (car r) (if (sd:dm-rect-p pts) "CN" "DAGIAC")
                         (sd:dm-n (nth 3 r) 1) (sd:dm-n (nth 4 r) 1)
                         (sd:dm-n (rem (+ 360.0 (* 180.0 (/ (nth 2 r) pi))) (if (< (abs (- (nth 3 r) (nth 4 r))) 2.0) 90.0 180.0)) 2)
                         (sd:dm-n (car (nth 5 r)) 1) (sd:dm-n (cadr (nth 5 r)) 1)
                         (sd:dm-n (/ (abs (sd:dm-sarea pts)) 1e6) 3)
                         (if (sd:dm-rect-p pts) ""
                           (sd:join (mapcar '(lambda (q) (strcat (sd:dm-n (car q) 1) ":" (sd:dm-n (cadr q) 1))) pts) " "))
                         (cond ((nth 6 r)) (""))
                         "" "")
                   ";")
          f))
      (sd:close f))))

;; Doc bang -> cac o (ma pts goc dai rong tam); canh bao dong loi
(defun sd:dm-read (fn / rows tiles v dai rong goc cx cy pts s q bad row hinh n)
  (setq n 0)
  (foreach row (if (sd:dm-json-p fn) (sd:dm-json-rows fn) (sd:nb-read fn))
    (if (= (cadr row) "VIENDA")
      (progn
        (setq v (caddr row))
        (if (member (cdr (assoc "BO" v)) '("1" "x" "X"))
          (setq n (1+ n))
          (progn
            (setq hinh (strcase (cond ((cdr (assoc "HINH" v))) ("CN")))
                  dai (sd:dm-num (cdr (assoc "DAI" v))) rong (sd:dm-num (cdr (assoc "RONG" v)))
                  goc (cond ((sd:dm-num (cdr (assoc "GOC" v)))) (0.0))
                  cx (sd:dm-num (cdr (assoc "CX" v))) cy (sd:dm-num (cdr (assoc "CY" v))) pts nil)
            (cond
              ((= hinh "DAGIAC")
               (foreach s (sd:split (cond ((cdr (assoc "PTS" v))) ("")) " ")
                 (if (and (/= s "") (setq q (sd:split s ":")) (cdr q) (sd:dm-num (car q)) (sd:dm-num (cadr q)))
                   (setq pts (cons (list (sd:dm-num (car q)) (sd:dm-num (cadr q))) pts))))
               (setq pts (reverse pts)))
              ((and dai rong cx cy (> dai 0.0) (> rong 0.0))
               (setq pts (mapcar '(lambda (p) (sd:l2w (list cx cy) (* pi (/ goc 180.0)) p))
                                 (list (list (/ dai -2.0) (/ rong -2.0)) (list (/ dai 2.0) (/ rong -2.0))
                                       (list (/ dai 2.0) (/ rong 2.0)) (list (/ dai -2.0) (/ rong 2.0)))))))
            (if (and pts (> (length pts) 2))
              (setq tiles (cons (list (cond ((cdr (assoc "MA" v))) ((strcat "T" (itoa (1+ (length tiles)))))) pts
                                      (* pi (/ goc 180.0)) (cond (dai) (0.0)) (cond (rong) (0.0)) (sd:centroid pts)
                                      (vl-string-trim " " (cond ((cdr (assoc "MAVL" v))) (""))))
                                tiles))
              (setq bad (cons (strcat "dong " (itoa (car row)) " (" (cond ((cdr (assoc "MA" v))) ("?")) "): thieu so lieu"
                                      (if (= hinh "DAGIAC") " pts (can >= 3 dinh x:y)" " (CN can cx;cy;dai;rong)"))
                              bad)))))))
    )
  (list (reverse tiles) (reverse bad) n))

(defun sd:dm-select (nguon lay / ss i ents)
  (cond
    ((= nguon "Layer") (setq ss (ssget "_X" (list '(0 . "LINE,LWPOLYLINE,ARC,CIRCLE,SPLINE,ELLIPSE") (cons 8 lay)))))
    (t (princ "\nQuet chon mat bang op lat (LINE, polyline, cung, tron, spline): ")
       (setq ss (ssget '((0 . "LINE,LWPOLYLINE,ARC,CIRCLE,SPLINE,ELLIPSE"))))))
  (if ss
    (progn (setq i 0)
           (repeat (sslength ss) (setq ents (cons (ssname ss i) ents) i (1+ i)))
           ;; bo net tren cac layer khong phai mat bang lat (mui bac, thang...)
           (if (and *SD:DMLAYX* (/= *SD:DMLAYX* ""))
             (progn
               (setq i (length ents)
                     ents (vl-remove-if '(lambda (e) (wcmatch (strcase (cdr (assoc 8 (entget e)))) (strcase *SD:DMLAYX*))) ents))
               (if (< (length ents) i) (princ (strcat "\n[SD] Bo qua " (itoa (- i (length ents))) " net tren layer " *SD:DMLAYX* ".")))))
           ents)))

;; Khoang cach tu diem toi doan a-b (co kep hai dau)
(defun sd:dm-segdist (p a b / tt)
  (setq tt (car (sd:dm-proj p a b)))
  (cond ((<= tt 0.0) (distance p a)) ((>= tt 1.0) (distance p b)) (t (cdr (sd:dm-proj p a b)))))

;; Dau mut khong noi voi net nao trong dung sai: ((x y khoang-cach) ...). khoang-cach <= 4 x dung sai = ho gan (gan nhu khep),
;; lon hon / khong co net gan = dau mut treo (khoang-cach = -1)
(defun sd:dm-near (segs tol / far i j q best res o mn)
  (setq far (* 4.0 tol) i 0)
  (foreach s segs
    (foreach q (list (car s) (cadr s))
      (setq best nil j 0)
      (foreach o segs
        (if (and (/= i j)
                 (>= (car q) (- (min (car (car o)) (car (cadr o))) far)) (<= (car q) (+ (max (car (car o)) (car (cadr o))) far))
                 (>= (cadr q) (- (min (cadr (car o)) (cadr (cadr o))) far)) (<= (cadr q) (+ (max (cadr (car o)) (cadr (cadr o))) far)))
          (progn (setq mn (sd:dm-segdist q (car o) (cadr o)))
                 (if (or (null best) (< mn best)) (setq best mn))))
        (setq j (1+ j)))
      (if (or (null best) (> best tol))
        (if (not (vl-some '(lambda (r) (< (distance r q) (* 2.0 far))) (mapcar 'list (mapcar 'car res) (mapcar 'cadr res))))
          (setq res (cons (list (car q) (cadr q) (if (and best (<= best far)) best -1.0)) res)))))
    (setq i (1+ i)))
  (reverse res))

;; Kiem tra o: ((x y ban-kinh chuoi) ...) - manh vun, nghi thieu net chia (o lon gap boi so o thuong), lech kich thuoc so voi o chuan
(defun sd:dm-odd (tiles sc / ars med keys modal r a w h rk out k kk mw mh cen)
  (foreach r tiles
    (if (sd:dm-rect-p (cadr r))
      (progn
        (setq ars (cons (* (nth 3 r) (nth 4 r)) ars)
              k (list (fix (+ 0.5 (max (nth 3 r) (nth 4 r)))) (fix (+ 0.5 (min (nth 3 r) (nth 4 r))))))
        (if (assoc k keys)
          (setq keys (subst (cons k (1+ (cdr (assoc k keys)))) (assoc k keys) keys))
          (setq keys (cons (cons k 1) keys))))))
  (if (> (length ars) 3)
    (progn
      (setq ars (sd:sort ars '<) med (nth (/ (length ars) 2) ars))
      (foreach kk keys (if (or (null modal) (> (cdr kk) (cdr modal))) (setq modal kk)))
      (setq mw (car (car modal)) mh (cadr (car modal)))
      (foreach r tiles
        (if (sd:dm-rect-p (cadr r))
          (progn
            (setq a (* (nth 3 r) (nth 4 r)) w (max (nth 3 r) (nth 4 r)) h (min (nth 3 r) (nth 4 r))
                  rk (min (* 0.25 h) (* 6.0 sc)) cen (nth 5 r))
            (cond
              ((< a (* 0.1 med))
               (setq out (cons (list (car cen) (cadr cen) rk (strcat (car r) ": manh vun " (sd:num w) "x" (sd:num h))) out)))
              ((> a (* 1.8 med))
               (setq out (cons (list (car cen) (cadr cen) rk
                                     (strcat (car r) ": nghi thieu net chia (~" (itoa (fix (+ 0.5 (/ a med)))) " o)"))
                               out)))
              ((and (>= (cdr modal) (* 0.4 (length ars)))
                    (< (abs (- w mw)) (* 0.15 mw)) (< (abs (- h mh)) (* 0.15 mh))
                    (> (+ (abs (- w mw)) (abs (- h mh))) 2.0))
               (setq out (cons (list (car cen) (cadr cen) rk
                                     (strcat (car r) ": lech kich thuoc " (sd:num w) "x" (sd:num h) " (chuan " (sd:num mw) "x" (sd:num mh) ")"))
                               out)))))))))
  (reverse out))

;; Bao cao kiem tra: in tom tat; khoanh do tren ban ve neu mark
(defun sd:dm-report (segs tiles tol mark sc / near odd nho ntreo)
  (if (> (length segs) 900)
    (princ "\n[SD] Nhieu net (>900): bo qua kiem tra ho / dau mut treo cho nhanh.")
    (progn
      (setq near (sd:dm-near segs tol))
      (foreach n near
        (if (>= (caddr n) 0.0) (setq nho (cons n nho)) (setq ntreo (cons n ntreo))))))
  (setq odd (sd:dm-odd tiles sc))
  (princ (strcat "\n[SD] Kiem tra: " (itoa (length nho)) " cho ho gan khep (dau mut cach net <= " (sd:num (* 4.0 tol)) " mm nhung > dung sai), "
                 (itoa (length ntreo)) " dau mut treo, " (itoa (length odd)) " o khac thuong."))
  (if (or nho ntreo odd)
    (if mark
      (progn
        (sd:make-layer "SD-KIEMTRA" 1 "Continuous" 35)
        (foreach n nho (sd:lk-mark (list (car n) (cadr n) 0.0) (* 2.0 sc) (strcat "ho " (sd:num (caddr n)) " mm: tang dung sai hoac noi net") sc))
        (foreach n ntreo (sd:lk-mark (list (car n) (cadr n) 0.0) (* 1.2 sc) "dau mut treo" sc))
        (foreach o odd (sd:lk-mark (list (car o) (cadr o) 0.0) (caddr o) (cadddr o) sc))
        (princ "\n[SD] Da khoanh do tren layer SD-KIEMTRA (xoa bang lenh SDKIEMTRA > hoac xoa layer)."))
      (progn
        (foreach o odd (princ (strcat "\n[SD]   " (cadddr o))))
        (if (or nho ntreo odd) (princ "\n[SD] Chay SDDOCDA che do Kiem de khoanh do tung cho tren ban ve.")))))
  (list (length nho) (length ntreo) (length odd)))

;; Cac da giac kin can NE khi dung o (mat cat mui bac, chi tiet): lay tu 1 layer hoac chon tren man hinh
(defun sd:dm-ne-get (/ ss i r)
  (cond
    ((= *SD:DMNEM* "Layer")
     (setq ss (ssget "_X" (list '(0 . "LWPOLYLINE") (cons 8 *SD:DMNEL*) '(-4 . "&") '(70 . 1)))))
    ((= *SD:DMNEM* "Chon")
     (princ "\nChon cac polyline kin can ne (mat cat mui bac, chi tiet...): ")
     (setq ss (ssget '((0 . "LWPOLYLINE") (-4 . "&") (70 . 1))))))
  (if ss
    (progn (setq i 0)
           (repeat (sslength ss) (setq r (cons (sd:curve-pts (ssname ss i)) r) i (1+ i)))))
  r)

;; Diem nam trong da giac hoac sat canh (<= 2 mm)
(defun sd:dm-pt-in-or-on (pt poly / a on)
  (setq a (last poly))
  (foreach b poly (if (<= (sd:dm-segdist pt a b) 2.0) (setq on t)) (setq a b))
  (or on (sd:inpoly pt poly)))

;; O (da giac) nam trong vung ne: moi dinh nam trong / sat canh vung ne, hoac it nhat 1/2 so diem lay mau (tam + trung diem tam - dinh) nam trong
(defun sd:dm-in-ne (pts nes / cx cy smp)
  (setq cx (/ (apply '+ (mapcar 'car pts)) (float (length pts))) cy (/ (apply '+ (mapcar 'cadr pts)) (float (length pts)))
        smp (cons (list cx cy) (mapcar '(lambda (q) (list (/ (+ cx (car q)) 2.0) (/ (+ cy (cadr q)) 2.0))) pts)))
  (vl-some '(lambda (ne)
              (or (vl-every '(lambda (q) (sd:dm-pt-in-or-on q ne)) pts)
                  (>= (* 2 (length (vl-remove-if-not '(lambda (pt) (sd:inpoly pt ne)) smp))) (length smp))))
           nes))

(defun sd:dm-doc (nguon lay tol amin ve dn anh mng lochu mat0 ten thk khoet json / ents segs polys tiles fn sc nrect ntot els codes ncode hr jfn nes n0)
  (setq sc (sd:sc))
  (if (null (setq ents (sd:dm-select nguon lay)))
    (princ "\n[SD] Khong co net nao.")
    (progn
      (setq segs (sd:dm-segs ents))
      (princ (strcat "\n[SD] " (itoa (length segs)) " doan thang, dung sai " (sd:num tol) " mm..."))
      (if (> (length segs) 3000) (princ "\n[SD] Nhieu net (>3000): co the cham, doi chut."))
      (setq polys (sd:dm-faces segs tol (* 1e6 amin)))
      (if (null polys)
        (princ "\n[SD] Khong dung duoc o kin nao: thu tang dung sai noi dau mut, hoac giam dien tich toi thieu.")
        (progn
          (if khoet
            (progn
              (setq hr (sd:dm-holes polys) polys (car hr))
              (if (> (cadr hr) 0)
                (princ (strcat "\n[SD] Khoet " (itoa (cadr hr)) " lo / cot ben trong o: tach thanh " (itoa (caddr hr))
                               " vien lom (chu U / L). Lo / cot van la o rieng - dat bo = 1 trong bang neu la cot.")))
              (if (> (cadddr hr) 0)
                (princ (strcat "\n[SD] " (itoa (cadddr hr)) " o co lo khong tach duoc (lo khong loi / chong nhau theo huong cat): giu nguyen.")))))
          (setq tiles (sd:dm-tiles polys))
          ;; ne cac vung kin da chi dinh (mat cat mui bac...): khong ve / khong hatch / khong cat anh
          (if (and *SD:DMNEM* (/= *SD:DMNEM* "Khong") (setq nes (sd:dm-ne-get)))
            (progn
              (setq n0 (length tiles) tiles (vl-remove-if '(lambda (r) (sd:dm-in-ne (cadr r) nes)) tiles))
              (princ (strcat "\n[SD] Ne " (itoa (- n0 (length tiles))) " o nam trong " (itoa (length nes)) " vung kin (mat cat mui bac, chi tiet): khong ve, khong hatch."))))
          (setq ntot (length tiles) nrect 0)
          (foreach r tiles (if (sd:dm-rect-p (cadr r)) (setq nrect (1+ nrect))))
          (princ (strcat "\n[SD] Dung duoc " (itoa ntot) " o kin: " (itoa nrect) " chu nhat, " (itoa (- ntot nrect)) " hinh vat / da giac."))
          (if (> *SD:DMDROP* 0) (princ (strcat "\n[SD] Bo " (itoa *SD:DMDROP*) " khung bao ngoai (chua cac o khac ben trong).")))
          (setq codes (sd:dm-codes tiles mng lochu) ncode 0)
          (foreach c codes (if c (setq ncode (1+ ncode))))
          (if (/= mng "Khong")
            (princ (strcat "\n[SD] Ma vat lieu (" (if (= mng "Hatch") "hatch" "chu") "): " (itoa ncode) " / " (itoa ntot) " o co ma"
                           (if (< ncode ntot) " - o chua co ma de trong cot mavl trong bang." ""))))
          (setq tiles (sd:dm-attach tiles codes))
          (sd:dm-report segs tiles tol nil sc)
          (if (setq fn (sd:csv-name "_DocMatBang.csv"))
            (progn (sd:dm-write fn tiles)
                   (princ (strcat "\n[SD] Da ghi bang: " fn "  (mo Excel soat, them o thieu, bo = 1 cho cot / lo; roi SDDOCDA > Ve)"))))
          (if (and json (setq jfn (sd:csv-name "_DocMatBang.json")))
            (progn (sd:dm-json-write jfn tiles)
                   (princ (strcat "\n[SD] Da ghi JSON cho AI ngoai: " jfn "  (AI dien lai theo huong_dan trong file, roi SDDOCDA > Ve chon file .json)"))))
          (if (or ve anh)
            (progn
              (setq els (sd:dm-draw tiles dn sc))
              (princ (strcat "\n[SD] Da ve " (itoa (length els)) " polyline kin (layer SD-GACH-DOC)."))
              (sd:dm-tagmsg tiles els mat0 ten thk sc)
              (if anh (sd:dm-anhda tiles els)))
            (if dn (foreach r tiles (sd:text (nth 5 r) (car r) (sd:tile-th (nth 3 r) (nth 4 r) sc) "MC" "SD-CHU")))))))))

;; Gan SD_TILE neu co ma (trong bang / mac dinh) va bao ket qua
(defun sd:dm-tagmsg (tiles els mat0 ten thk sc / n)
  (if (or (and mat0 (/= mat0 "")) (vl-some '(lambda (r) (and (nth 6 r) (/= (nth 6 r) ""))) tiles))
    (progn (setq n (sd:dm-tag tiles els mat0 ten thk sc))
           (princ (strcat "\n[SD] Gan du lieu SD_TILE cho " (itoa n) " vien (ma VL, vien nguyen / cat): dung duoc SDGACHTK, SDDATHO, SDGIACONG.")))))

;; Che do Kiem: dung o + khoanh do cho ho / dau mut treo / o khac thuong
(defun sd:dm-kiem (nguon lay tol amin / ents segs polys tiles sc)
  (setq sc (sd:sc))
  (if (null (setq ents (sd:dm-select nguon lay)))
    (princ "\n[SD] Khong co net nao.")
    (progn
      (setq segs (sd:dm-segs ents) polys (sd:dm-faces segs tol (* 1e6 amin)) tiles (sd:dm-tiles polys))
      (princ (strcat "\n[SD] " (itoa (length segs)) " doan thang, " (itoa (length tiles)) " o kin."))
      (sd:dm-report segs tiles tol t sc))))

;; Chay SDANHDA ngay tren cac polyline vua ve, voi khung van chung cua luoi
(defun sd:dm-anhda (tiles els)
  (setq *SD:IFRAME* (sd:dm-frame tiles))
  (if *SD:IFRAME* (princ (strcat "\n[SD] Luoi chung huong " (sd:num (* 180.0 (/ *SD:IFRAME* pi))) " do: van da song song voi luoi.")))
  (sd:anhda els)
  (setq *SD:IFRAME* nil))

(defun sd:dm-ve (dn anh mat0 ten thk / fn res tiles els sc)
  (setq sc (sd:sc))
  (if (setq fn (getfiled "Chon file bang vien da (CSV hoac JSON tu SDDOCDA)" (getvar "DWGPREFIX") "csv;json" 0))
    (progn
      (setq res (sd:dm-read fn) tiles (car res))
      (foreach b (cadr res) (princ (strcat "\n[SD]   Loi " b)))
      (if (null tiles)
        (princ "\n[SD] Bang khong co dong VIENDA hop le.")
        (progn
          (setq els (sd:dm-draw tiles dn sc))
          (princ (strcat "\n[SD] Da ve " (itoa (length els)) " polyline kin tu bang (bo qua " (itoa (caddr res)) " dong bo = 1, "
                         (itoa (length (cadr res))) " dong loi)."))
          (sd:dm-tagmsg tiles els mat0 ten thk sc)
          (if anh (sd:dm-anhda tiles els)
            (princ "\n[SD] Tiep theo: SDANHDA (quet chon cac polyline vua ve), SDTKDA, SDGACHTK, SDVANDA.")))))))

;;; --------------------------------------------------------------------------
;;;  SDHANDINH - Han dinh: cac polyline sinh ra tu cung 1 diem giao cat phai co dinh TRUNG NHAU
;;;  1) cac dinh cach nhau <= dung sai duoc gop ve 1 toa do chung (trung binh)
;;;  2) dinh nam tren canh cua polyline ke ben (nut chu T) duoc chen them vao canh do
;;; --------------------------------------------------------------------------
;; Tach ban ghi polyline: (phan-dau (dinh ...) phan-duoi); dinh = ((x y) cap-phu ...) voi cap-phu = 40 / 41 / 42 / 91 ngay sau dinh
(defun sd:wd-split (ed / head vs cur tail in)
  (foreach p ed
    (cond
      (tail (setq tail (cons p tail)))
      ((= (car p) 10) (if cur (setq vs (cons (reverse cur) vs))) (setq cur (list (list (cadr p) (caddr p))) in t))
      ((and in (member (car p) '(40 41 42 91))) (setq cur (cons p cur)))
      (in (if cur (setq vs (cons (reverse cur) vs))) (setq cur nil tail (list p)))
      (t (setq head (cons p head)))))
  (if cur (setq vs (cons (reverse cur) vs)))
  (list (reverse head) (reverse vs) (reverse tail)))

(defun sd:wd-join (head vs tail)
  (append (mapcar '(lambda (p) (if (= (car p) 90) (cons 90 (length vs)) p)) head)
          (apply 'append (mapcar '(lambda (v) (cons (list 10 (car (car v)) (cadr (car v))) (cdr v))) vs))
          tail))

;; Gop diem trong dung sai thanh nut. Tra ve toa do nut (x y) theo dung thu tu diem dau vao
(defun sd:wd-cluster (pts tol / i items win hit asg nid x k res)
  (setq i 0)
  (foreach p pts (setq i (1+ i) items (cons (list i (car p) (cadr p)) items)))
  (setq nid 0)
  (foreach it (sd:sort items '(lambda (a b) (< (cadr a) (cadr b))))
    (setq x (cadr it)
          win (vl-remove-if '(lambda (n) (< (cadr n) (- x tol))) win)
          hit (vl-some '(lambda (n) (if (<= (distance (cdr n) (cdr it)) tol) (car n))) win))
    (if (null hit)
      (progn (setq hit nid nid (1+ nid) win (cons (list hit (cadr it) (caddr it)) win))
             (set (read (strcat "SDWD_S" (itoa hit))) (list 0.0 0.0 0))))
    (set (read (strcat "SDWD_S" (itoa hit)))
         (list (+ (cadr it) (car (eval (read (strcat "SDWD_S" (itoa hit))))))
               (+ (caddr it) (cadr (eval (read (strcat "SDWD_S" (itoa hit))))))
               (1+ (caddr (eval (read (strcat "SDWD_S" (itoa hit))))))))
    (setq asg (cons (cons (car it) hit) asg)))
  (setq k 0)
  (while (< k nid)
    (setq hit (eval (read (strcat "SDWD_S" (itoa k)))))
    (set (read (strcat "SDWD_P" (itoa k))) (list (/ (car hit) (caddr hit)) (/ (cadr hit) (caddr hit))))
    (set (read (strcat "SDWD_S" (itoa k))) nil)
    (setq k (1+ k)))
  (foreach a (sd:sort asg '(lambda (x y) (< (car x) (car y))))
    (setq res (cons (eval (read (strcat "SDWD_P" (itoa (cdr a))))) res)))
  (setq k 0)
  (while (< k nid) (set (read (strcat "SDWD_P" (itoa k))) nil) (setq k (1+ k)))
  (reverse res))

(defun sd:wd-cell (x y cs) (strcat "SDWD_G" (itoa (fix (sd:floor (/ x cs)))) "_" (itoa (fix (sd:floor (/ y cs))))))
(defun sd:floor (x) (if (and (< x 0.0) (/= x (fix x))) (1- (fix x)) (fix x)))

;; Cac nut nam trong thanh tren canh a-b (khong tinh a, b): ((t x y) ...) da sap theo t
(defun sd:wd-onedge (a b tol cs / x0 x1 y0 y1 ix iy r c pr)
  (setq x0 (- (min (car a) (car b)) tol) x1 (+ (max (car a) (car b)) tol)
        y0 (- (min (cadr a) (cadr b)) tol) y1 (+ (max (cadr a) (cadr b)) tol)
        ix (sd:floor (/ x0 cs)))
  (while (<= ix (sd:floor (/ x1 cs)))
    (setq iy (sd:floor (/ y0 cs)))
    (while (<= iy (sd:floor (/ y1 cs)))
      (foreach c (eval (read (strcat "SDWD_G" (itoa ix) "_" (itoa iy))))
        (if (and (> (distance c a) tol) (> (distance c b) tol))
          (progn (setq pr (sd:dm-proj c a b))
                 (if (and (> (car pr) 0.0) (< (car pr) 1.0) (<= (cdr pr) tol))
                     (setq r (cons (list (car pr) (car c) (cadr c)) r))))))
      (setq iy (1+ iy)))
    (setq ix (1+ ix)))
  (sd:sort r '(lambda (p q) (< (car p) (car q)))))

(defun c:SDHANDINH (/ ss i e ed sp recs allp cn k tol tdinh nodes keys cs cell nweld nins nfail nent new vs nv res dn nxt v2 ons a b c1 cnt)
  (sd:begin)
  (if (sd:dlg "Han dinh polyline (SDHANDINH)"
              (list (list "note" "Gop cac dinh sinh ra tu cung 1 diem giao cat ve 1 toa do, chen dinh nut chu T vao canh ke ben" 'note nil)
                    (list "tol" "Dung sai han dinh (mm)" 'real (sd:cfg "WD-TOL" 0.5))
                    (list "tdinh" "Chen dinh vao canh polyline ke ben (nut chu T)" 'tog t)))
    (progn
      (setq tol (sd:cfg-put "WD-TOL" (sd:v "tol")) tdinh (sd:v "tdinh") cs 500.0)
      (princ "\nQuet chon polyline can han dinh <Enter = tat ca polyline tren ban ve>: ")
      (if (not (setq ss (ssget '((0 . "LWPOLYLINE")))))
        (setq ss (ssget "_X" '((0 . "LWPOLYLINE") (410 . "Model")))))
      (if (null ss)
        (princ "\n[SD] Khong co polyline.")
        (progn
          ;; doc tat ca polyline
          (setq i 0)
          (repeat (sslength ss)
            (setq e (ssname ss i) ed (entget e) sp (sd:wd-split ed) i (1+ i))
            (setq recs (cons (cons e sp) recs)))
          (setq recs (reverse recs) allp nil)
          (foreach r recs (foreach v (cadr (cdr r)) (setq allp (cons (car v) allp))))
          (setq allp (reverse allp) cn (sd:wd-cluster allp tol))
          ;; gan toa do nut moi cho tung dinh, dem so dinh bi doi
          (setq nweld 0 nodes nil)
          (setq new nil)
          (foreach r recs
            (setq vs nil)
            (foreach v (cadr (cdr r))
              (setq c1 (car cn) cn (cdr cn))
              (if (> (distance c1 (car v)) 1e-9) (setq nweld (1+ nweld)))
              (setq vs (cons (cons c1 (cdr v)) vs)))
            (setq new (cons (list (car r) (cadr r) (reverse vs) (cadddr r)) new)
                  nodes (append (mapcar 'car vs) nodes)))
          (setq new (reverse new))
          ;; luoi o de tra nut tren canh
          (setq keys nil nins 0)
          (if tdinh
            (progn
              (foreach c nodes
                (setq cell (sd:wd-cell (car c) (cadr c) cs))
                (if (not (member cell keys)) (setq keys (cons cell keys)))
                (set (read cell) (if (member c (eval (read cell))) (eval (read cell)) (cons c (eval (read cell))))))
              (setq new
                (mapcar
                  '(lambda (r / vs n k out a b ons own)
                     (setq vs (nth 2 r) n (length vs) k 0 out nil own (mapcar 'car vs))
                     (while (< k n)
                       (setq a (nth k vs) out (cons a out))
                       (if (or (< k (1- n)) (= 1 (logand 1 (cond ((cdr (assoc 70 (nth 1 r)))) (0)))))
                         (progn
                           (setq b (nth (rem (1+ k) n) vs))
                           (if (and (< (abs (cond ((cdr (assoc 42 (cdr a)))) (0.0))) 1e-9) (> (distance (car a) (car b)) 1e-9))
                             (foreach o (sd:wd-onedge (car a) (car b) tol cs)
                               (if (not (member (cdr o) own))
                                 (setq out (cons (list (cdr o)) out) nins (1+ nins)))))))
                       (setq k (1+ k)))
                     (list (car r) (nth 1 r) (reverse out) (nth 3 r)))
                  new))
              (foreach cell keys (set (read cell) nil))))
          ;; ghi lai
          (setq nent 0 nfail 0)
          (foreach r new
            (setq res (sd:wd-join (nth 1 r) (nth 2 r) (nth 3 r)))
            (if (not (equal res (entget (car r))))
              (if (vl-catch-all-error-p (vl-catch-all-apply 'entmod (list res)))
                (setq nfail (1+ nfail))
                (setq nent (1+ nent)))))
          (princ (strcat "\n[SD] SDHANDINH: " (itoa (length recs)) " polyline, da han " (itoa nweld) " dinh lech toa do, chen " (itoa nins)
                         " dinh nut T, sua " (itoa nent) " polyline" (if (> nfail 0) (strcat ", " (itoa nfail) " polyline khong sua duoc (layer khoa?)") "") "."))))))
  (sd:finish))

(defun c:SDDOCDA (/ che)
  (sd:begin)
  (if (sd:dlg "Doc mat bang op lat da (SDDOCDA)"
              (list (list "che" "Che do" 'kw (cond (*SD:DMCHE*) ("Doc"))
                          '(("Doc" . "Doc mat bang -> dung o kin -> ghi bang CSV de soat") ("Ve" . "Ve polyline kin tu bang CSV da soat")
                            ("Kiem" . "Kiem tra mat bang: khoanh do cho ho, dau mut treo, o khac thuong")))
                    (list "nguon" "Nguon net mat bang" 'kw (cond (*SD:DMNG*) ("Chon"))
                          '(("Chon" . "Quet chon tren ban ve") ("Layer" . "Tat ca net tren 1 layer"))
                          '("che" "Doc" "Kiem"))
                    (list "lay" "Ten layer chua net op lat" 'str (cond (*SD:DMLAY*) ("0")) nil '("nguon" "Layer"))
                    (list "layerx" "Bo qua cac layer (VD *STAIR*,*THANG*,*MUI*; cach nhau dau phay; trong = khong bo)" 'str (sd:cfg "LAYERX" "") nil '("che" "Doc" "Kiem"))
                    (list "ne" "Ne cac vung kin (mat cat mui bac, chi tiet): khong ve o, khong hatch" 'kw (cond (*SD:DMNEM*) ("Khong"))
                          '(("Khong" . "Khong ne") ("Layer" . "Ne cac polyline kin tren 1 layer") ("Chon" . "Chon cac polyline kin tren man hinh khi chay"))
                          '("che" "Doc"))
                    (list "layern" "Layer chua cac vung kin can ne" 'str (cond (*SD:DMNEL*) ("")) nil '("ne" "Layer"))
                    (list "tol" "Dung sai noi dau mut / ho (mm)" 'real (cond (*SD:DMTOL*) (5.0)) nil '("che" "Doc" "Kiem"))
                    (list "amin" "Bo o nho hon (m2)" 'real0 (cond (*SD:DMAMIN*) (0.01)) nil '("che" "Doc" "Kiem"))
                    (list "mng" "Lay ma vat lieu cua o tu" 'kw (cond (*SD:DMMNG*) ("Khong"))
                          '(("Khong" . "Khong lay (tu nhap cot mavl trong bang)") ("Chu" . "Chu (TEXT / MTEXT) nam trong o, vd D1, G2") ("Hatch" . "Hatch trong o (ten pattern / mau / layer)"))
                          '("che" "Doc"))
                    (list "lochu" "Chi nhan ma bat dau bang (vd D,G; trong = moi chu)" 'str (cond (*SD:DMLOC*) ("")) nil '("mng" "Chu"))
                    (list "lo" "Khoet lo / cot ben trong o (tach vien lom chu U / L)" 'tog t nil '("che" "Doc"))
                    (list "json" "Xuat them file JSON (cho AI ngoai doc / dien bang)" 'tog nil nil '("che" "Doc"))
                    (list "ve" "Ve luon polyline kin (bo qua buoc soat bang)" 'tog nil nil '("che" "Doc"))
                    (list "dn" "Danh so T1, T2... tren ban ve" 'tog t nil '("che" "Doc" "Ve"))
                    (list "mat0" "Ma VL mac dinh cho o chua co ma (trong = khong gan SD_TILE)" 'str (cond (*SD:DMMV0*) ("")) nil '("che" "Doc" "Ve"))
                    (list "ten" "Ten vat lieu (cho bang thong ke / gia cong)" 'str (cond (*SD:DMTEN*) ("")) nil '("che" "Doc" "Ve"))
                    (list "thk" "Chieu day da (mm)" 'real (cond (*SD:DMTHK*) (20.0)) nil '("che" "Doc" "Ve"))
                    (list "anh" "Chay SDANHDA ngay tren cac polyline (can ve luon / che do Ve)" 'tog nil nil '("che" "Doc" "Ve"))))
    (progn
      (setq che (sd:v "che") *SD:DMCHE* che *SD:DMLAYX* (sd:cfg-put "LAYERX" (cond ((sd:v "layerx")) ("")))
            *SD:DMNEM* (cond ((sd:v "ne")) ("Khong")) *SD:DMNEL* (cond ((sd:v "layern")) ("")))
      (cond
        ((= che "Ve")
         (setq *SD:DMMV0* (sd:v "mat0") *SD:DMTEN* (sd:v "ten") *SD:DMTHK* (sd:v "thk"))
         (sd:dm-ve (sd:v "dn") (sd:v "anh") (sd:v "mat0") (sd:v "ten") (sd:v "thk")))
        (t
         (setq *SD:DMNG* (sd:v "nguon") *SD:DMLAY* (sd:v "lay") *SD:DMTOL* (sd:v "tol") *SD:DMAMIN* (sd:v "amin"))
         (if (= che "Kiem")
           (sd:dm-kiem (sd:v "nguon") (sd:v "lay") (sd:v "tol") (sd:v "amin"))
           (progn
             (setq *SD:DMMNG* (sd:v "mng") *SD:DMLOC* (sd:v "lochu") *SD:DMMV0* (sd:v "mat0") *SD:DMTEN* (sd:v "ten") *SD:DMTHK* (sd:v "thk"))
             (sd:dm-doc (sd:v "nguon") (sd:v "lay") (sd:v "tol") (sd:v "amin") (sd:v "ve") (sd:v "dn") (sd:v "anh")
                        (sd:v "mng") (sd:v "lochu") (sd:v "mat0") (sd:v "ten") (sd:v "thk") (sd:v "lo") (sd:v "json"))))))))
  (sd:finish))

;;; --------------------------------------------------------------------------
;;;  DANH MUC LENH - nguon duy nhat cho SDHELP, SDPANEL, menu, toolbar, icon
;;;  (nhom  lenh  mo-ta  chu-tren-icon  lenh-tat)   [build.py doc danh sach nay de sinh menu]
;;; --------------------------------------------------------------------------
(setq *SD:CMDS*
  '(("Thiet lap va ban ve" "SDSET" "Thiet lap ty le, layer, text style, dimstyle" "SET" "TYLE")
    ("Thiet lap va ban ve" "SDKHUNG" "Khung ban ve A0-A4 + khung ten" "KT" "KHG")
    ("Thiet lap va ban ve" "SDTRUC" "Luoi truc + bong truc + kich thuoc" "TRUC" "TRUC")
    ("Thiet lap va ban ve" "SDCAODO" "Ky hieu cao do" "CD" "CAO")
    ("Thiet lap va ban ve" "SDMC" "Ky hieu mat cat" "MC" "MCT")
    ("Thiet lap va ban ve" "SDSO" "Danh so tu dong" "123" "DSO")
    ("Thiet lap va ban ve" "SDLEN" "Tong chieu dai doi tuong theo layer" "SUM" "TDAI")
    ("Thiet lap va ban ve" "SDDIENTICH" "Dem + tong dien tich theo layer (polyline, tron, hatch...), nhan FIELD" "AREA" "TDT")
    ("Thiet lap va ban ve" "SDCHUGIUA" "Tao / can chu 1 dong giua 2 diem, xoay theo 2 diem" "TXT" "CGI")
    ("Thiet lap va ban ve" "SDDIMTAY" "Kich thuoc ghi tay: to mau, khoi phuc gia tri do, xoa" "DIM" "DMT")
    ("Thiet lap va ban ve" "SDTHUTU" "Thu tu ve (draworder) theo layer" "ORD" "TTL")
    ("Thiet lap va ban ve" "SDREV" "Ky hieu lan sua doi + dam may" "REV" "SUA")
    ("Thiet lap va ban ve" "SDCHUAN" "Chuan layer / style / dimstyle: kiem tra, ap dung, xuat file mau .dwt" "STD" "CHN")
    ("Thiet lap va ban ve" "SDTKBLOCK" "Thong ke block dong + thuoc tinh (bang, CSV), gan gia tri hang loat" "BLK" "TKB")
    ("Thiet lap va ban ve" "SDXREF" "Quan ly Xref: trang thai, duong dan tuong doi, tim lai, nap lai" "XR" "XRF")
    ("Thiet lap va ban ve" "SDDMBV" "Danh muc ban ve (Sheet List) tu Layout / khung ten + CSV" "DM" "DMB")
    ("Thiet lap va ban ve" "SDLOC" "Loc / tim doi tuong theo bieu thuc: layer, thuoc tinh, tham so, du lieu SD, VA / HOAC" "FLT" "LOC")
    ("BTCT va ket cau thep" "SDDAM" "Mat cat dam BTCT" "DAM" "MCD")
    ("BTCT va ket cau thep" "SDCOT" "Mat cat cot BTCT" "COT" "MCC")
    ("BTCT va ket cau thep" "SDNOITHEP" "Toi uu cat noi thep trong vung cho phep noi, so le, coupler" "NOI" "CNT")
    ("BTCT va ket cau thep" "SDTHEPSET" "Cai dat thep: cay, be tong, noi chong, moc" "TS" "CDT")
    ("BTCT va ket cau thep" "SDTHEP" "Ghi chu thanh thep: hinh dang, noi chong" "THEP" "THP")
    ("BTCT va ket cau thep" "SDTHEPTM" "Thep thong minh tu polyline: tu cap nhat L, SL, bang" "TM" "TTM")
    ("BTCT va ket cau thep" "SDTKTHEP" "Bang thong ke cot thep + CSV" "TKT" "TKT")
    ("BTCT va ket cau thep" "SDBONGTHEP" "Danh lai so hieu thep dong bo + kiem tra trung / lech so hieu" "SH" "DSH")
    ("BTCT va ket cau thep" "SDTOIUU" "Toi uu cat thep tu cay thuong pham" "OPT" "TUT")
    ("BTCT va ket cau thep" "SDBANMA" "Ban ma / ban de co lo bulong" "BM" "BMA")
    ("BTCT va ket cau thep" "SDIH" "Tiet dien thep hinh I/H" "IH" "THH")
    ("Khai trien BTCT" "SDMONGTHEP" "Khai trien thep mong don: mat bang + 2 mat cat" "KTM" "KTM")
    ("Khai trien BTCT" "SDMONGBANG" "Khai trien thep mong bang (ban + suon), mat bang + mat cat" "KMB" "KMB")
    ("Khai trien BTCT" "SDDAICOC" "Khai trien thep dai coc: luoi coc, luoi thep, thep cho" "KDC" "KDC")
    ("Khai trien BTCT" "SDCOTTHEP" "Khai trien thep cot 1 tang: mat dung + mat cat" "KTC" "KTC")
    ("Khai trien BTCT" "SDDAMDUNG" "Mat dung thep dam lien tuc: thep suot, mu goi, dai L/4" "MDD" "MDD")
    ("Khai trien BTCT" "SDSANTHEP" "Khai trien thep o san: thep duoi 2 phuong, thep mu" "KTS" "KTS")
    ("Khai trien BTCT" "SDTHANGTHEP" "Khai trien thep ve cau thang (mat cat)" "KTT" "KTT")
    ("Khai trien BTCT" "SDNHAPBANG" "Nhap bang cau kien CSV / Excel -> ve khai trien hang loat (dam, cot, mong, san, thang)" "BANG" "NBG")
    ("Khai trien BTCT" "SDCK" "Khai bao khoi luong cau kien (kich thuoc / polyline)" "CK" "CKL")
    ("Khai trien BTCT" "SDKL" "Xuat khoi luong be tong, van khuon, thep sang Excel" "XLS" "KLX")
    ("Op lat da granite / gach" "SDGACH" "Chia vien: thang/so le/xuong ca/chevron, vien, khe" "GACH" "CHV")
    ("Op lat da granite / gach" "SDCHANTUONG" "Len chan tuong + trien khai mat dung" "LEN" "LCT")
    ("Op lat da granite / gach" "SDRAITAM" "Rai panel / da lat theo kho: tam lon tu goc, tam di hinh mep bien, go bu, huong van" "RAI" "RTA")
    ("Op lat da granite / gach" "SDVANDA" "Hatch van da (file .pat) len vien: tiep noi / doi guong / xoay 4 chieu" "VAN" "VDA")
    ("Thiet lap va ban ve" "SDKIEMTRA" "Tac tu kiem tra ban ve: thep, mat bang, chuan, dim ghi tay, Xref; xep uu tien + goi y lenh" "AGT" "KTA")
    ("Op lat da granite / gach" "SDQUYTRINH" "Hop thoai quy trinh da lat: goi y buoc tiep theo, chay tung buoc hoac lien hoan" "QT" "QTR")
    ("Op lat da granite / gach" "SDDOCDA" "Doc mat bang op lat: dung lai o kin tu net roi, ghi bang CSV de soat / bo sung, ve polyline kin, chay SDANHDA" "DOC" "DOD")
    ("Op lat da granite / gach" "SDMOANH" "Mo bien anh da: bien vien moi vuot anh nhung tam con du kho thi tu dich anh va cat lai" "MOB" "MOA")
    ("Op lat da granite / gach" "SDRON" "Doi ron giua cac vien: thu phong polyline vien, cap nhat hatch lien ket va cat lai anh, khong sua tay" "RON" "DRN")
    ("Op lat da granite / gach" "SDVAN" "Kiem tra van da lien tuc giua cac vien ke nhau (dua vao vi tri cat tren tam), khoanh moi noi dut van" "VKT" "LTV")
    ("Op lat da granite / gach" "SDKTLAT" "Kiem tra ban ve lat: vien cat hep / nho, ron khong deu, o thieu ma vat lieu" "KTL" "KLT")
    ("Op lat da granite / gach" "SDDIEMBD" "So sanh diem bat dau rai luoi vien: so vien cat, vien cat hep, hao hut; goi y diem tot nhat" "DBD" "DBT")
    ("Op lat da granite / gach" "SDKHEGIAN" "Khe co gian: khe sat tuong va khe phan vung vung lat, chong chiu dai toi da giua cac khe" "KGN" "KCG")
    ("Op lat da granite / gach" "SDTHOATNUOC" "Pheu thu nuoc + doc san: chenh cao den cac goc, khoanh vung vien cat quanh pheu" "TNG" "PTN")
    ("Op lat da granite / gach" "SDTUDONG" "Bat / tat tu dong: sua bien vien (grip, stretch...) thi anh IMAGECLIP tu cat lai theo bien moi" "TDG" "TDO")
    ("Op lat da granite / gach" "SDLOT" "Chay lo nhieu phong: rai vien cho tung khu vuc, diem bat dau tot nhat, thong ke tung vung + tong, tuy chon cat anh / hatch" "LOT" "NPH")
    ("Op lat da granite / gach" "SDRONIN" "Cho ron / duong vien hien ra khi in: doi mau trang + net, dua duong vien len tren anh" "RIN" "IRN")
    ("Op lat da granite / gach" "SDVATLIEU" "Danh sach vat lieu da dung (ma, kich thuoc, ron, khe): xem va xoa muc; SDGACH / SDLOT hien danh sach de chon lai nhanh" "VLD" "VLI")
    ("Op lat da granite / gach" "SDXOAVIEN" "Go bo vien trong vung chon: xoa polyline vien + anh + hatch + so hieu, lo ra chi tiet nam duoi (mat cat mui bac)" "XOV" "GOV")
    ("Op lat da granite / gach" "SDANHDA" "Cat anh tam da (imageclip) vao cac vien da quet chon: chieu van, xep it hao" "ANH" "ADA")
    ("Op lat da granite / gach" "SDTKDA" "Quet polyline vien da cat: bang thong ke theo nhom kich thuoc, chi tiet tung vien, CSV" "TKD" "TKD")
    ("Op lat da granite / gach" "SDDOCDATK" "Thong ke vien da sau SDDOCDA: bang nhom kich thuoc, dat tam da, CSV" "DTK" "DTK")
    ("Op lat da granite / gach" "SDANHDATK" "Thong ke tam da sau SDANHDA: so vien, hao hut tung tam, dat tam, CSV" "ATK" "ATK")
    ("Op lat da granite / gach" "SDGACHTK" "Thong ke vien + du tru dat hang" "TKV" "TKV")
    ("Op lat da granite / gach" "SDKHODA" "Kho da tho nhieu kich thuoc" "KHO" "KHO")
    ("Op lat da granite / gach" "SDDATHO" "Cat vien tu da tho: so do cat, hieu suat" "SLAB" "DTH")
    ("Op lat da granite / gach" "SDTHANGDA" "Cau thang da: mat bac, co bac, mui bac (thang / vat 45 / roi / CNC), khe LED, len, ra da kieu ABF" "THD" "TDA")
    ("Op lat da granite / gach" "SDGIACONG" "Ban ve gia cong tung ma vien" "GC" "GCV")
    ("Op lat da granite / gach" "SDLOP" "Chi tiet cau tao lop op / lat" "LOP" "CTL")
    ("Coffa" "SDCOFFASET" "Thong so coffa, ap luc be tong" "CFS" "CFT")
    ("Coffa" "SDCOFFAMONG" "Coffa mong don / mong bang / dai coc" "MONG" "CFM")
    ("Coffa" "SDCOFFACOT" "Coffa cot" "CFC" "CFC")
    ("Coffa" "SDCOFFAVACH" "Coffa vach / vach ham" "VACH" "CFV")
    ("Coffa" "SDCOFFATM" "Coffa loi thang may" "TM" "CTM")
    ("Coffa" "SDCOFFATHANG" "Coffa thang bo" "TB" "CTB")
    ("Coffa" "SDCOFFADAM" "Coffa dam + giao duoi dam" "CFD" "CFD")
    ("Coffa" "SDCOFFASAN" "Coffa san + gian giao + giang" "SAN" "CFS")
    ("Coffa" "SDNHOMSET" "Coffa nhom: catalogue tam (W, IC, EC, SC, tam san, dam do, chong)" "ALS" "NHS")
    ("Coffa" "SDNHOMVACH" "Coffa nhom vach / cot / loi: chia tam theo mat be tong chon" "ALV" "NHV")
    ("Coffa" "SDNHOMSAN" "Coffa nhom san: goc san, dam do san, dau chong, tam san" "ALF" "NHN")
    ("Coffa" "SDNHOMDAM" "Coffa nhom dam: thanh, day, goc ngoai, cay chong" "ALD" "NHD")
    ("Coffa" "SDNHOMKHO" "Coffa nhom: tong hop cong trinh + doi chieu kho (thieu / gia cong)" "ALK" "NHK")
    ("Gian giao" "SDGIAOSET" "Thong so gian giao, on dinh, giang" "GGS" "GGS")
    ("Gian giao" "SDGIAOTANG" "Mat bang gian giao ca tang (tu nhan dam, o san)" "GGT" "GGT")
    ("Gian giao" "SDGIAOH" "Giao khung H ca tang: dam san, giao H, giang cheo, mat cat, khoi luong" "GGH" "GKH")
    ("Gian giao" "SDGIAOTK" "Thong ke gian giao theo tang + dinh muc" "GTK" "GGK")
    ("Tien ich" "SDIN" "In hang loat theo khung ten (block / layer), hang / cot, ra may in hoac PDF" "PLT" "INH")
    ("Tien ich" "SDPURGE" "Don rac ban ve sau: DGN, RegApps, purge lap, scale list" "PRG" "DPU")
    ("Tien ich" "SDHANDINH" "Han dinh: gop dinh polyline lech nhau o cung diem giao cat, chen dinh nut chu T" "WLD" "HDI")
    ("Tien ich" "SDDIMGD" "Dim giao diem: ve 1 duong cat, tu dong dim tung doan giua cac giao diem + dim tong (co tuy chon chu dim canh duong dim)" "DGD" "DGD")
    ("Tien ich" "SDDIMPOLY" "Dim polyline kin (co cung tron): tu dong dim tung canh, chu ra ngoai cho goc hep (co tuy chon chu dim)" "DPK" "DPK")
    ("Tien ich" "SDSOSANH" "So sanh 2 ban ve DWG: to mau them / xoa / dich chuyen" "CMP" "SSD")
    ("Tien ich" "SDLAYOUT" "Quan ly Layout: mo, sap xep, them, chep, doi ten (hang loat), xoa" "LO" "QLL")
    ("Tien ich" "SDTAOLAYOUT" "Tao Layout hang loat tu khung ten + danh so to vao khung ten" "LAY" "TLO")
    ("Tien ich" "SDNHANLK" "Nhan lien ket doi tuong (chieu dai / dien tich) tu cap nhat bang FIELD" "FLD" "NLK")
    ("Tien ich" "SDLIENKET" "Kiem tra mat bang <-> khai trien: cau kien thieu / thua" "LNK" "LKT")
    ("Tien ich" "SDCDE" "Phat hanh len CDE theo ISO 19650: ma so hieu, trang thai, phien ban, luu tru" "CDE" "CDE")
    ("Tien ich" "SDPANEL" "Bang lenh ShopDrawing (hop thoai)" "ALL" "BLN")
    ("Tien ich" "SDHELP" "Danh sach lenh" "HLP" "HDL")
    ("Op lat da granite / gach" "SDBLOCKDA" "Block chi tiet da: tao block mat cat mui bac tu mau, quet hinh tao block, chen file .dwg, luu ra .dwg, mo Block Editor them thong so dong" "BCD" "KCD")
    ("Op lat da granite / gach" "SDTRINH" "Ban trinh khach: bang chu thich vat lieu co o mau anh da (A1 1:50) va che do trinh khach lam mo nen kien truc, an layer nhan" "TRK" "BTK")
    ("Op lat da granite / gach" "SDKHUNGIN" "Khung in A1 / A3 tu dung: khung ten, huong Bac, thuoc ty le, dat san cai dat in cho SDIN / SDTAOLAYOUT" "KHI" "KIN")
    ("Op lat da granite / gach" "SDKHAOSAT" "Dung phong tu file so do khao sat (room,ab,bc,cd,da,ac,bd): 4 canh + cheo, xep hang tin cay A / B / C / X / D, ve polyline phong lam bien cho SDGACH / SDLOT" "KSA" "KSH")
    ("Op lat da granite / gach" "SDCHIABAC" "Chia bac thang tu cao do (so voi +-0.000): chieu cao bac, lam tron don phan lech, bang cao do hoan thien / ket cau tung bac va chieu nghi, dat san SDTHANGDA" "CBA" "CHB")
    ("Op lat da granite / gach" "SDMAVIEN" "Ma vien theo hinh dang: cung vat lieu va hinh dang cung ma (VD G1-01), nho trong ban ve, ghi len vien, bang + CSV" "MVI" "SMV")
    ("Op lat da granite / gach" "SDKIEMTONG" "Luot kiem tong: ho so so lieu, vien hep / nho, ron khong deu, luoi ron lech, chuoi cao do; bao cao + CSV" "KTG" "KTO")
    ("Op lat da granite / gach" "SDHOSO" "Ho so so lieu du an: ron, cao do, doc, du...; danh dau da xac nhan / chua xac nhan, canh bao khi lenh dung so chua xac nhan, bang ra ban ve" "HSO" "SLD")
    ("Op lat da granite / gach" "SDDIMVIEN" "Dim tu dong theo hang vien: chuoi tung vien + tong, ngang / dung, ngoai phong hoac trong phong" "DMV" "DVI")
    ("Op lat da granite / gach" "SDOPTUONG" "Op tuong trung ron san: mat dung trai phang, ron dung theo ron san, kiem tra trung ron" "OTU" "OPTU")
    ("Op lat da granite / gach" "SDTRUNGRON" "Kiem tra luoi ron lien tuc xuyen cac phong: nhom vien lech luoi chinh, khoanh may, goi y dich" "TRG" "RLE")
    ("Op lat da granite / gach" "SDBACCAODO" "Cho doi cao do (nguong WC, mep ho, chan thanh): gan du mm, SDCATDU tu nhan" "BCO" "CDB")
    ("Op lat da granite / gach" "SDLIENCAODO" "Chuoi cao do: san chinh, san WC (ha cot, doc ve pheu thu), san ho, muc nuoc, day ho; chenh cao tung muc, canh bao, so do" "LCD" "LKD")
    ("Op lat da granite / gach" "SDHOBOI" "Ho boi: doc day dau nong - dau sau, duong dong muc day, khe co gian, mat cat doc + bang cao do day theo vien, doi chieu TCVN 4260:2012 / ISPSC 2015" "HBO" "HOB")
    ("Op lat da granite / gach" "SDMAP" "Thu vien map (anh) da granite co san: chen anh tam da dung kich thuoc that de SDANHDA cat vao vien; tha them .jpg / .png vao thu muc Maps" "MAP" "TVM")
    ("Op lat da granite / gach" "SDDICHVAN" "Dich van da tung buoc: nhich anh tam da duoi bien vien (trai / phai / len / xuong, buoc mm), bien dung yen, co hoan buoc" "DVA" "DCV")
    ("Op lat da granite / gach" "SDCATDU" "Cat du sat tuong: vien cat nao, canh nao phai cat dai ra (+du mm) de be lai khi thi cong; gach do tren ban ve, bang kich thuoc cat, CSV" "CDU" "CTD")
    ("Op lat da granite / gach" "SDDUTOAN" "Du toan tien da theo don gia m2 tung ma vat lieu (nho lai), hao hut, cong lat, VAT; bang + CSV" "DTO" "DTD")
    ("Op lat da granite / gach" "SDPHUONGAN" "Phuong an lat A / B tren mot to: nhan + bang ngan (so vien, nguyen / cat, hao hut) + khung in bao ca hai" "PAB" "PHA")
    ("Op lat da granite / gach" "SDLENH" "Ra lenh bang cau tieng Viet cho cac o da: gop o 25+36 thanh 1, xoa o 12 13 (hoi xac nhan, UNDO duoc)" "LNH" "AIA")
    ("Tien ich" "SDTUNAP" "Bat / tat tu nap ShopDrawing moi khi mo AutoCAD (khong can APPLOAD lai)" "TNP" "AUL")
    ("Tien ich" "SDMENU" "Cai menu + toolbar + Ribbon" "MNU" "CMN")
    ("Tien ich" "SDDLG" "Bat / tat hop thoai nhap lieu" "DLG" "HTN")))

;; Lenh tat: moi muc trong danh muc sinh 1 lenh ngan goi lenh chinh (vd TKT -> SDTKTHEP)
(foreach c *SD:CMDS*
  (if (nth 4 c)
    (eval (list 'defun (read (strcat "c:" (nth 4 c))) '()
                (list (read (strcat "c:" (cadr c))))))))

(defun sd:groups (/ r)
  (foreach c *SD:CMDS* (if (not (member (car c) r)) (setq r (cons (car c) r))))
  (reverse r))

;;; --------------------------------------------------------------------------
;;;  SDHELP - Danh sach lenh
;;; --------------------------------------------------------------------------
(defun sd:pad (s n) (strcat s (substr "                    " 1 (max 1 (- n (strlen s))))))

(defun c:SDHELP (/ g)
  (textscr)
  (princ (strcat "\n================ SHOPDRAWING TOOLS v" *SD:VER* " ================"
                 "\n Ty le: 1/" (itoa *SD:SCALE*) "   chi tiet: 1/" (itoa *SD:DETSCALE*)))
  (foreach c *SD:CMDS*
    (if (/= (car c) g) (progn (setq g (car c)) (princ (strcat "\n -- " g " --"))))
    (princ (strcat "\n  " (sd:pad (cadr c) 14) (sd:pad (nth 4 c) 6) (caddr c))))
  (princ "\n Cot 2 la lenh tat. Go SDPANEL (BLN) de mo bang lenh; xem them dist/HuongDanLenh.html.")
  (princ "\n================================================================")
  (princ))

;;; --------------------------------------------------------------------------
;;;  SDPANEL - Bang lenh dang hop thoai (DCL tao tu dong, chay ca ZWCAD/BricsCAD)
;;; --------------------------------------------------------------------------
(defun sd:panel-fill (g)
  (setq *SD:PCMDS* (vl-remove-if-not '(lambda (c) (= (car c) g)) *SD:CMDS*) *SD:PIDX* 0)
  (start_list "lst")
  (mapcar '(lambda (c) (add_list (strcat (sd:pad (cadr c) 14) (sd:pad (nth 4 c) 6) (caddr c)))) *SD:PCMDS*)
  (end_list)
  (set_tile "lst" "0"))

(defun c:SDPANEL (/ fn f id res cmd)
  (setq fn (vl-filename-mktemp "sdpanel" nil ".dcl"))
  (if (setq f (open fn "w"))
    (progn
      (foreach l '("sdpanel : dialog { label = \"ShopDrawing Tools\";"
                   "  : popup_list { key = \"grp\"; label = \"Nhom lenh:\"; width = 46; }"
                   "  : list_box { key = \"lst\"; height = 16; width = 72; }"
                   "  : text { label = \"Nhap dup hoac OK de chay lenh.\"; }"
                   "  ok_cancel;"
                   "}")
        (write-line l f))
      (close f)))
  (if (and (setq id (load_dialog fn)) (> id 0) (new_dialog "sdpanel" id))
    (progn
      (start_list "grp") (mapcar 'add_list (sd:groups)) (end_list)
      (sd:panel-fill (car (sd:groups)))
      (action_tile "grp" "(sd:panel-fill (nth (atoi $value) (sd:groups)))")
      (action_tile "lst" "(setq *SD:PIDX* (atoi $value)) (if (= $reason 4) (done_dialog 1))")
      (action_tile "accept" "(setq *SD:PIDX* (atoi (get_tile \"lst\"))) (done_dialog 1)")
      (setq res (start_dialog))
      (unload_dialog id)
      (vl-file-delete fn)
      (if (and (= res 1) (setq cmd (cadr (nth *SD:PIDX* *SD:PCMDS*))))
        (vla-SendCommand (sd:doc) (strcat cmd "\n"))))
    (princ "\n[SD] Khong mo duoc hop thoai."))
  (princ))

;;; --------------------------------------------------------------------------
;;;  SDTRINH - Ban trinh khach: (Chuthich) bang chu thich vat lieu co o mau anh da, ma, ten, kich thuoc, so luong, dien tich;
;;;  (Bat / Tat) che do trinh khach: lam mo nen kien truc (mau xam nhat, net manh 0,09), an cac layer nhan ky thuat, Tat tra lai nhu cu.
;;;  Kich thuoc bang tinh theo kho giay: 1 mm tren giay = tl don vi ban ve (A1 ty le 1:50 -> tl = 50).
;;; --------------------------------------------------------------------------
;; Gom cac vien theo ma vat lieu: ((ma ten w h day so-luong dien-tich-m2 anh) ...)
(defun sd:tr-collect (/ ss i e xd g rows ims)
  (setq ims (ssget "_X" '((0 . "IMAGE") (-3 ("SD_ANH")))))
  (if (setq ss (ssget "_X" '((0 . "LWPOLYLINE") (-3 ("SD_TILE")))))
    (progn
      (setq i 0)
      (repeat (sslength ss)
        (setq e (ssname ss i) i (1+ i) xd (mapcar 'cdr (cdadr (assoc -3 (entget e '("SD_TILE"))))))
        (if (and (>= (length xd) 12) (/= (nth 1 xd) "X"))
          (progn
            (if (setq g (assoc (nth 0 xd) rows))
              (setq rows (subst (list (nth 0 g) (nth 1 g) (nth 2 g) (nth 3 g) (nth 4 g) (1+ (nth 5 g)) (+ (nth 6 g) (nth 5 xd))
                                      (cond ((nth 7 g)) ((if ims (sd:im-find (sd:curve-pts e) ims)))))
                                g rows))
              (setq rows (cons (list (nth 0 xd) (nth 7 xd) (nth 8 xd) (nth 9 xd) (nth 11 xd) 1 (nth 5 xd)
                                     (if ims (sd:im-find (sd:curve-pts e) ims)))
                               rows))))))))
  (sd:sort rows '(lambda (a b) (< (car a) (car b)))))

;; O mau: ban sao anh tam da, bo clip, xoay thang truc, phong vua phu o sw x sh roi cat; ban sao khong mang SD_ANH (khong lam roi cac lenh ghep anh)
(defun sd:tr-swatch (im x0 y0 sw sh lay / o cp ce g a s p)
  (setq o (vlax-ename->vla-object im) cp (vla-Copy o) ce (vlax-vla-object->ename cp))
  (vl-catch-all-apply 'entmod (list (append (entget ce) (list (list -3 (list "SD_ANH"))))))
  (command "_.IMAGECLIP" ce "_D")
  (setq g (sd:im-geom ce) a (cadr g) p (car g))
  (vla-Rotate cp (vlax-3d-point (list (car p) (cadr p) 0.0)) (- a))
  (setq s (max (/ sw (caddr g)) (/ sh (cadddr g))))
  (vla-ScaleEntity cp (vlax-3d-point (list (car p) (cadr p) 0.0)) s)
  (vla-Move cp (vlax-3d-point (list (car p) (cadr p) 0.0)) (vlax-3d-point (list x0 y0 0.0)))
  (vla-put-Layer cp lay)
  (command "_.IMAGECLIP" ce "_N" "_P" (list x0 y0) (list (+ x0 sw) y0) (list (+ x0 sw) (+ y0 sh)) (list x0 (+ y0 sh)) ""))

;; Ve bang chu thich, goc tren trai o, tl = don vi ban ve tren 1 mm giay
(defun sd:tr-legend (rows o tl / lay cy hh rh x y n r xs hdr tot k a)
  (setq lay (sd:make-layer "SD-CHUTHICH" 7 "Continuous" 18)
        xs (list 0.0 26.0 44.0 116.0 148.0 164.0 184.0 210.0)
        hdr (list "M\\U+1EABu" "M\\U+00E3" "T\\U+00EAn v\\U+1EADt li\\U+1EC7u" "K\\U+00EDch th\\U+01B0\\U+1EDBc (mm)" "D\\U+00E0y" "SL" "Di\\U+1EC7n t\\U+00EDch (m\\U+00B2)")
        hh 8.0 rh 16.0 x (car o) y (cadr o))
  (sd:text (list x (+ y (* 3.0 tl))) "B\\U+1EA2NG CH\\U+00DA TH\\U+00CDCH V\\U+1EACT LI\\U+1EC6U" (* 5.0 tl) "L" lay)
  (setq tot (+ hh (* rh (length rows))))
  (sd:pline (list (list x y) (list (+ x (* tl 210.0)) y) (list (+ x (* tl 210.0)) (- y (* tl tot))) (list x (- y (* tl tot)))) t lay)
  (setq k 0)
  (foreach c hdr
    (sd:text (list (+ x (* tl (+ (nth k xs) 1.5))) (- y (* tl (/ hh 2.0)))) c (* 3.0 tl) "ML" lay) (setq k (1+ k)))
  (sd:line (list x (- y (* tl hh))) (list (+ x (* tl 210.0)) (- y (* tl hh))) lay)
  (foreach xc (cdr (reverse (cdr (reverse xs))))
    (sd:line (list (+ x (* tl xc)) y) (list (+ x (* tl xc)) (- y (* tl tot))) lay))
  (setq n 0 a 0.0)
  (foreach r rows
    (setq cy (- y (* tl (+ hh (* rh n)))) n (1+ n))
    (sd:line (list x (- cy (* tl rh))) (list (+ x (* tl 210.0)) (- cy (* tl rh))) lay)
    ;; o mau
    (if (and (nth 7 r) (vl-catch-all-error-p
                          (vl-catch-all-apply 'sd:tr-swatch (list (nth 7 r) (+ x (* tl 2.0)) (- cy (* tl (+ rh -1.0))) (* tl 22.0) (* tl 14.0) lay))))
      (sd:text (list (+ x (* tl 3.0)) (- cy (* tl (/ rh 2.0)))) "(l\\U+1ED7i \\U+1EA3nh)" (* 2.5 tl) "ML" lay))
    (if (null (nth 7 r))
      (sd:text (list (+ x (* tl 3.0)) (- cy (* tl (/ rh 2.0)))) "(kh\\U+00F4ng \\U+1EA3nh)" (* 2.5 tl) "ML" lay)
      (sd:pline (list (list (+ x (* tl 2.0)) (- cy (* tl (+ rh -1.0)))) (list (+ x (* tl 24.0)) (- cy (* tl (+ rh -1.0))))
                      (list (+ x (* tl 24.0)) (- cy (* tl 1.0))) (list (+ x (* tl 2.0)) (- cy (* tl 1.0)))) t lay))
    (setq k 1)
    (foreach v (list (nth 0 r) (nth 1 r) (strcat (sd:num (nth 2 r)) " x " (sd:num (nth 3 r))) (sd:num (nth 4 r)) (itoa (nth 5 r)) (sd:rtos (nth 6 r) 2))
      (sd:text (list (+ x (* tl (+ (nth k xs) 1.5))) (- cy (* tl (/ rh 2.0)))) v (* 3.0 tl) "ML" lay) (setq k (1+ k)))
    (setq a (+ a (nth 6 r))))
  (sd:text (list (+ x (* tl 186.0)) (- y (* tl (+ tot 5.0)))) (strcat "T\\U+1ED5ng: " (sd:rtos a 2) " m\\U+00B2") (* 3.5 tl) "L" lay)
  (length rows))

;; Che do trinh khach: lam mo nen, an layer nhan; nho mau / net / bat-tat cu de Tat tra lai
(defun sd:tr-on (hide fade / lays old nm l hs)
  (if (vlax-ldata-get "SD" "TRINH-OLD")
    (princ "\n[SD] Che do trinh khach dang bat (g\\U+00F5 Tat de tra lai).")
    (progn
      (setq lays (vla-get-Layers (sd:doc)) hs (mapcar 'strcase (sd:split hide ",")))
      (vlax-for l lays
        (setq nm (vla-get-Name l))
        (if (and (not (wcmatch (strcase nm) "SD-*,0,DEFPOINTS,*|*")) (or fade (member (strcase nm) hs)))
          (progn (setq old (cons (list nm (vla-get-Color l) (vla-get-Lineweight l) (if (= (vla-get-LayerOn l) :vlax-true) 1 0)) old))
                 (vl-catch-all-apply '(lambda () (vla-put-Color l 253) (vla-put-Lineweight l 9)) nil)))
        (if (member (strcase nm) hs)
          (progn (if (not (assoc nm old)) (setq old (cons (list nm (vla-get-Color l) (vla-get-Lineweight l) (if (= (vla-get-LayerOn l) :vlax-true) 1 0)) old)))
                 (vl-catch-all-apply 'vla-put-LayerOn (list l :vlax-false)))))
      (vlax-ldata-put "SD" "TRINH-OLD" (cond (old) ((list (list "" 7 -3 1)))))
      (command "_.REGENALL")
      (princ (strcat "\n[SD] Che do trinh khach: lam mo " (itoa (length old)) " layer nen / an. G\\U+00F5 SDTRINH > Tat de tra lai.")))))

(defun sd:tr-off (/ old l)
  (if (setq old (vlax-ldata-get "SD" "TRINH-OLD"))
    (progn
      (foreach o old
        (if (and (/= (car o) "") (tblsearch "LAYER" (car o)))
          (vl-catch-all-apply '(lambda ()
            (setq l (vla-Item (vla-get-Layers (sd:doc)) (car o)))
            (vla-put-Color l (cadr o)) (vla-put-Lineweight l (caddr o)) (vla-put-LayerOn l (if (= (cadddr o) 1) :vlax-true :vlax-false))) nil)))
      (vlax-ldata-delete "SD" "TRINH-OLD")
      (command "_.REGENALL")
      (princ "\n[SD] Da tra lai mau, net va layer nhu cu."))
    (princ "\n[SD] Che do trinh khach chua bat.")))

(defun c:SDTRINH (/ mode rows pt tl)
  (sd:begin)
  (if (sd:dlg "B\\U+1EA3n tr\\U+00ECnh kh\\U+00E1ch (SDTRINH)"
              (list (list "mode" "Vi\\U+1EC7c c\\U+1EA7n l\\U+00E0m" 'kw (sd:cfg "TRINH-MODE" "Chuthich")
                          '(("Chuthich" . "V\\U+1EBD b\\U+1EA3ng ch\\U+00FA th\\U+00EDch v\\U+1EADt li\\U+1EC7u (\\U+00F4 m\\U+1EABu \\U+1EA3nh \\U+0111\\U+00E1)") ("Bat" . "B\\U+1EADt ch\\U+1EBF \\U+0111\\U+1ED9 tr\\U+00ECnh kh\\U+00E1ch") ("Tat" . "T\\U+1EAFt, tr\\U+1EA3 l\\U+1EA1i nh\\U+01B0 c\\U+0169")))
                    (list "tl" "\\U+0110\\U+01A1n v\\U+1ECB b\\U+1EA3n v\\U+1EBD tr\\U+00EAn 1 mm gi\\U+1EA5y (A1 t\\U+1EF7 l\\U+1EC7 1:50 = 50)" 'real (sd:cfg "TRINH-TL" 50.0) nil '("mode" "Chuthich"))
                    (list "an" "Layer \\U+1EA9n khi tr\\U+00ECnh kh\\U+00E1ch (c\\U+00E1ch nhau d\\U+1EA5u ph\\U+1EA9y)" 'str (sd:cfg "TRINH-AN" "SD-CHU") nil '("mode" "Bat"))
                    (list "mo" "L\\U+00E0m m\\U+1EDD c\\U+00E1c layer n\\U+1EC1n ki\\U+1EBFn tr\\U+00FAc (x\\U+00E1m nh\\U+1EA1t, n\\U+00E9t 0,09)" 'tog t nil '("mode" "Bat"))))
    (progn
      (setq mode (sd:cfg-put "TRINH-MODE" (sd:v "mode")))
      (cond
        ((= mode "Chuthich")
         (setq tl (sd:cfg-put "TRINH-TL" (sd:v "tl")) rows (sd:tr-collect))
         (if (null rows)
           (princ "\n[SD] Chua co vien da (SD_TILE) nao: chay SDGACH / SDDOCDA truoc.")
           (if (setq pt (sd:getpt "\nDiem goc tren trai bang chu thich: " nil))
             (princ (strcat "\n[SD] Da ve bang chu thich " (itoa (sd:tr-legend rows (sd:2d pt) tl)) " vat lieu (khung giay 1 mm = " (sd:num tl) " don vi)")))))
        ((= mode "Bat") (sd:tr-on (sd:cfg-put "TRINH-AN" (cond ((sd:v "an")) (""))) (sd:v "mo")))
        (t (sd:tr-off)))))
  (sd:finish))

;;; --------------------------------------------------------------------------
;;;  SDKHUNGIN - Khung in tu dung: to giay A1 / A3 (A2, A4) o ty le 1:N: khung to (layer SD-KHUNGIN, khong in) lam khung cho SDTAOLAYOUT / SDIN,
;;;  vien trong, khung ten (du an, hang muc, ten ban ve, ty le, ngay, so to), mui ten huong Bac, thuoc ty le; dat san cai dat in
;;;  (SDIN / SDTAOLAYOUT: khung = layer SD-KHUNGIN, net in acad.ctb, vua kho giay, chinh giua; khong in khung anh)
;;;  SDPHUONGAN - Hai phuong an lat A / B tren mot to: nhan phuong an + bang ngan (so vien, nguyen / cat, vien cat hep, hao hut uoc tinh) + khung in bao ca hai
;;; --------------------------------------------------------------------------
(defun sd:khi-paper (kho)
  (cond ((= kho "A1") (list 841.0 594.0)) ((= kho "A2") (list 594.0 420.0)) ((= kho "A4") (list 297.0 210.0)) (t (list 420.0 297.0))))

(defun sd:khi-date (/ d)
  (setq d (rtos (getvar "CDATE") 2 6))
  (strcat (substr d 7 2) "/" (substr d 5 2) "/" (substr d 1 4)))

(defun sd:khi-solid (a b c d lay)
  (entmake (list '(0 . "SOLID") (cons 8 lay) (cons 10 a) (cons 11 b) (cons 12 d) (cons 13 c))))

;; Ve to giay tai goc trai duoi (ox oy): kich thuoc mm giay x k don vi ban ve. Tra ve (w h) don vi ban ve
;; So hieu ban ve: ma-du-an.ma-nha-thau.loai.so (so 2 chu so, tu tang moi lan ve khung neu bat)
(defun sd:khi-num2 (n) (if (< n 10) (strcat "0" (itoa n)) (itoa n)))
(defun sd:khi-sohieu (/ a)
  (setq a (list (sd:cfg "KHI-MADA" "") (sd:cfg "KHI-MANT" "") (sd:cfg "KHI-LOAI" "SDS") (sd:khi-num2 (fix (sd:cfg "KHI-STT" 1)))))
  (sd:join (vl-remove "" a) "."))
(defun sd:khi-hasno () (or (/= (sd:cfg "KHI-MADA" "") "") (/= (sd:cfg "KHI-MANT" "") "")))
;; Cac hang them phia tren khung ten (tu duoi len): ((chu-trai [chu-phai]) ...)
(defun sd:khi-ext (/ r v)
  (if (sd:khi-hasno) (setq r (list (list (strcat "S\\U+1ED0 HI\\U+1EC6U: " (sd:khi-sohieu)) (strcat "REV." (sd:cfg "KHI-REV" "00"))))))
  (foreach kl '(("KHI-NTH" "NG\\U+01AF\\U+1EDCI TH\\U+1EF0C HI\\U+1EC6N") ("KHI-NT" "NH\\U+00C0 TH\\U+1EA6U THI C\\U+00D4NG") ("KHI-TV" "T\\U+01AF V\\U+1EA4N GI\\U+00C1M S\\U+00C1T") ("KHI-CDT" "CH\\U+1EE6 \\U+0110\\U+1EA6U T\\U+01AF"))
    (if (/= (setq v (vl-string-trim " " (sd:cfg (car kl) ""))) "")
      (setq r (append r (list (list (strcat (cadr kl) ": " v)))))))
  r)

(defun sd:khi-draw (kho k ox oy da hm ten ngay so bac thuoc / pp w h lv ll lt bx0 by0 bx1 by1 tbw tx0 cx cy st n i x e r ex ie rw yy)
  (setq pp (sd:khi-paper kho) w (car pp) h (cadr pp)
        lv (sd:make-layer "SD-KHUNGIN-VIEN" 7 "Continuous" 50)
        ll (sd:make-layer "SD-KHUNGIN-LUOI" 7 "Continuous" 25)
        lt (sd:make-layer "SD-KHUNGIN-CHU" 7 "Continuous" 18))
  ;; khung to: dung lam khung in, khong in ra giay
  (sd:make-layer "SD-KHUNGIN" 8 "Continuous" 13)
  (setq r (entget (tblobjname "LAYER" "SD-KHUNGIN")))
  (if (/= (cdr (assoc 290 r)) 0) (entmod (append (vl-remove (assoc 290 r) r) '((290 . 0)))))
  (sd:pline (list (list ox oy) (list (+ ox (* k w)) oy) (list (+ ox (* k w)) (+ oy (* k h))) (list ox (+ oy (* k h)))) t "SD-KHUNGIN")
  (setq bx0 25.0 by0 10.0 bx1 (- w 10.0) by1 (- h 10.0)
        tbw (if (> w 500.0) 180.0 150.0) tx0 (- bx1 tbw))
  (sd:pline (list (list (+ ox (* k bx0)) (+ oy (* k by0))) (list (+ ox (* k bx1)) (+ oy (* k by0)))
                  (list (+ ox (* k bx1)) (+ oy (* k by1))) (list (+ ox (* k bx0)) (+ oy (* k by1)))) t lv)
  ;; khung ten (4 hang: du an, hang muc, ten ban ve, ty le | ngay | so to)
  (sd:pline (list (list (+ ox (* k tx0)) (+ oy (* k by0))) (list (+ ox (* k bx1)) (+ oy (* k by0)))
                  (list (+ ox (* k bx1)) (+ oy (* k (+ by0 40.0)))) (list (+ ox (* k tx0)) (+ oy (* k (+ by0 40.0))))) t lv)
  (foreach dy '(10.0 20.0 30.0)
    (sd:line (list (+ ox (* k tx0)) (+ oy (* k (+ by0 dy)))) (list (+ ox (* k bx1)) (+ oy (* k (+ by0 dy)))) ll))
  (foreach fx '(0.4 0.7)
    (sd:line (list (+ ox (* k (+ tx0 (* tbw fx)))) (+ oy (* k by0))) (list (+ ox (* k (+ tx0 (* tbw fx)))) (+ oy (* k (+ by0 10.0)))) ll))
  (sd:text (list (+ ox (* k (+ tx0 2.0))) (+ oy (* k (+ by0 35.0)))) (strcat "D\\U+1EF0 \\U+00C1N: " da) (* 3.5 k) "ML" lt)
  (sd:text (list (+ ox (* k (+ tx0 2.0))) (+ oy (* k (+ by0 25.0)))) (strcat "H\\U+1EA0NG M\\U+1EE4C: " hm) (* 3.5 k) "ML" lt)
  (sd:text (list (+ ox (* k (+ tx0 2.0))) (+ oy (* k (+ by0 15.0)))) ten (* 5.0 k) "ML" lt)
  (sd:text (list (+ ox (* k (+ tx0 2.0))) (+ oy (* k (+ by0 5.0)))) (strcat "T\\U+1EF6 L\\U+1EC6 1:" (sd:num k)) (* 3.5 k) "ML" lt)
  (sd:text (list (+ ox (* k (+ tx0 (* tbw 0.4) 2.0))) (+ oy (* k (+ by0 5.0)))) (strcat "NG\\U+00C0Y " ngay) (* 3.5 k) "ML" lt)
  (sd:text (list (+ ox (* k (+ tx0 (* tbw 0.7) 2.0))) (+ oy (* k (+ by0 5.0)))) (strcat "T\\U+1EDC " so) (* 3.5 k) "ML" lt)
  ;; cac hang them: so hieu + REV, nguoi thuc hien, nha thau, tu van GS, chu dau tu (chi ve hang co noi dung)
  (setq ex (sd:khi-ext))
  (if ex
    (progn
      (sd:pline (list (list (+ ox (* k tx0)) (+ oy (* k (+ by0 40.0)))) (list (+ ox (* k bx1)) (+ oy (* k (+ by0 40.0))))
                      (list (+ ox (* k bx1)) (+ oy (* k (+ by0 40.0 (* 10.0 (length ex)))))) (list (+ ox (* k tx0)) (+ oy (* k (+ by0 40.0 (* 10.0 (length ex)))))))
                t lv)
      (setq ie 0)
      (foreach rw ex
        (setq yy (+ by0 40.0 (* 10.0 ie)))
        (if (> ie 0) (sd:line (list (+ ox (* k tx0)) (+ oy (* k yy))) (list (+ ox (* k bx1)) (+ oy (* k yy))) ll))
        (sd:text (list (+ ox (* k (+ tx0 2.0))) (+ oy (* k (+ yy 5.0)))) (car rw) (* 3.5 k) "ML" lt)
        (if (cadr rw)
          (progn
            (sd:line (list (+ ox (* k (+ tx0 (* tbw 0.7)))) (+ oy (* k yy))) (list (+ ox (* k (+ tx0 (* tbw 0.7)))) (+ oy (* k (+ yy 10.0)))) ll)
            (sd:text (list (+ ox (* k (+ tx0 (* tbw 0.7) 2.0))) (+ oy (* k (+ yy 5.0)))) (cadr rw) (* 3.5 k) "ML" lt)))
        (setq ie (1+ ie)))))
  (if (and (sd:khi-hasno) (sd:cfg "KHI-TANG" t)) (sd:cfg-put "KHI-STT" (1+ (fix (sd:cfg "KHI-STT" 1)))))
  ;; mui ten huong Bac (tren phai khung)
  (if bac
    (progn
      (setq cx (+ ox (* k (- bx1 20.0))) cy (+ oy (* k (- by1 25.0))))
      (sd:circle (list cx cy) (* 9.0 k) lv)
      (sd:pline (list (list cx (+ cy (* 13.0 k))) (list (+ cx (* 4.0 k)) (- cy (* 6.0 k))) (list cx (- cy (* 2.0 k))) (list (- cx (* 4.0 k)) (- cy (* 6.0 k)))) t lv)
      (sd:text (list cx (+ cy (* 17.0 k))) "N" (* 5.0 k) "MC" lt)))
  ;; thuoc ty le: 5 doan, moi doan st m (1 m neu ty le <= 1:60, 2 m neu <= 1:120, 5 m neu lon hon)
  (if thuoc
    (progn
      (setq st (cond ((<= k 60.0) 1.0) ((<= k 120.0) 2.0) (t 5.0)) n 5 i 0
            x (+ ox (* k (+ bx0 10.0))) cy (+ oy (* k (+ by0 8.0))))
      (sd:text (list x (+ cy (* k 7.0))) (strcat "TH\\U+01AF\\U+1EDAC T\\U+1EF6 L\\U+1EC6 1:" (sd:num k)) (* 3.0 k) "L" lt)
      (repeat n
        (setq e (* st 1000.0))
        (if (= (rem i 2) 0)
          (sd:khi-solid (list x cy) (list (+ x e) cy) (list (+ x e) (+ cy (* 2.0 k))) (list x (+ cy (* 2.0 k))) lv)
          (sd:pline (list (list x cy) (list (+ x e) cy) (list (+ x e) (+ cy (* 2.0 k))) (list x (+ cy (* 2.0 k)))) t lv))
        (sd:text (list x (- cy (* k 3.0))) (sd:num (* i st)) (* 2.5 k) "MC" lt)
        (setq x (+ x e) i (1+ i)))
      (sd:text (list x (- cy (* k 3.0))) (strcat (sd:num (* n st)) " m") (* 2.5 k) "MC" lt)))
  (list (* k w) (* k h)))

(defun sd:khi-put (al k v) (cons (cons k v) (vl-remove (assoc k al) al)))

;; dat san cai dat in cho SDIN / SDTAOLAYOUT: khung = layer SD-KHUNGIN, net in acad.ctb, vua kho giay, chinh giua
(defun sd:khi-preset (tl / a)
  (setq a (vlax-ldata-get "SD" "INHL"))
  (foreach kv (list '("mode" . "Layer") '("key" . "SD-KHUNGIN") '("ctb" . "acad.ctb") '("sc" . "Fit") (cons "center" t))
    (setq a (sd:khi-put a (car kv) (cdr kv))))
  (vlax-ldata-put "SD" "INHL" a)
  (setq a (vlax-ldata-get "SD" "TLO"))
  (foreach kv (list '("mode" . "Layer") '("key" . "SD-KHUNGIN") '("ctb" . "acad.ctb") (cons "sc" (fix tl)))
    (setq a (sd:khi-put a (car kv) (cdr kv))))
  (vlax-ldata-put "SD" "TLO" a)
  (sd:imgframe "Trang"))

(defun c:SDKHUNGIN (/ kho tl pt da hm ten so pp)
  (sd:begin)
  (if (sd:dlg "Khung in (SDKHUNGIN)"
              (list (list "kho" "Kh\\U+1ED5 gi\\U+1EA5y" 'kw (sd:cfg "KHI-KHO" "A1") '(("A1" . "A1 (841 x 594)") ("A3" . "A3 (420 x 297)") ("A2" . "A2 (594 x 420)") ("A4" . "A4 (297 x 210)")))
                    (list "tl" "T\\U+1EF7 l\\U+1EC7 1:" 'real (sd:cfg "KHI-TL" 50.0))
                    (list "da" "D\\U+1EF1 \\U+00E1n" 'str (sd:cfg "KHI-DA" ""))
                    (list "hm" "H\\U+1EA1ng m\\U+1EE5c" 'str (sd:cfg "KHI-HM" ""))
                    (list "ten" "T\\U+00EAn b\\U+1EA3n v\\U+1EBD" 'str (sd:cfg "KHI-TEN" "M\\U+1EB6T B\\U+1EB0NG L\\U+00C1T \\U+0110\\U+00C1"))
                    (list "so" "S\\U+1ED1 t\\U+1EDD (vd 01/03)" 'str (sd:cfg "KHI-SO" "01/01"))
                    (list "cdt" "Ch\\U+1EE7 \\U+0111\\U+1EA7u t\\U+01B0 (tr\\U+1ED1ng = kh\\U+00F4ng ghi)" 'str (sd:cfg "KHI-CDT" ""))
                    (list "tv" "T\\U+01B0 v\\U+1EA5n gi\\U+00E1m s\\U+00E1t (tr\\U+1ED1ng = kh\\U+00F4ng ghi)" 'str (sd:cfg "KHI-TV" ""))
                    (list "nt" "Nh\\U+00E0 th\\U+1EA7u thi c\\U+00F4ng (tr\\U+1ED1ng = kh\\U+00F4ng ghi)" 'str (sd:cfg "KHI-NT" ""))
                    (list "nth" "Ng\\U+01B0\\U+1EDDi th\\U+1EF1c hi\\U+1EC7n (tr\\U+1ED1ng = kh\\U+00F4ng ghi)" 'str (sd:cfg "KHI-NTH" ""))
                    (list "mada" "S\\U+1ED1 hi\\U+1EC7u: m\\U+00E3 d\\U+1EF1 \\U+00E1n (VD C6B)" 'str (sd:cfg "KHI-MADA" ""))
                    (list "mant" "S\\U+1ED1 hi\\U+1EC7u: m\\U+00E3 nh\\U+00E0 th\\U+1EA7u (VD 319)" 'str (sd:cfg "KHI-MANT" ""))
                    (list "loai" "S\\U+1ED1 hi\\U+1EC7u: lo\\U+1EA1i b\\U+1EA3n v\\U+1EBD (VD SDS)" 'str (sd:cfg "KHI-LOAI" "SDS"))
                    (list "stt" "S\\U+1ED1 hi\\U+1EC7u: s\\U+1ED1 th\\U+1EE9 t\\U+1EF1 c\\U+1EE7a b\\U+1EA3n v\\U+1EBD n\\U+00E0y" 'int (fix (sd:cfg "KHI-STT" 1)))
                    (list "rev" "REV (VD 00)" 'str (sd:cfg "KHI-REV" "00"))
                    (list "tang" "T\\U+1EF1 t\\U+0103ng s\\U+1ED1 th\\U+1EE9 t\\U+1EF1 sau m\\U+1ED7i l\\U+1EA7n v\\U+1EBD khung" 'tog (sd:cfg "KHI-TANG" t))
                    (list "bac" "M\\U+0169i t\\U+00EAn h\\U+01B0\\U+1EDBng B\\U+1EAFc" 'tog t)
                    (list "thuoc" "Th\\U+01B0\\U+1EDBc t\\U+1EF7 l\\U+1EC7" 'tog t)
                    (list "cl" "\\U+0110\\U+1EB7t s\\U+1EB5n c\\U+00E0i \\U+0111\\U+1EB7t in cho SDIN / SDTAOLAYOUT (acad.ctb, v\\U+1EEBa kh\\U+1ED5 gi\\U+1EA5y, kh\\U+00F4ng in khung \\U+1EA3nh)" 'tog t)))
    (progn
      (setq kho (sd:cfg-put "KHI-KHO" (sd:v "kho")) tl (sd:cfg-put "KHI-TL" (sd:v "tl"))
            da (sd:cfg-put "KHI-DA" (cond ((sd:v "da")) (""))) hm (sd:cfg-put "KHI-HM" (cond ((sd:v "hm")) (""))) 
            ten (sd:cfg-put "KHI-TEN" (cond ((sd:v "ten")) (""))) so (sd:cfg-put "KHI-SO" (cond ((sd:v "so")) ("")))
            *SD:KHIX* (list (sd:cfg-put "KHI-CDT" (cond ((sd:v "cdt")) (""))) (sd:cfg-put "KHI-TV" (cond ((sd:v "tv")) (""))) (sd:cfg-put "KHI-NT" (cond ((sd:v "nt")) ("")))
                            (sd:cfg-put "KHI-NTH" (cond ((sd:v "nth")) (""))) (sd:cfg-put "KHI-MADA" (vl-string-trim " " (cond ((sd:v "mada")) (""))))
                            (sd:cfg-put "KHI-MANT" (vl-string-trim " " (cond ((sd:v "mant")) (""))))
                            (sd:cfg-put "KHI-LOAI" (vl-string-trim " " (cond ((sd:v "loai")) ("SDS")))) (sd:cfg-put "KHI-STT" (cond ((sd:v "stt")) (1)))
                            (sd:cfg-put "KHI-REV" (cond ((sd:v "rev")) ("00"))) (sd:cfg-put "KHI-TANG" (sd:v "tang")))
            pp (sd:khi-paper kho))
      (if (setq pt (sd:getpt "\nGoc trai duoi cua to giay <0,0>: " nil))
        (progn (sd:khi-draw kho tl (car pt) (cadr pt) da hm ten (sd:khi-date) so (sd:v "bac") (sd:v "thuoc"))
               (if (sd:v "cl") (sd:khi-preset tl))
               (princ (strcat "\n[SD] Da ve khung " kho " ty le 1:" (sd:num tl) " (" (sd:num (* tl (car pp))) " x " (sd:num (* tl (cadr pp))) " don vi)."
                              (if (sd:v "cl") " Cai dat in: SDIN / SDTAOLAYOUT chon khung = layer SD-KHUNGIN (da dat san)." ""))))
        (princ "\n[SD] Chua chon diem."))))
  (sd:finish))

;; Thong ke 1 phuong an tu cac polyline vien SD_TILE: (n nguyen cat dac-biet hep dien-tich hao-hut%) va khung bao
(defun sd:pa-stats (ss hep / i e xd pts nF nC nD nH ar wst nom bb x0 y0 x1 y1)
  (setq i 0 nF 0 nC 0 nD 0 nH 0 ar 0.0 wst 0.0 nom 0.0)
  (repeat (sslength ss)
    (setq e (ssname ss i) i (1+ i) xd (mapcar 'cdr (cdadr (assoc -3 (entget e '("SD_TILE"))))) pts (sd:curve-pts e))
    (if (and (>= (length xd) 12) (/= (nth 1 xd) "X"))
      (progn
        (cond ((= (nth 1 xd) "F") (setq nF (1+ nF))) ((= (nth 1 xd) "C") (setq nC (1+ nC))) (t (setq nD (1+ nD))))
        (if (and (/= (nth 1 xd) "F") (< (min (nth 3 xd) (nth 4 xd)) hep)) (setq nH (1+ nH)))
        (setq ar (+ ar (nth 5 xd)) nom (+ nom (/ (* (nth 8 xd) (nth 9 xd)) 1e6)))
        (if (/= (nth 1 xd) "F") (setq wst (+ wst (max 0.0 (- (/ (* (nth 8 xd) (nth 9 xd)) 1e6) (nth 5 xd))))))
        (setq x0 (cond ((and x0 (< x0 (apply 'min (mapcar 'car pts)))) x0) ((apply 'min (mapcar 'car pts))))
              y0 (cond ((and y0 (< y0 (apply 'min (mapcar 'cadr pts)))) y0) ((apply 'min (mapcar 'cadr pts))))
              x1 (cond ((and x1 (> x1 (apply 'max (mapcar 'car pts)))) x1) ((apply 'max (mapcar 'car pts))))
              y1 (cond ((and y1 (> y1 (apply 'max (mapcar 'cadr pts)))) y1) ((apply 'max (mapcar 'cadr pts))))))))
  (list (list (+ nF nC nD) nF nC nD nH ar (if (> nom 0.0) (* 100.0 (/ wst nom)) 0.0)) (list x0 y0 x1 y1)))

;; Nhan + bang ngan cua 1 phuong an: tieu de tren khung bao, bang duoi khung bao; k = don vi ban ve / 1 mm giay
(defun sd:pa-label (nm st bb k / lay x y lines)
  (setq lay (sd:make-layer "SD-CHUTHICH" 7 "Continuous" 18) x (car bb) y (cadr bb)
        lines (list (strcat "T\\U+1ED5ng: " (itoa (nth 0 st)) " vi\\U+00EAn, " (sd:rtos (nth 5 st) 2) " m\\U+00B2")
                    (strcat "Nguy\\U+00EAn: " (itoa (nth 1 st)) " | C\\U+1EAFt ch\\U+1EEF nh\\U+1EADt: " (itoa (nth 2 st)) " | C\\U+1EAFt \\U+0111\\U+1EB7c bi\\U+1EC7t: " (itoa (nth 3 st)))
                    (strcat "Vi\\U+00EAn c\\U+1EAFt h\\U+1EB9p: " (itoa (nth 4 st)))
                    (strcat "Hao h\\U+1EE5t \\U+01B0\\U+1EDBc t\\U+00EDnh: " (sd:rtos (nth 6 st) 1) " % (ph\\U+1EA7n th\\U+1EEBa c\\U+1EE7a vi\\U+00EAn c\\U+1EAFt)")))
  (sd:text (list x (+ (cadddr bb) (* 6.0 k))) nm (* 6.0 k) "L" lay)
  (setq y (- y (* 6.0 k)))
  (foreach l lines (sd:text (list x y) l (* 3.5 k) "L" lay) (setq y (- y (* 6.0 k)))))

(defun c:SDPHUONGAN (/ kho tl da hm ten hep sa sb ra rb ba bb ux0 uy0 ux1 uy1 pp w h wn hn need ox oy cx cy)
  (sd:begin)
  (if (sd:dlg "Ph\\U+01B0\\U+01A1ng \\U+00E1n A / B (SDPHUONGAN)"
              (list (list "kho" "Kh\\U+1ED5 gi\\U+1EA5y" 'kw (sd:cfg "KHI-KHO" "A1") '(("A1" . "A1 (841 x 594)") ("A3" . "A3 (420 x 297)") ("A2" . "A2 (594 x 420)") ("A4" . "A4 (297 x 210)")))
                    (list "tl" "T\\U+1EF7 l\\U+1EC7 1:" 'real (sd:cfg "KHI-TL" 50.0))
                    (list "da" "D\\U+1EF1 \\U+00E1n" 'str (sd:cfg "KHI-DA" ""))
                    (list "hm" "H\\U+1EA1ng m\\U+1EE5c" 'str (sd:cfg "KHI-HM" ""))
                    (list "ten" "T\\U+00EAn b\\U+1EA3n v\\U+1EBD" 'str "PH\\U+01AF\\U+01A0NG \\U+00C1N L\\U+00C1T \\U+0110\\U+00C1 A / B")
                    (list "hep" "Vi\\U+00EAn c\\U+1EAFt h\\U+1EB9p h\\U+01A1n (mm) t\\U+00EDnh l\\U+00E0 h\\U+1EB9p" 'real (sd:cfg "PA-HEP" 100.0))
                    (list "ve" "V\\U+1EBD lu\\U+00F4n khung in bao c\\U+1EA3 hai ph\\U+01B0\\U+01A1ng \\U+00E1n" 'tog t)))
    (progn
      (setq kho (sd:cfg-put "KHI-KHO" (sd:v "kho")) tl (sd:cfg-put "KHI-TL" (sd:v "tl")) hep (sd:cfg-put "PA-HEP" (sd:v "hep"))
            da (sd:cfg-put "KHI-DA" (cond ((sd:v "da")) (""))) hm (sd:cfg-put "KHI-HM" (cond ((sd:v "hm")) (""))) ten (sd:v "ten"))
      (princ "\nQuet chon cac vi\\U+00EAn c\\U+1EE7a PH\\U+01AF\\U+01A0NG \\U+00C1N A: ")
      (setq sa (ssget '((0 . "LWPOLYLINE") (-3 ("SD_TILE")))))
      (princ "\nQuet chon cac vi\\U+00EAn c\\U+1EE7a PH\\U+01AF\\U+01A0NG \\U+00C1N B: ")
      (setq sb (ssget '((0 . "LWPOLYLINE") (-3 ("SD_TILE")))))
      (if (not (and sa sb))
        (princ "\n[SD] Can chon du hai phuong an (cac vien da dung bang SDGACH / SDDOCDA).")
        (progn
          (setq ra (sd:pa-stats sa hep) rb (sd:pa-stats sb hep) ba (cadr ra) bb (cadr rb) ra (car ra) rb (car rb))
          (sd:pa-label "PH\\U+01AF\\U+01A0NG \\U+00C1N A" ra ba tl)
          (sd:pa-label "PH\\U+01AF\\U+01A0NG \\U+00C1N B" rb bb tl)
          (princ (strcat "\n[SD] A: " (itoa (car ra)) " vien, hao hut uoc tinh " (sd:rtos (nth 6 ra) 1) " % | B: " (itoa (car rb)) " vien, hao hut uoc tinh "
                         (sd:rtos (nth 6 rb) 1) " %."))
          (if (sd:v "ve")
            (progn
              (setq ux0 (min (car ba) (car bb)) uy0 (- (min (cadr ba) (cadr bb)) (* 30.0 tl))
                    ux1 (max (caddr ba) (caddr bb)) uy1 (+ (max (cadddr ba) (cadddr bb)) (* 14.0 tl))
                    pp (sd:khi-paper kho) w (car pp) h (cadr pp)
                    wn (/ (- ux1 ux0) tl) hn (/ (- uy1 uy0) tl))
              (if (or (> wn (- w 45.0)) (> hn (- h 20.0 45.0)))
                (princ (strcat "\n[SD] Hai phuong an khong vua to " kho " ty le 1:" (sd:num tl) " (can ~" (sd:num (fix (+ 1.0 wn))) " x " (sd:num (fix (+ 1.0 hn)))
                               " mm giay, khung ten chiem day to): tang ty le hoac doi kho giay roi chay lai (cac nhan van da ve)."))
                (progn
                  (setq cx (/ (+ ux0 ux1) 2.0) cy (/ (+ uy0 uy1) 2.0)
                        ox (- cx (* tl (/ (+ w 15.0) 2.0))) oy (- cy (* tl (/ (+ h 55.0) 2.0))))
                  (sd:khi-draw kho tl ox oy da hm ten (sd:khi-date) "01/01" t t)
                  (sd:khi-preset tl)
                  (princ (strcat "\n[SD] Da ve khung in " kho " 1:" (sd:num tl) " bao ca hai phuong an; SDIN / SDTAOLAYOUT chon khung = layer SD-KHUNGIN."))))))))))
  (sd:finish))

;;; --------------------------------------------------------------------------
;;;  SDLENH - Ra lenh bang cau tieng Viet cho cac o da: "gop o 25+36" (gop 2 hay nhieu o thanh 1), "xoa o 12 13"
;;;  Lenh doc cau, noi lai y hieu, hoi xac nhan roi moi lam; so o la so hieu T.. ghi tren ban ve (SD-CHU). Hoan lai bang UNDO.
;;; --------------------------------------------------------------------------
;; tach cau thanh cac tu (chu thuong ASCII, so); moi ky tu khac ASCII (dau tieng Viet) thanh "~" trong tu, sd:ai-bare bo "~" khi so khop (gop hoac gp)
(defun sd:ai-bare (w / i c r)
  (setq i 1 r "")
  (while (<= i (strlen w)) (setq c (substr w i 1) i (1+ i)) (if (/= c "~") (setq r (strcat r c))))
  r)

(defun sd:ai-tokens (s / i c w r)
  (setq i 1 w "" s (strcase s t))
  (while (<= i (strlen s))
    (setq c (substr s i 1) i (1+ i))
    (cond
      ((>= (ascii c) 128) (setq w (strcat w "~")))
      ((wcmatch c "[a-z0-9]") (setq w (strcat w c)))
      (t (if (/= w "") (setq r (cons w r))) (setq w ""))))
  (if (/= w "") (setq r (cons w r)))
  (reverse r))

;; (y-dinh so-o...): y-dinh = GOP / XOA / nil
(defun sd:ai-parse (s / tk nums act ang prev b)
  (setq tk (sd:ai-tokens s))
  (foreach w tk
    (setq b (sd:ai-bare w))
    (cond ((wcmatch w "[0-9]*")
           (if (vl-every '(lambda (ch) (< 47 ch 58)) (vl-string->list w)) (setq nums (cons (atoi w) nums))))
          ;; "90 do" hoac "90" kem do co dau (chu co dau chi con "~~")
          ((and prev (wcmatch prev "[0-9]*") nums (= (car nums) (atoi prev)) (or (= b "do") (and (= b "") (> (strlen w) 0))))
           (setq ang (car nums) nums (cdr nums)))
          ((member b '("xoay" "quay" "rotate")) (setq act 'XOAY))
          ((member b '("gop" "gp" "ghep" "ghp" "noi" "merge" "join")) (setq act (cond (act) ('GOP))))
          ((member b '("xoa" "xa" "bo" "go" "del" "delete")) (setq act (cond (act) ('XOA)))))
    (setq prev w))
  (list act (reverse nums) ang))

;; xoay van 1 o: xoay anh cua o quanh tam o goc ang (do), cat lai; tra ve nil neu xong, chuoi bao loi
(defun sd:ai-turn (rec ims ang / pts im o c ron xd a)
  (setq pts (sd:curve-pts (caddr rec)) im (if ims (sd:im-find pts ims)) ron (cond (*SD:IRON*) (0.0)) a (* pi (/ ang 180.0)))
  (cond
    ((null im) "khong thay anh cua o (o khong co anh cat, hoac anh cu khong co du lieu SD_ANH)")
    ((null (sd:im-delta im)) "anh dung chung cho nhieu o (luoi chung) nen khong xoay rieng duoc")
    (t
     (setq o (vlax-ename->vla-object im)
           c (list (/ (apply '+ (mapcar 'car pts)) (float (length pts))) (/ (apply '+ (mapcar 'cadr pts)) (float (length pts))) 0.0))
     (vla-Rotate o (vlax-3d-point c) a)
     (if (sd:im-fit (sd:im-geom im) (sd:inset-pts pts (/ ron 2.0)) 10.0)
       (progn
         (setq xd (mapcar 'cdr (cdadr (assoc -3 (entget im '("SD_ANH"))))))
         (vl-catch-all-apply 'sd:put-xd
           (list im (list -3 (list "SD_ANH" (cons 1040 (car xd)) (cons 1040 (cadr xd))
                                   (cons 1040 (rem (+ (nth 2 xd) a) (* 2.0 pi)))))))
         (sd:im-reclip im (sd:inset-pts pts (/ ron 2.0)) 10.0 nil)
         nil)
       (progn (vla-Rotate o (vlax-3d-point c) (- a))
              "xoay xong thi het kho (tam da khong du theo huong do), da tra ve nhu cu")))))

;; chi muc cac o: ((so text polyline) ...) - so hieu T<n> nam trong polyline vien nao thi thuoc o do
(defun sd:ai-index (/ txs pls i e str n c k pl r)
  (setq txs (ssget "_X" '((0 . "TEXT") (8 . "SD-CHU") (1 . "T#*")))
        pls (ssget "_X" '((0 . "LWPOLYLINE") (8 . "SD-GACH,SD-GACH-CAT,SD-GACH-VIEN,SD-GACH-DOC") (-4 . "&") (70 . 1))))
  (if (and txs pls)
    (progn
      (setq i 0)
      (repeat (sslength txs)
        (setq e (ssname txs i) i (1+ i) str (cdr (assoc 1 (entget e))) n (atoi (substr str 2))
              c (cdr (assoc 10 (entget e))) k 0 pl nil)
        (while (and (null pl) (< k (sslength pls)))
          (if (sd:inpoly (list (car c) (cadr c)) (sd:curve-pts (ssname pls k))) (setq pl (ssname pls k)))
          (setq k (1+ k)))
        (if pl (setq r (cons (list n e pl) r))))))
  r)

;; xoa polyline + anh + hatch + so hieu cua mot o; tra ve so doi tuong da xoa
(defun sd:ai-del-tile (rec ims hs / pts k h n x)
  (setq pts (sd:curve-pts (caddr rec)) n 0)
  (foreach x (list (caddr rec) (cadr rec) (if ims (sd:im-find pts ims)))
    (if (and x (entget x)) (progn (entdel x) (setq n (1+ n)))))
  (if hs
    (progn (setq k 0)
           (repeat (sslength hs)
             (setq h (ssname hs k) k (1+ k))
             (if (and (entget h) (sd:inpoly (sd:hatch-center h) pts)) (progn (entdel h) (setq n (1+ n)))))))
  n)

;; thay dinh cua LWPOLYLINE e bang pts (dung nguyen xdata va thuoc tinh khac)
(defun sd:ai-setpts (e pts / ed pre post)
  (setq ed (vl-remove-if '(lambda (g) (member (car g) '(10 40 41 42))) (entget e '("SD_TILE")))
        ed (subst (cons 90 (length pts)) (assoc 90 ed) ed))
  (foreach g ed
    (if (and (null post) (member (car g) '(210 -3))) (setq post (list g)) (if post (setq post (cons g post)) (setq pre (cons g pre)))))
  (entmod (append (reverse pre) (mapcar '(lambda (q) (list 10 (car q) (cadr q))) pts) (reverse post))))

;; gop o b vao o a: bao loi (chuoi) neu khong gop duoc, nil neu xong. a giu so hieu, b bi xoa
(defun sd:ai-merge (ra rb ims hs / pa pb ha a1 a2 ah ia ib im fr xd c ron)
  (setq pa (sd:curve-pts (caddr ra)) pb (sd:curve-pts (caddr rb))
        ha (sd:hull (append pa pb)) a1 (abs (sd:area pa)) a2 (abs (sd:area pb)) ah (abs (sd:area ha))
        ron (cond (*SD:IRON*) (0.0)))
  (cond
    ((> (- ah a1 a2) (* 0.05 (+ a1 a2)))
     "hai o khong tao thanh mot hinh loi (xa nhau hoac lech): chi gop duoc cac o ke nhau tao thanh hinh loi, VD hai o cung ben rong")
    (t
     (setq ia (if ims (sd:im-find pa ims)) ib (if ims (sd:im-find pb ims)))
     (setq im (cond ((and ia (sd:im-fit (sd:im-geom ia) (sd:inset-pts ha (/ ron 2.0)) 10.0)) ia)
                    ((and ib (sd:im-fit (sd:im-geom ib) (sd:inset-pts ha (/ ron 2.0)) 10.0)) ib)))
     (if (and (or ia ib) (null im))
       "o gop lon hon ca tam da (het kho): khong gop duoc, hoac chon xoay van roi chay lai"
       (progn
         (setq xd (mapcar 'cdr (cdadr (assoc -3 (entget (caddr ra) '("SD_TILE"))))))
         (sd:ai-setpts (caddr ra) ha)
         (setq fr (sd:tile-frame ha))
         (if (>= (length xd) 13)
           (sd:put-xd (caddr ra)
             (sd:tile-xd (nth 0 xd) "D" "GOP" (cadr fr) (caddr fr) (/ ah 1e6) 0 (nth 7 xd) (cadr fr) (caddr fr) (nth 10 xd) (nth 11 xd) "G")))
         ;; xoa o b va cac phan cua no; anh khong dung thi xoa luon
         (foreach x (list (caddr rb) (cadr rb) (if (and ia ib) (if (eq im ia) ib ia)))
           (if (and x (entget x)) (entdel x)))
         ;; hatch cua ca hai o bo di (van da hatch phai tao lai bang SDVANDA)
         (if hs
           (progn (setq c 0)
                  (repeat (sslength hs)
                    (if (and (entget (ssname hs c))
                             (or (sd:inpoly (sd:hatch-center (ssname hs c)) ha)))
                      (entdel (ssname hs c)))
                    (setq c (1+ c)))))
         (if im (sd:im-reclip im (sd:inset-pts ha (/ ron 2.0)) 10.0 nil))
         nil)))))

;; lich su cau lenh (toi da 8, moi nhat truoc) va cau truoc (thao tac, goc, so o) luu trong ban ve
(defun sd:ai-his () (sd:cfg "LENH-HIS" nil))
(defun sd:ai-his-add (s) (sd:cfg-put "LENH-HIS" (sd:take (cons s (vl-remove s (sd:ai-his))) 8)))

(defun sd:ai-help (/ h k)
  (princ "\nCau mau: gop o 25+36 | ghep 5 6 7 | xoa o 12 13 | xoay van 90 do o 25 36 | (chon cac o truoc) xoay van 90 do")
  (princ "\nLenh nhanh: ? = tro giup | lai = lam lai cau truoc | lai o 40 41 = cung viec cho o khac | #n = chay lai cau thu n trong lich su | Enter = lai cau truoc")
  (if (setq h (sd:ai-his))
    (progn (princ "\nLich su (moi nhat truoc):") (setq k 0)
           (foreach x h (setq k (1+ k)) (princ (strcat "\n  #" (itoa k) "  " x))))))

;; doc cau lenh: ? hien tro giup roi hoi lai; #n lay cau thu n trong lich su; Enter lay cau truoc
(defun sd:ai-ask (/ s r n his)
  (setq his (sd:ai-his))
  (while (null r)
    (setq s (getstring T "\nGo lenh bang tieng Viet (VD: gop o 25+36; ? = tro giup, Enter = lai cau truoc): "))
    (cond
      ((or (null s) (= s ""))
       (if his (progn (princ (strcat "\n[SD] Dung lai cau truoc: " (car his))) (setq r (car his))) (setq r "")))
      ((member (strcase s t) '("?" "help" "tro giup")) (sd:ai-help))
      ((and (= (substr s 1 1) "#") (> (atoi (substr s 2)) 0))
       (setq n (atoi (substr s 2)))
       (if (nth (1- n) his) (setq r (nth (1- n) his)) (princ "\n[SD] Khong co cau thu do trong lich su.")))
      (t (setq r s))))
  r)

;; xac nhan: hop thoai co tom tat, khong hop thoai thi hoi tren dong lenh
(defun sd:ai-confirm (msg)
  (if (sd:dlg-on)
    (sd:dlg "Xac nhan lenh (SDLENH)" (list (list "tt" msg 'note nil)))
    (progn (initget "Co Khong") (/= "Khong" (getkword "\nThuc hien? [Co/Khong] <Co>: ")))))

(defun c:SDLENH (/ s r act nums ang idx hs ims recs miss ok yn first n err done ss k tk lst msg redo)
  (sd:begin)
  (setq s (sd:ai-ask))
  (setq r (sd:ai-parse (cond (s) (""))) act (car r) nums (cadr r) ang (caddr r)
        tk (sd:ai-tokens (cond (s) (""))))
  ;; "lai" / "lai o 40 41": lam lai viec cua cau truoc (cung thao tac va goc), so o moi neu co
  (if (and (null act) tk (member (sd:ai-bare (car tk)) '("lai" "lap" "again")) (setq lst (sd:cfg "LENH-LAST" nil)))
    (setq act (cdr (assoc (car lst) '(("GOP" . GOP) ("XOA" . XOA) ("XOAY" . XOAY))))
          ang (cond (ang) ((cadr lst))) nums (cond (nums) ((caddr lst))) redo t))
  (cond
    ((null act)
     (princ "\n[SD] Chua hieu cau lenh. Hien biet: GOP (gop / ghep / noi) va XOA (xoa / bo / go), kem so o. VD: gop o 25+36, ghep 5 6 7, xoa o 12 13."))
    ((and (/= act 'XOAY) (null nums)) (princ "\n[SD] Can kem so o. VD: gop o 25+36, xoa o 12 13."))
    ((and (= act 'GOP) (< (length nums) 2)) (princ "\n[SD] Gop can it nhat hai o. VD: gop o 25+36."))
    (t
     (setq idx (sd:ai-index))
     ;; xoay van ma khong neu so o: dung cac o dang chon (pickfirst) hoac hoi chon
     (if (and (= act 'XOAY) (null nums))
       (progn
         (setq ss (cond ((ssget "_I" '((0 . "LWPOLYLINE")))) ((progn (princ "\nChon cac o (polyline vien) can xoay van: ") (ssget '((0 . "LWPOLYLINE")))))) k 0)
         (if ss (repeat (sslength ss) (setq recs (append recs (list (list nil nil (ssname ss k)))) k (1+ k))))))
     (foreach k nums
       (if (assoc k idx) (setq recs (append recs (list (assoc k idx)))) (setq miss (cons k miss))))
     (cond
       (miss (princ (strcat "\n[SD] Khong tim thay o so " (sd:join (mapcar 'itoa (reverse miss)) ", ") " (so hieu T.. tren layer SD-CHU nam trong polyline vien).")))
       (t
        (setq msg (strcat "Hieu: " (cond ((= act 'GOP) "GOP cac o ") ((= act 'XOA) "XOA cac o ")
                                         (t (strcat "XOAY VAN " (itoa (cond (ang) (90))) " do cho " (itoa (length recs)) " o: ")))
                          (if nums (sd:join (mapcar 'itoa nums) ", ") "dang chon")
                          (if (= act 'GOP) (strcat " thanh 1 (giu so hieu T" (itoa (car nums)) ")") "")))
        (princ (strcat "\n[SD] " msg))
        (setq yn (if (sd:ai-confirm msg) "Co" "Khong"))
        (if (and (/= yn "Khong") recs)
          (progn
            (sd:cfg-put "LENH-LAST" (list (cond ((= act 'GOP) "GOP") ((= act 'XOA) "XOA") (t "XOAY")) ang nums))
            (if (and s (not redo) (/= s "")) (sd:ai-his-add s))
            (setq hs (ssget "_X" '((0 . "HATCH") (8 . "SD-GACH-VAN")))
                  ims (ssget "_X" '((0 . "IMAGE") (-3 ("SD_ANH")))) first (car recs))
            (cond
              ((= act 'XOAY)
               (setq n 0)
               (foreach rc recs
                 (if (setq err (sd:ai-turn rc ims (cond (ang) (90))))
                   (princ (strcat "\n[SD] O " (if (car rc) (itoa (car rc)) "dang chon") ": " err))
                   (setq n (1+ n))))
               (princ (strcat "\n[SD] Da xoay van " (itoa n) " / " (itoa (length recs)) " o. Hoan lai bang UNDO.")))
              ((= act 'GOP)
              (progn
                (foreach rb (cdr recs)
                  (if (null err)
                    (if (setq err (sd:ai-merge first rb ims hs))
                      (princ (strcat "\n[SD] Khong gop duoc o " (itoa (car rb)) ": " err))
                      (setq done (1+ (cond (done) (0)))))))
                (princ (strcat "\n[SD] Da gop " (itoa (cond (done) (0))) " o vao o " (itoa (car first)) ". Hatch van (neu co) da bo: chay SDVANDA de tao lai. Hoan lai bang UNDO."))))
              (t
                (setq n 0)
                (foreach rc recs (setq n (+ n (sd:ai-del-tile rc ims hs))))
                (princ (strcat "\n[SD] Da xoa " (itoa (length recs)) " o (" (itoa n) " doi tuong). Hoan lai bang UNDO."))))))))))
  (sd:finish))

;;; --------------------------------------------------------------------------
;;;  SDBLOCKDA - Block chi tiet da: (Mau) tao block mat cat mui bac 3 bac tu mau co san (Thang / V45 / Roi / CNC, tuy chon hoc LED),
;;;  (Quet) quet hinh bat ky de tao block, (Chen) chen file block .dwg da luu. Tuy chon luu ra .dwg de dung cho ban ve khac
;;;  va mo Block Editor de them thong so dong (Linear + Stretch). Block khong chua polyline vien / anh cat cua SDGACH, SDANHDA...
;;;  (cac lenh quet SDDOCDA, SDANHDA, SDTUDONG, SDRON, SDXOAVIEN khong thay doi tuong nam trong block).
;;; --------------------------------------------------------------------------
(defun sd:bm-since (e0 / e ss)
  (setq e (if e0 (entnext e0) (entnext)))
  (while e (setq ss (cond (ss) ((ssadd))) ss (ssadd e ss) e (entnext e)))
  ss)

(defun sd:bm-name (kieu gd R tm tc nho hoc)
  (strcat "SDCT_" kieu "_" (sd:num gd) "x" (sd:num R) "_t" (sd:num tm) "c" (sd:num tc) "n" (sd:num nho) (if hoc "_LED" "")))

(defun sd:bm-stamp () (substr (vl-string-translate "." "" (rtos (getvar "CDATE") 2 6)) 5))

;; tao block tu ss, goc base; neu ten da co thi hoi ghi de (chi khi hoi = t)
(defun sd:bm-define (name base ss ask / yn)
  (cond
    ((null (tblsearch "BLOCK" name)) (command "_.-BLOCK" name base ss "") t)
    ((and ask (progn (initget "Co Khong")
                     (setq yn (getkword (strcat "\nBlock " name " da co. Ghi de dinh nghia (cac block da chen se doi theo)? [Co/Khong] <Khong>: ")))
                     (= yn "Co")))
     (command "_.-BLOCK" name base ss "_Y" "") t)
    (t nil)))

(defun sd:bm-save (name / f)
  (if (setq f (getfiled "Luu block ra file .dwg (dung cho ban ve khac)" name "dwg" 1))
    (progn
      (if (findfile f) (command "_.-WBLOCK" f "_Y" name) (command "_.-WBLOCK" f name))
      (princ (strcat "\n[SD] Da luu " f)))))

;; Ten cac layer hien co trong ban ve
(defun sd:bm-layers (/ r d)
  (setq d (tblnext "LAYER" T))
  (while d (setq r (cons (cdr (assoc 2 d)) r) d (tblnext "LAYER")))
  r)

;; Don layer cua block vua chen tu file ngoai: dua moi doi tuong trong dinh nghia block (tru layer 0 / DEFPOINTS) ve 1 layer lay,
;; roi xoa cac layer moi do file mang vao (old = danh sach layer truoc khi chen). Tra ve (so-doi-tuong so-layer-xoa)
(defun sd:bm-clean (bn lay old / e ed n nd nm)
  (sd:make-layer lay 7 "Continuous" 18)
  (setq e (cdr (assoc -2 (tblsearch "BLOCK" bn))) n 0 nd 0)
  (while e
    (setq ed (entget e))
    (if (and (assoc 8 ed) (not (member (strcase (cdr (assoc 8 ed))) (list "0" "DEFPOINTS" (strcase lay)))))
      (progn (entmod (subst (cons 8 lay) (assoc 8 ed) ed)) (setq n (1+ n))))
    (setq e (entnext e)))
  (foreach nm (sd:bm-layers)
    (if (and (not (member nm old)) (/= (strcase nm) (strcase lay)))
      (if (not (vl-catch-all-error-p (vl-catch-all-apply 'vla-Delete (list (vla-Item (vla-get-Layers (sd:doc)) nm)))))
        (setq nd (1+ nd)))))
  (list n nd))

;; Mat cat chi tiet op kho (da treo tren khung thep): tuong ben trai, 2 tam da chong len nhau co khe joint, bat treo inox + moc treo inox o cao do khe,
;; thep L, bulong no. Ve 1:1 (mm) tai goc (0,0); tam duoi y 0..hh. t day da, g khe lung da - tuong, j khe joint, c vat canh (0 = thang),
;; la canh thep L, lt day thep L, bd duong kinh bulong, bl chieu dai bulong. So lieu mac dinh chi la mau minh hoa: kiem tra voi phu kien thuc te.
(defun sd:bm-opkho (dd g j c la lt bd bl hh / x1 yj yb yc xc th lbl)
  (sd:make-layer "SD-GACH" 7 "Continuous" 25) (sd:make-layer "SD-GACH-CAT" 4 "Continuous" 25) (sd:make-layer "SD-KHUAT" 8 "Continuous" 13)
  (sd:make-layer "SD-CHU" 7 "Continuous" 18)
  (setq x1 (+ g dd) yj (+ hh (/ j 2.0)) yb (- yj lt (/ la 2.0)) yc (+ yb (/ la 2.0)) xc (+ g (/ dd 2.0)) th 8.0)
  ;; tuong
  (sd:pline (list (list -150.0 -80.0) (list 0.0 -80.0) (list 0.0 (+ (* 2.0 hh) j 80.0)) (list -150.0 (+ (* 2.0 hh) j 80.0))) t "SD-KHUAT")
  ;; tam da duoi va tren (vat canh phia khe joint neu c > 0)
  (sd:pline (if (> c 0.0)
              (list (list g 0.0) (list x1 0.0) (list x1 (- hh c)) (list (- x1 c) hh) (list g hh))
              (list (list g 0.0) (list x1 0.0) (list x1 hh) (list g hh)))
            t "SD-GACH")
  (sd:pline (if (> c 0.0)
              (list (list g (+ hh j)) (list (- x1 c) (+ hh j)) (list x1 (+ hh j c)) (list x1 (+ (* 2.0 hh) j)) (list g (+ (* 2.0 hh) j)))
              (list (list g (+ hh j)) (list x1 (+ hh j)) (list x1 (+ (* 2.0 hh) j)) (list g (+ (* 2.0 hh) j))))
            t "SD-GACH")
  ;; thep L: canh dung sat tuong, canh ngang nam duoi bat treo
  (sd:pline (list (list 0.0 yb) (list la yb) (list la (+ yb lt)) (list lt (+ yb lt)) (list lt (+ yb la)) (list 0.0 (+ yb la))) t "SD-GACH-CAT")
  ;; bulong no xuyen canh dung (dau bulong ben ngoai)
  (sd:pline (list (list (- bl) (- yc (/ bd 2.0))) (list lt (- yc (/ bd 2.0))) (list lt (+ yc (/ bd 2.0))) (list (- bl) (+ yc (/ bd 2.0)))) t "SD-GACH-CAT")
  (sd:pline (list (list lt (- yc (* 0.9 bd))) (list (+ lt 5.0) (- yc (* 0.9 bd))) (list (+ lt 5.0) (+ yc (* 0.9 bd))) (list lt (+ yc (* 0.9 bd)))) t "SD-GACH-CAT")
  ;; bat treo inox: ban dua nam tren canh ngang thep L, voi toi giua day da
  (sd:pline (list (list (/ la 2.0) (+ yb lt)) (list (+ xc 10.0) (+ yb lt)) (list (+ xc 10.0) (+ yb lt 3.0)) (list (/ la 2.0) (+ yb lt 3.0))) t "SD-GACH-CAT")
  ;; moc treo inox: chot dung xuyen ban dua, cam vao canh tam duoi va tam tren
  (sd:pline (list (list (- xc 2.0) (- hh 15.0)) (list (+ xc 2.0) (- hh 15.0)) (list (+ xc 2.0) (+ hh j 15.0)) (list (- xc 2.0) (+ hh j 15.0))) t "SD-GACH-CAT")
  ;; chu thich
  (setq lbl (+ x1 80.0))
  (sd:line (list xc (/ hh 2.0)) (list lbl (/ hh 2.0)) "SD-CHU")
  (sd:text (list (+ lbl 5.0) (/ hh 2.0)) (strcat "\\U+0110\\U+00C1 GRANIT D\\U+00C0Y " (sd:num dd)) th "ML" "SD-CHU")
  (sd:line (list x1 yj) (list lbl yj) "SD-CHU")
  (sd:text (list (+ lbl 5.0) yj) (strcat "KHE JOINT " (sd:num j) (if (> c 0.0) (strcat ", V\\U+00C1T C\\U+1EA0NH " (sd:num c) " x 45\\U+00B0") ", TH\\U+1EB2NG")) th "ML" "SD-CHU")
  (sd:line (list xc (+ hh j 15.0)) (list lbl (+ hh j 45.0)) "SD-CHU")
  (sd:text (list (+ lbl 5.0) (+ hh j 45.0)) "M\\U+00D3C TREO INOX" th "ML" "SD-CHU")
  (setq lbl (- (- bl) 40.0))
  (sd:line (list (- (/ bl 2.0)) yc) (list lbl yc) "SD-CHU")
  (sd:text (list (- lbl 5.0) yc) (strcat "BUL\\U+00D4NG N\\U+1EDE INOX M" (sd:num bd) "x" (sd:num bl)) th "MR" "SD-CHU")
  (sd:line (list (/ la 2.0) (+ yb lt 1.5)) (list lbl (+ yb lt 40.0)) "SD-CHU")
  (sd:text (list (- lbl 5.0) (+ yb lt 40.0)) "B\\U+00C1T TREO INOX" th "MR" "SD-CHU")
  (sd:line (list (/ lt 2.0) (+ yb la)) (list lbl (- yb 40.0)) "SD-CHU")
  (sd:text (list (- lbl 5.0) (- yb 40.0)) (strcat "TH\\U+00C9P L" (sd:num la) "x" (sd:num la) "x" (sd:num lt)) th "MR" "SD-CHU")
  (sd:text (list (- lbl 5.0) (/ hh 2.0)) "T\\U+01AF\\U+1EDCNG / K\\U+1EBET C\\U+1EA4U" th "MR" "SD-CHU")
  t)

(defun c:SDBLOCKDA (/ mode kieu gd R tm tc nho hoc name e0 ss base pt keep wb dyn ok f ents n don laych bn nuevo old ot og oj oc ol olt obd obl ohh)
  (sd:begin)
  (if (sd:dlg "Block chi tiet da (SDBLOCKDA)"
              (list (list "mode" "Viec can lam" 'kw (sd:cfg "BLK-MODE" "Mau")
                          '(("Mau" . "Tao block mat cat mui bac tu mau co san")
                            ("Quet" . "Quet hinh bat ky de tao block")
                            ("Chen" . "Chen file block .dwg da luu")
                            ("Opkho" . "Chi tiet op kho: da treo tren khung thep, joint vat canh")))
                    (list "kieu" "Kieu mui bac" 'kw (sd:cfg "BLK-KIEU" "Thang")
                          '(("Thang" . "Thang (mat chong len co, mui nho ra)") ("V45" . "Ghep vat 45 do") ("Roi" . "Dai mui roi") ("CNC" . "Mui bo / vat CNC"))
                          '("mode" "Mau"))
                    (list "gd" "Mat bac rong (mm)" 'real (sd:cfg "BLK-GD" 300.0) nil '("mode" "Mau"))
                    (list "R" "Cao bac (mm)" 'real (sd:cfg "BLK-R" 150.0) nil '("mode" "Mau"))
                    (list "tm" "Day mat bac (mm)" 'real (sd:cfg "BLK-TM" 20.0) nil '("mode" "Mau"))
                    (list "tc" "Day co bac (mm)" 'real (sd:cfg "BLK-TC" 20.0) nil '("mode" "Mau"))
                    (list "nho" "Mui nho ra (mm)" 'real0 (sd:cfg "BLK-NHO" 20.0) nil '("mode" "Mau"))
                    (list "hoc" "Co hoc LED duoi mep truoc mat bac (17 x 20, cach mep 20)" 'tog nil nil '("mode" "Mau"))
                    (list "ot" "Day da (mm)" 'real (sd:cfg "OK-T" 20.0) nil '("mode" "Opkho"))
                    (list "og" "Khe tu lung da den tuong (mm)" 'real (sd:cfg "OK-G" 40.0) nil '("mode" "Opkho"))
                    (list "oj" "Khe joint giua hai tam (mm)" 'real (sd:cfg "OK-J" 8.0) nil '("mode" "Opkho"))
                    (list "oc" "Vat canh phia mat khe joint (mm, 0 = joint thang)" 'real0 (sd:cfg "OK-C" 3.0) nil '("mode" "Opkho"))
                    (list "ol" "Thep L: canh (mm)" 'real (sd:cfg "OK-L" 30.0) nil '("mode" "Opkho"))
                    (list "olt" "Thep L: day (mm)" 'real (sd:cfg "OK-LT" 3.0) nil '("mode" "Opkho"))
                    (list "obd" "Bulong no: duong kinh (mm)" 'real (sd:cfg "OK-BD" 8.0) nil '("mode" "Opkho"))
                    (list "obl" "Bulong no: chieu dai (mm)" 'real (sd:cfg "OK-BL" 100.0) nil '("mode" "Opkho"))
                    (list "ohh" "Chieu cao moi tam ve (mm)" 'real (sd:cfg "OK-H" 600.0) nil '("mode" "Opkho"))
                    (list "keep" "Giu hinh tren ban ve (chen lai thanh block)" 'tog t nil '("mode" "Quet"))
                    (list "wb" "Luu ra file .dwg de dung cho ban ve khac" 'tog nil nil '("mode" "Mau" "Quet" "Opkho"))
                    (list "dyn" "Mo Block Editor de them thong so dong (Linear + Stretch)" 'tog nil nil '("mode" "Mau" "Quet" "Opkho"))
                    (list "don" "Layer cua block tai tu ngoai" 'kw (sd:cfg "BLK-DON" "Gop")
                          '(("Gop" . "Don: dua moi doi tuong ve 1 layer, xoa layer la file mang vao") ("Giu" . "Giu nguyen layer cua file"))
                          '("mode" "Chen"))
                    (list "laych" "Ten layer chung cho block chen" 'str (sd:cfg "BLK-LAY" "SD-CHITIET") nil '("mode" "Chen"))))
    (progn
      (setq mode (sd:cfg-put "BLK-MODE" (sd:v "mode")))
      (cond
        ;; ---- mau mui bac
        ((= mode "Mau")
         (setq kieu (sd:cfg-put "BLK-KIEU" (sd:v "kieu")) gd (sd:cfg-put "BLK-GD" (sd:v "gd")) R (sd:cfg-put "BLK-R" (sd:v "R"))
               tm (sd:cfg-put "BLK-TM" (sd:v "tm")) tc (sd:cfg-put "BLK-TC" (sd:v "tc")) nho (sd:cfg-put "BLK-NHO" (cond ((sd:v "nho")) (0.0)))
               hoc (sd:v "hoc") wb (sd:v "wb") dyn (sd:v "dyn")
               name (sd:bm-name kieu gd R tm tc nho hoc))
         (if (tblsearch "BLOCK" name)
           (princ (strcat "\n[SD] Block " name " da co: dung lai."))
           (progn
             (sd:make-layer "SD-GACH" 7 "Continuous" 25) (sd:make-layer "SD-GACH-CAT" 4 "Continuous" 25) (sd:make-layer "SD-KHUAT" 8 "Continuous" 13)
             (setq e0 (entlast))
             (sd:st-profile (list 0.0 0.0 0.0) kieu gd R tm tc nho 30.0 0.0 (if hoc "Hoc" "Khong") 17.0 20.0 20.0)
             (if (setq ss (sd:bm-since e0))
               (progn (sd:bm-define name (list 0.0 0.0 0.0) ss nil)
                      (princ (strcat "\n[SD] Da tao block " name " (mat cat 3 bac, goc tai mui bac dau, mat chieu nghi duoi).")))
               (princ "\n[SD] Khong ve duoc mau."))))
         (if (tblsearch "BLOCK" name)
           (progn
             (if (setq pt (sd:getpt "\nDiem chen block <Enter = chi tao khong chen>: " nil))
               (command "_.-INSERT" name (list (car pt) (cadr pt) 0.0) "1" "1" "0"))
             (if wb (sd:bm-save name))
             (if dyn (command "_.BEDIT" name)))))
        ;; ---- chi tiet op kho
        ((= mode "Opkho")
         (setq ot (sd:cfg-put "OK-T" (sd:v "ot")) og (sd:cfg-put "OK-G" (sd:v "og")) oj (sd:cfg-put "OK-J" (sd:v "oj"))
               oc (sd:cfg-put "OK-C" (cond ((sd:v "oc")) (0.0))) ol (sd:cfg-put "OK-L" (sd:v "ol")) olt (sd:cfg-put "OK-LT" (sd:v "olt"))
               obd (sd:cfg-put "OK-BD" (sd:v "obd")) obl (sd:cfg-put "OK-BL" (sd:v "obl")) ohh (sd:cfg-put "OK-H" (sd:v "ohh"))
               wb (sd:v "wb") dyn (sd:v "dyn")
               name (strcat "SDCT_OPKHO_t" (sd:num ot) "g" (sd:num og) "j" (sd:num oj) "c" (sd:num oc) "L" (sd:num ol) "x" (sd:num olt) "M" (sd:num obd) "x" (sd:num obl)))
         (if (tblsearch "BLOCK" name)
           (princ (strcat "\n[SD] Block " name " da co: dung lai."))
           (progn
             (setq e0 (entlast))
             (sd:bm-opkho ot og oj oc ol olt obd obl ohh)
             (if (setq ss (sd:bm-since e0))
               (progn (sd:bm-define name (list 0.0 0.0 0.0) ss nil)
                      (princ (strcat "\n[SD] Da tao block " name " (mat cat 1:1 mm, goc tai mat tuong o duoi tam da duoi). So lieu phu kien la mau minh hoa: doi chieu voi phu kien thuc te truoc khi dung.")))
               (princ "\n[SD] Khong ve duoc chi tiet."))))
         (if (tblsearch "BLOCK" name)
           (progn
             (if (setq pt (sd:getpt "\nDiem chen block <Enter = chi tao khong chen>: " nil))
               (command "_.-INSERT" name (list (car pt) (cadr pt) 0.0) "1" "1" "0"))
             (if wb (sd:bm-save name))
             (if dyn (command "_.BEDIT" name)))))
        ;; ---- quet hinh
        ((= mode "Quet")
         (setq keep (sd:v "keep") wb (sd:v "wb") dyn (sd:v "dyn"))
         (princ "\nQuet chon hinh de tao block (lenh nay khong dung cho cac vien da dung bang SDGACH / SDANHDA: do la nhieu doi tuong lien ket): ")
         (if (setq ss (ssget))
           (if (setq base (getpoint "\nDiem goc (diem chen) cua block: "))
             (progn
               (setq name (getstring T "\nTen block <tu dat>: "))
               (if (or (null name) (= name "")) (setq name (strcat "SDCT_Q" (sd:bm-stamp))))
               (if (sd:bm-define name (list (car base) (cadr base) 0.0) ss t)
                 (progn
                   (if keep (command "_.-INSERT" name (list (car base) (cadr base) 0.0) "1" "1" "0"))
                   (princ (strcat "\n[SD] Da tao block " name "."))
                   (if wb (sd:bm-save name))
                   (if dyn (command "_.BEDIT" name)))
                 (princ "\n[SD] Giu nguyen, khong tao block."))))))
        ;; ---- chen file
        (t
         (setq don (sd:cfg-put "BLK-DON" (sd:v "don")) laych (sd:cfg-put "BLK-LAY" (cond ((sd:v "laych")) ("SD-CHITIET"))))
         (if (setq f (getfiled "Chon file block (.dwg) de chen" "" "dwg" 4))
           (if (setq pt (sd:getpt "\nDiem chen block: " nil))
             (progn
               (setq nuevo (not (tblsearch "BLOCK" (vl-filename-base f))) old (sd:bm-layers))
               (command "_.-INSERT" (vl-string-translate "\\" "/" f) (list (car pt) (cadr pt) 0.0) "1" "1" "0")
               (princ "\n[SD] Da chen block.")
               (if (and nuevo (= don "Gop") (setq e0 (entlast)) (= (cdr (assoc 0 (entget e0))) "INSERT"))
                 (progn
                   (setq bn (cdr (assoc 2 (entget e0))) n (sd:bm-clean bn laych old))
                   (princ (strcat "\n[SD] Don layer: " (itoa (car n)) " doi tuong ve layer " laych ", xoa " (itoa (cadr n)) " layer la.")))))))))))
  (sd:finish))

;;; --------------------------------------------------------------------------
;;;  SDTUNAP - tu nap ShopDrawing.lsp moi khi mo AutoCAD (khong can APPLOAD lai):
;;;  ghi mot khoi co danh dau vao acaddoc.lsp trong thu muc Support cua nguoi dung; chay lai de go
;;; --------------------------------------------------------------------------
(defun sd:au-file () (strcat (getvar "ROAMABLEROOTPREFIX") "Support\\acaddoc.lsp"))

(defun sd:au-read (f / h l r)
  (if (and (findfile f) (setq h (open f "r")))
    (progn (while (setq l (read-line h)) (setq r (cons l r))) (close h)))
  (reverse r))

;; bo khoi ShopDrawing (giua hai dong danh dau) khoi danh sach dong
(defun sd:au-strip (lines / r in)
  (foreach l lines
    (cond ((wcmatch l ";;; SD-AUTOLOAD-BEGIN*") (setq in t))
          ((wcmatch l ";;; SD-AUTOLOAD-END*") (setq in nil))
          (in)
          (t (setq r (cons l r)))))
  (reverse r))

(defun sd:au-has (lines) (vl-some '(lambda (l) (wcmatch l ";;; SD-AUTOLOAD-BEGIN*")) lines))

(defun sd:au-write (f lines / h)
  (if (setq h (open f "w"))
    (progn (foreach l lines (write-line l h)) (close h) t)))

(defun c:SDTUNAP (/ f lines lsp tp ans)
  (sd:begin)
  (setq f (sd:au-file) lines (sd:au-read f))
  (cond
    ((sd:au-has lines)
     (initget "Giu Go")
     (setq ans (getkword "\nShopDrawing dang tu nap moi khi mo AutoCAD. [Giu/Go] <Giu>: "))
     (if (= ans "Go")
       (if (sd:au-write f (sd:au-strip lines))
         (princ "\n[SD] Da go tu nap. Lan sau mo AutoCAD phai APPLOAD hoac SDMENU.")
         (princ (strcat "\n[SD] Khong ghi duoc " f)))
       (princ "\n[SD] Giu nguyen tu nap.")))
    (t
     (setq lsp (cond ((findfile "ShopDrawing.lsp"))
                     ((getfiled "Chon ShopDrawing.lsp (cho tu nap)" "" "lsp" 4))))
     (if (null lsp)
       (princ "\n[SD] Chua chon file ShopDrawing.lsp.")
       (progn
         (setq lsp (vl-string-translate "\\" "/" lsp))
         (if (sd:au-write f
               (append (sd:au-strip lines)
                       (list ";;; SD-AUTOLOAD-BEGIN - ShopDrawing Tools tu nap (SDTUNAP, go bang SDTUNAP > Go)"
                             (strcat "(if (and (not c:SDHELP) (findfile \"" lsp "\")) (load \"" lsp "\"))")
                             ";;; SD-AUTOLOAD-END")))
           (progn
             ;; thu muc tin cay de AutoCAD khong hoi / chan khi nap
             (setq tp (getvar "TRUSTEDPATHS"))
             (if (and tp (not (vl-string-search (strcase (vl-filename-directory lsp)) (strcase (vl-string-translate "\\" "/" tp)))))
               (vl-catch-all-apply 'setvar (list "TRUSTEDPATHS" (strcat tp ";" (vl-filename-directory lsp)))))
             (princ (strcat "\n[SD] Da bat tu nap: " lsp "\n   Moi lan mo AutoCAD / ban ve moi se tu nap, khong can APPLOAD. Dung doi cho / xoa thu muc ShopDrawing."
                            "\n   Ten thu muc nen la chu khong dau. Go bang SDTUNAP > Go.")))
           (princ (strcat "\n[SD] Khong ghi duoc " f " - chay AutoCAD voi quyen ghi thu muc Support, hoac dung SDMENU.")))))))
  (sd:finish))

;;; --------------------------------------------------------------------------
;;;  SDMENU / SDMENUXOA - Nap / go menu + toolbar (ShopDrawing.mnu -> .cuix)
;;;  va tab Ribbon (ShopDrawingRibbon.cuix, nhom SHOPDRAWINGRIBBON, sinh boi build_ribbon.py)
;;; --------------------------------------------------------------------------
(defun sd:try (step fn args / r)
  (setq r (vl-catch-all-apply fn args))
  (if (vl-catch-all-error-p r)
    (progn (princ (strcat "\n[SD] Buoc '" step "' loi: " (vl-catch-all-error-message r))) nil)
    (if r r t)))

(defun sd:add-path (dir / fl sp tp)
  (setq fl (vla-get-Files (vla-get-Preferences (vlax-get-acad-object))) sp (vla-get-SupportPath fl))
  (if (not (vl-string-search (strcase dir) (strcase sp)))
    (vla-put-SupportPath fl (strcat sp ";" dir)))
  ;; AutoCAD 2014+: thu muc tin cay de nap LSP/MNL khong bi canh bao
  (if (and (setq tp (vl-catch-all-apply 'getvar '("TRUSTEDPATHS"))) (= (type tp) 'STR)
           (not (vl-string-search (strcase dir) (strcase tp))))
    (vl-catch-all-apply 'setvar (list "TRUSTEDPATHS" (if (= tp "") dir (strcat tp ";" dir))))))

(defun sd:rx-off ()
  (foreach v '(*SD:TM-CR* *SD:TM-LR*)
    (if (and (boundp v) (eval v)) (vl-catch-all-apply 'vlr-remove (list (eval v)))))
  (setq *SD:TM-CR* nil *SD:TM-LR* nil))

;; SDMENU: nap menu / Ribbon bang COM (AcadMenuGroups.Load / Unload): khong qua dong lenh nen duong dan co dau cach,
;; chu co dau van dung (SendCommand tach duong dan tai dau cach). Du phong: SendCommand co dau nhay quanh duong dan.
(defun sd:mg-find (grp / mgs r)
  (setq mgs (vla-get-MenuGroups (vlax-get-acad-object)) r (vl-catch-all-apply 'vla-Item (list mgs grp)))
  (if (vl-catch-all-error-p r) nil r))

(defun sd:mg-load (fn grp / mgs g r)
  (setq mgs (vla-get-MenuGroups (vlax-get-acad-object)))
  (if (setq g (sd:mg-find grp)) (vl-catch-all-apply 'vla-Unload (list g)))
  (setq r (vl-catch-all-apply 'vla-Load (list mgs fn)))
  (if (vl-catch-all-error-p r)
    (progn
      (vla-SendCommand (sd:doc) (strcat "_.CUILOAD\n\"" fn "\"\n"))
      (princ (strcat "\n[SD] Nap '" grp "' bang lenh CUILOAD (COM loi: " (vl-catch-all-error-message r) ")."))
      nil)
    t))

;; Phien ban ghi trong dong dau cua file .mnu ("//  ShopDrawing Tools vX.Y.Z ..."), nil neu khong co (ban cu)
(defun sd:mnu-ver (f / h l r k)
  (if (and f (setq h (open f "r")))
    (progn
      (repeat 8
        (if (and (null r) (setq l (read-line h)) (setq k (vl-string-search "Tools v" l)))
          (setq r (car (sd:split (substr l (+ k 8)) " ")))))
      (close h)))
  r)

;; Moi file ShopDrawing.mnu tren duong dan tim kiem cua AutoCAD (moi thu muc da tung SDMENU / them vao duong dan deu duoc liet ke)
(defun sd:mnu-cands (/ r d)
  (foreach p (append (sd:split (cond ((getenv "ACAD")) ("")) ";") (list (cond ((getvar "DWGPREFIX")) (""))))
    (if (and (/= p "") (setq d (findfile (strcat (vl-string-right-trim "\\" p) "\\ShopDrawing.mnu"))) (not (member d r)))
      (setq r (cons d r))))
  (if (and (setq d (findfile "ShopDrawing.mnu")) (not (member d r))) (setq r (cons d r)))
  (reverse r))

;; Dua pull-down "ShopDrawing" cua nhom menu grp len thanh menu neu chua co (CUILOAD khong luon tu them vao workspace dang dung).
;; Tra ve "them" / "co" / "khong-thay-popup"
(defun sd:menu-bar (grp / mg menus bar pm found)
  (setq mg (sd:mg-find grp))
  (if mg
    (progn
      (setq menus (vla-get-Menus mg) bar (vla-get-MenuBar (vlax-get-acad-object)))
      (vlax-for m menus (if (and (null pm) (wcmatch (strcase (vla-get-Name m)) "*SHOPDRAWING*")) (setq pm m)))
      (if pm
        (progn
          (vlax-for b bar (if (wcmatch (strcase (vla-get-Name b)) "*SHOPDRAWING*") (setq found t)))
          (if found
            "co"
            (progn (vla-InsertInMenuBar pm (vla-get-Count bar)) "them")))
        "khong-thay-popup"))))

(defun c:SDMENU (/ mnu dir rb ok1 ok2 r cands mver f mb)
  (princ (strcat "\n[SD] SDMENU v" *SD:VER*))
  (sd:rx-off)
  (setq r (vl-catch-all-apply
            '(lambda ()
               ;; chon file .mnu dung phien ban dang chay: cac ban cu con nam tren duong dan tim kiem se khong bi nap nham
               (setq cands (sd:mnu-cands))
               (foreach f cands (if (and (null mnu) (= (sd:mnu-ver f) *SD:VER*)) (setq mnu f)))
               (if (null mnu)
                 (progn
                   (if cands
                     (progn
                       (princ (strcat "\n[SD] Khong thay ShopDrawing.mnu phien ban " *SD:VER* " tren duong dan tim kiem. Cac file tim thay:"))
                       (foreach f cands (princ (strcat "\n     " f "  (ban " (cond ((sd:mnu-ver f)) ("cu, khong ghi phien ban")) ")")))
                       (princ "\n     Chon file ShopDrawing.mnu trong thu muc ban vua giai nen (cung thu muc voi ShopDrawing.lsp ban dang nap).")))
                   (setq mnu (getfiled "Chon file ShopDrawing.mnu (thu muc ban moi giai nen)" (cond ((car cands) (vl-filename-directory (car cands))) ((getvar "DWGPREFIX"))) "mnu" 0))))
               (if mnu
                 (progn
                   (setq dir (vl-filename-directory mnu)
                         rb (findfile (strcat dir "\\ShopDrawingRibbon.cuix")))
                   (vl-catch-all-apply 'sd:add-path (list dir))
                   ;; xoa ban .cuix / .mns da chuyen doi tu .mnu cu (de AutoCAD chuyen lai tu .mnu moi)
                   (foreach ext '("cuix" "mns" "mnc" "mnr")
                     (setq f (strcat dir "\\ShopDrawing." ext))
                     (if (findfile f) (vl-catch-all-apply 'vl-file-delete (list f))))
                   (setq mver (sd:mnu-ver mnu))
                   (if (/= mver *SD:VER*)
                     (princ (strcat "\n[!] File menu nap la ban " (cond (mver) ("cu, khong ghi phien ban")) " nhung ShopDrawing.lsp dang chay la ban " *SD:VER*
                                    ": lenh moi co the thieu tren menu. Giai nen ban moi vao thu muc rieng roi chay lai SDMENU.")))
                   (setq ok1 (sd:mg-load mnu "SHOPDRAWING"))
                   (if ok1
                     (progn
                       (setq mb (vl-catch-all-apply 'sd:menu-bar (list "SHOPDRAWING")))
                       (princ (cond ((vl-catch-all-error-p mb)
                                     (strcat "\n[SD] Khong them duoc menu ShopDrawing vao thanh menu (" (vl-catch-all-error-message mb)
                                             "). Them tay: CUI > Workspaces > (workspace dang dung) > Customize Workspace > tich ShopDrawing."))
                                    ((= mb "them") "\n[SD] Da them menu ShopDrawing vao thanh menu.")
                                    ((= mb "co") "\n[SD] Menu ShopDrawing da co tren thanh menu.")
                                    (t "\n[SD] Khong thay pull-down ShopDrawing trong nhom menu da nap.")))))
                   (if rb (setq ok2 (sd:mg-load rb "SHOPDRAWINGRIBBON")))
                   (princ (strcat "\n[SD] " (if ok1 "Da nap menu + toolbar" "Chua nap duoc menu")
                                  (if rb (if ok2 " + Ribbon" ", chua nap duoc Ribbon") ", khong thay file Ribbon") " tu " dir))
                   (if ok2 (princ "\n     Neu khong thay tab Ribbon: nhap phai vung Ribbon -> Show Tabs -> tich ShopDrawing."))))
               nil)
            nil))
  (if (vl-catch-all-error-p r)
    (princ (strcat "\n[SD] Khong nap duoc menu: " (vl-catch-all-error-message r)
                   "\n     Nap tay: CUILOAD -> ShopDrawing.mnu va ShopDrawingRibbon.cuix (thu muc dist).")))
  (vl-catch-all-apply 'sd:tm-init nil)
  (princ))

(defun c:SDMENUXOA (/ yn)
  (initget "Co Khong")
  (setq yn (cond ((getkword "\nGo menu, toolbar va Ribbon ShopDrawing [Co/Khong] <Khong>: ")) ("Khong")))
  (if (= yn "Co") (sd:menu-unload) (princ "\n[SD] Khong go menu."))
  (princ))

(defun sd:menu-unload (/ g)
  (foreach grp '("SHOPDRAWINGRIBBON" "SHOPDRAWING")
    (if (setq g (sd:mg-find grp))
      (progn (vl-catch-all-apply 'vla-Unload (list g))
             (princ (strcat "\n[SD] Da go " grp ".")))
      (princ (strcat "\n[SD] " grp " chua duoc nap.")))))

;;; --------------------------------------------------------------------------
;;;  SDDIMGD (DGD) va SDDIMPOLY (DPK) - tich hop tu DimGiaoDiem_v2.lsp / DimPolyline_v2.lsp (ban goc: ShopDrawing/goc/)
;;;  Ma o duoi giong tools/modules/dgd.lsp + dpk.lsp (goi SDOpLat dung chung).
;;; --------------------------------------------------------------------------
;;; ==========================================================================
;;;  SDDIMGD (lenh tat DGD) - Dim giao diem: ve 1 duong cat, lenh tu dong dim tung doan giua cac giao diem + dim tong
;;;  Tich hop tu DimGiaoDiem v2 theo yeu cau khach hang (UCS xoay van dung, tra lai bien he thong khi loi / Esc).
;;; ==========================================================================
;;; ---- Tuy chon "chu dim canh duong dim" dung chung cho DGD va DPK (luu trong ban ve, mac dinh BAT) ----
;;; BAT: ep DIMATFIT=1 (Text), DIMTIX=0, DIMTMOVE=0 (Beside the dimension line) khi dim, xong tra lai; TAT: giu nguyen kieu dim cua ban.
(defun sd:dimchu-on () (/= (vlax-ldata-get "SD" "DIMCHU") "TAT"))
(defun sd:dimchu-toggle ()
  (vlax-ldata-put "SD" "DIMCHU" (if (sd:dimchu-on) "TAT" "BAT"))
  (princ (strcat "\n[SD] Chu dim canh duong dim (DIMATFIT 1, DIMTIX 0, DIMTMOVE 0): " (if (sd:dimchu-on) "BAT" "TAT"))))
;; Hoi diem, co tu khoa C de doi tuy chon; base = diem co so (nil neu khong co)
(defun sd:dimchu-msg (msg)
  (strcat msg " [Chu dim canh duong dim: " (if (sd:dimchu-on) "BAT" "TAT") " (C) / Kieu dim ShopDrawing: " (if (sd:dimkieu-on) "BAT" "TAT") " (K)]: "))
(defun sd:dimchu-pt (msg0 base / r msg)
  (setq msg (sd:dimchu-msg msg0))
  (initget "Chu Kieu")
  (setq r (if base (getpoint base msg) (getpoint msg)))
  (while (member r '("Chu" "Kieu"))
    (if (= r "Chu") (sd:dimchu-toggle) (sd:dimkieu-toggle))
    (setq msg (sd:dimchu-msg msg0))
    (initget "Chu Kieu")
    (setq r (if base (getpoint base msg) (getpoint msg))))
  r)

;;; Tuy chon "kieu dim ShopDrawing" (mac dinh BAT): dim bang dimstyle SD-1-<ty le> tren layer SD-KICHTHUOC (tick kien truc, chu 2.5, lam tron 0 so le)
;;; giong cac dim khac cua ShopDrawing; TAT: dung kieu dim hien hanh. Chi co tac dung khi co ham sd:use-dimstyle (ShopDrawing / SDOpLat).
(defun sd:dimkieu-on () (/= (vlax-ldata-get "SD" "DIMKIEU") "TAT"))
(defun sd:dimkieu-toggle ()
  (vlax-ldata-put "SD" "DIMKIEU" (if (sd:dimkieu-on) "TAT" "BAT"))
  (princ (strcat "\n[SD] Kieu dim ShopDrawing (dimstyle SD-1-ty le, layer SD-KICHTHUOC): " (if (sd:dimkieu-on) "BAT" "TAT"))))
;; Chuyen sang kieu dim SD; tra ve (dimstyle-cu layer-cu) de tra lai bang sd:dimkieu-end (nil neu khong dung)
(defun sd:dimkieu-begin ( / old)
  (if (and (sd:dimkieu-on) (boundp 'sd:use-dimstyle) (numberp *SD:SCALE*) (> *SD:SCALE* 0))
    (progn
      (if (boundp 'sd:ensure) (sd:ensure))
      (setq old (list (getvar "DIMSTYLE") (getvar "CLAYER")))
      (sd:use-dimstyle *SD:SCALE*)
      (if (tblsearch "LAYER" "SD-KICHTHUOC") (setvar "CLAYER" "SD-KICHTHUOC"))
      old)))
(defun sd:dimkieu-end (old)
  (if old
    (progn
      (if (tblsearch "LAYER" (cadr old)) (setvar "CLAYER" (cadr old)))
      (if (and (tblsearch "DIMSTYLE" (car old)) (/= (strcase (getvar "DIMSTYLE")) (strcase (car old))))
        (command "_.-DIMSTYLE" "_R" (car old))))))


;; Dim doan ngan (chu khong du cho, nhay ra ngoai): thu nho chu cho vua doan (0.75 / 0.6 / 0.45 lan), khong de chu de len doan ke ben (chi khi tuy chon BAT).
;; Goi truoc moi lenh dim, sau do tra DIMTXT ve gia tri cu. Tra ve he so da dung (de in chan doan).
(defun sd:dimchu-small (len / sc h n fs f r)
  (setq r 1.0 *SD:DIMOUT* nil)   ;; *SD:DIMOUT* = T neu chu van khong vua doan du da thu nho het co (can dat chu canh doan)
  (if (sd:dimchu-on)
    (progn
      (setq sc (if (> (getvar "DIMSCALE") 0) (getvar "DIMSCALE") 1.0)
            h (* (getvar "DIMTXT") sc)
            n (strlen (rtos len 2 (getvar "DIMDEC")))
            fs '(1.0 0.75 0.6 0.45) r nil)
      ;; chu rong khoang 0.8 * cao moi ky tu, cong 2 khoang DIMGAP hai ben
      (while (and fs (not r))
        (setq f (car fs) fs (cdr fs))
        (if (>= len (+ (* n 0.8 h f) (* 2.0 (getvar "DIMGAP") sc))) (setq r f)))
      (if (not r) (setq r 0.45 *SD:DIMOUT* T))
      (if (< r 1.0) (setvar "DIMTXT" (* r (getvar "DIMTXT"))))))
  r)
;; Dat lai vi tri chu cua dim vua tao (entlast) den diem pt (toa do UCS); bo qua neu khong phai dim.
(defun sd:dimchu-move (pt / e)
  (setq e (entlast))
  (if (and e (= (cdr (assoc 0 (entget e))) "DIMENSION"))
    (progn
      (vl-catch-all-apply '(lambda () (command "_.DIMTEDIT" e pt)))
      (while (> (getvar "CMDACTIVE") 0) (command ""))))
  (princ))
(defun sd:dimchu-apply ()
  (if (sd:dimchu-on)
    (progn (setvar "DIMATFIT" 1) (setvar "DIMTIX" 0) (setvar "DIMTMOVE" 0))))

(defun c:SDDIMGD ( / *error* old_os old_echo old_fit old_tix old_tmove old_txt txt0 dk undo_on tmp lineobj p1 p2 p3
                     ss i ent r pts uniq p sorted k s ang1 side dirang sp p4 dp pa pb hh)
  (defun *error* (msg)
    (if tmp (progn (entdel tmp) (setq tmp nil)))
    (if undo_on (progn (command "_.UNDO" "_E") (setq undo_on nil)))
    (if old_txt (setvar "DIMTXT" old_txt))
    (if old_fit (setvar "DIMATFIT" old_fit))
    (if old_tix (setvar "DIMTIX" old_tix))
    (if old_tmove (setvar "DIMTMOVE" old_tmove))
    (if dk (progn (sd:dimkieu-end dk) (setq dk nil)))
    (if old_os (setvar "OSMODE" old_os))
    (if old_echo (setvar "CMDECHO" old_echo))
    (if (and msg (not (wcmatch (strcase msg) "*CANCEL*,*QUIT*,*EXIT*")))
      (princ (strcat "\n[SD] Loi: " msg))
    )
    (princ)
  )

  (setq old_os (getvar "OSMODE")
        old_echo (getvar "CMDECHO")
        old_fit (getvar "DIMATFIT")
        old_tix (getvar "DIMTIX")
        old_tmove (getvar "DIMTMOVE")
        old_txt (getvar "DIMTXT"))

  (if (and (setq p1 (sd:dimchu-pt "\nChon diem bat dau cua duong cat" nil))
           (setq p2 (getpoint p1 "\nChon diem ket thuc cua duong cat: "))
           (setq p3 (getpoint p2 "\nChon vi tri dat duong Dim chi tiet: ")))
    (progn
      (setvar "CMDECHO" 0)
      (command "_.UNDO" "_BE")
      (setq undo_on T)
      (setvar "OSMODE" 0)
      ;; Dim ron: chu nam canh duong dim, khong ep vao giua 2 duong dong (tra lai khi xong / loi)
      (setq dk (sd:dimkieu-begin))   ;; kieu dim ShopDrawing (neu BAT)
      (setq txt0 (getvar "DIMTXT"))  ;; chieu cao chu cua kieu dim dang dung (sau khi chuyen kieu)
      (sd:dimchu-apply)       ;; DIMATFIT 1 / DIMTIX 0 / DIMTMOVE 0 neu tuy chon chu dim dang BAT
      (princ (strcat "\n[SD] Dim: kieu " (getvar "DIMSTYLE") ", DIMTXT " (rtos (getvar "DIMTXT") 2 2) ", DIMSCALE " (rtos (getvar "DIMSCALE") 2 2)
                     ", DIMATFIT " (itoa (getvar "DIMATFIT")) ", DIMTMOVE " (itoa (getvar "DIMTMOVE")) ", layer " (getvar "CLAYER")))

      ;; Line tam (WCS) de lay giao diem
      (entmake (list '(0 . "LINE") (cons 10 (trans p1 1 0)) (cons 11 (trans p2 1 0))))
      (setq tmp (entlast))
      (setq lineobj (vlax-ename->vla-object tmp))

      ;; Cac doi tuong cat qua duong cat (fence nhan diem UCS)
      (if (setq ss (ssget "_F" (list p1 p2)))
        (repeat (setq i (sslength ss))
          (setq ent (ssname ss (setq i (1- i))))
          (if (/= ent tmp)
            (progn
              (setq r (vl-catch-all-apply 'vlax-invoke
                        (list (vlax-ename->vla-object ent) 'IntersectWith lineobj 0)))
              (if (and r (not (vl-catch-all-error-p r)))
                (while (>= (length r) 3)
                  (setq pts (cons (trans (list (car r) (cadr r) (caddr r)) 0 1) pts)
                        r (cdddr r))
                )
              )
            )
          )
        )
      )

      (entdel tmp)
      (setq tmp nil)

      ;; Loc diem trung (sai so 0.1)
      (foreach p pts
        (if (not (vl-some '(lambda (x) (< (distance p x) 0.1)) uniq))
          (setq uniq (cons p uniq))
        )
      )
      ;; Sap xep doc duong cat
      (setq sorted (vl-sort uniq '(lambda (a b) (< (distance p1 a) (distance p1 b)))))

      (if (< (length sorted) 2)
        (princ "\n[SD] Duong cat chi di qua duoi 2 diem, khong du de tao Dim!")
        (progn
          ;; huong ve phia dat dim (dirang) va khoang cach tu duong cat den duong dim (dp)
          (setq ang1 (angle p1 p2)
                side (- (* (- (car p2) (car p1)) (- (cadr p3) (cadr p1)))
                        (* (- (cadr p2) (cadr p1)) (- (car p3) (car p1))))
                dirang (if (< side 0) (- ang1 (/ pi 2)) (+ ang1 (/ pi 2)))
                dp (/ (abs side) (max 1e-9 (distance p1 p2))))
          ;; 1. Dim chi tiet
          (setq k 0 s "")
          (while (< k (1- (length sorted)))
            (setq pa (nth k sorted) pb (nth (1+ k) sorted))
            (sd:dimchu-small (distance pa pb))
            (setq hh (* (getvar "DIMTXT") (if (> (getvar "DIMSCALE") 0) (getvar "DIMSCALE") 1.0)))
            (command "_.DIMALIGNED" pa pb p3)
            ;; doan qua ngan, chu nho van khong vua: dat chu canh duong dim, so le 2 muc de khong de nhau
            (if *SD:DIMOUT*
              (sd:dimchu-move (polar (polar pa (angle pa pb) (/ (distance pa pb) 2.0)) dirang
                                     (+ dp (* hh (if (= (rem k 2) 0) 1.3 2.4))))))
            (setvar "DIMTXT" txt0)
            (setq s (strcat s (rtos (distance (nth k sorted) (nth (1+ k) sorted)) 2 2) "  "))
            (setq k (1+ k))
          )
          ;; 2. Dim tong, day ra phia xa duong cat hon dim chi tiet
          (setq sp (* 3.5 (getvar "DIMTXT")
                      (if (> (getvar "DIMSCALE") 0) (getvar "DIMSCALE") 1.0))
                p4 (polar p3 dirang sp))
          (command "_.DIMALIGNED" (car sorted) (last sorted) p4)

          (princ (strcat "\n[SD] So doan: " (itoa (1- (length sorted)))
                         " | Tong: " (rtos (distance (car sorted) (last sorted)) 2 2)))
          (princ (strcat "\n[SD] Cac doan: " s))
        )
      )

      (command "_.UNDO" "_E")
      (setq undo_on nil)
      (setvar "DIMTXT" old_txt)
      (setvar "DIMATFIT" old_fit)
      (setvar "DIMTIX" old_tix)
      (setvar "DIMTMOVE" old_tmove)
      (if dk (progn (sd:dimkieu-end dk) (setq dk nil)))
      (setvar "OSMODE" old_os)
      (setvar "CMDECHO" old_echo)
      (princ "\n[SD] Da hoan thanh!")
    )
  )
  (princ)
)

;;; ==========================================================================
;;;  SDDIMPOLY (lenh tat DPK) - Dim tu dong cho polyline kin (co chua cung tron)
;;;  Tich hop tu "LISP DIM TU DONG POLYLINE KIN" v2 theo yeu cau khach hang (ban goc luu o ShopDrawing/goc/DimPolyline_v2.lsp):
;;;  huong ngoai tinh theo dien tich co dau lay mau ca cung, nhan cung bang hinh hoc (chay ca POLYLINE 2D/3D), dung khi UCS xoay,
;;;  *error* tra bien va dong UNDO. Them tuy chon chu dim canh duong dim (sd:dimchu-*, dinh nghia trong dgd.lsp).
;;; ==========================================================================
(defun c:SDDIMPOLY ( / *error* old_vars undo_on ent n i k p1 p2 pm dv ang d_offset
                       ccw pt_dim sum_area pts a b ds r dk e0 nfail nok txt0)
  (defun *error* (msg)
    (if old_vars (foreach x old_vars (setvar (car x) (cdr x))))
    (if dk (progn (sd:dimkieu-end dk) (setq dk nil)))
    (if undo_on (progn (command "_.UNDO" "_E") (setq undo_on nil)))
    (if (and msg (not (wcmatch (strcase msg) "*CANCEL*,*QUIT*,*EXIT*")))
      (princ (strcat "\n[SD] Loi: " msg))
    )
    (princ)
  )

  ;; hoi polyline; go C / K de doi tuy chon
  (setq r (progn (initget "Chu Kieu") (entsel (sd:dimchu-msg "\nChon Polyline kin can Dim tu dong"))))
  (while (member r '("Chu" "Kieu"))
    (if (= r "Chu") (sd:dimchu-toggle) (sd:dimkieu-toggle))
    (initget "Chu Kieu")
    (setq r (entsel (sd:dimchu-msg "\nChon Polyline kin can Dim tu dong"))))
  (setq ent (if (listp r) (car r)))

  (if (and ent (wcmatch (cdr (assoc 0 (entget ent))) "*POLYLINE"))
    (progn
      (setq old_vars (list (cons "DIMATFIT" (getvar "DIMATFIT"))
                           (cons "DIMTIX" (getvar "DIMTIX"))
                           (cons "DIMTMOVE" (getvar "DIMTMOVE"))
                           (cons "DIMTXT" (getvar "DIMTXT"))
                           (cons "OSMODE" (getvar "OSMODE"))
                           (cons "CMDECHO" (getvar "CMDECHO"))))
      (command "_.UNDO" "_BE")
      (setq undo_on T)
      (setq dk (sd:dimkieu-begin))
      (setq txt0 (getvar "DIMTXT"))
      (sd:dimchu-apply)
      (setvar "OSMODE" 0)
      (setvar "CMDECHO" 0)

      ;; Khoang cach dat Dim = 3.5 lan chieu cao chu
      (setq d_offset (* 3.5 (getvar "DIMTXT")
                        (if (> (getvar "DIMSCALE") 0) (getvar "DIMSCALE") 1.0)))

      ;; Chieu ve: dien tich co dau tren cac diem mau (ca diem tren cung)
      (setq n (fix (+ 0.5 (vlax-curve-getEndParam ent))) i 0 pts nil)
      (while (< i n)
        (foreach k '(0.0 0.25 0.5 0.75)
          (setq pts (cons (vlax-curve-getPointAtParam ent (+ i k)) pts)))
        (setq i (1+ i))
      )
      (setq pts (reverse pts) sum_area 0.0 a (last pts))
      (foreach b pts
        (setq sum_area (+ sum_area (* (- (car b) (car a)) (+ (cadr b) (cadr a)))))
        (setq a b)
      )
      (setq ccw (< sum_area 0)) ;; T neu nguoc chieu kim dong ho

      (setq i 0)
      (while (< i n)
        (setq p1 (vlax-curve-getPointAtParam ent i)
              p2 (vlax-curve-getPointAtParam ent (1+ i))
              pm (vlax-curve-getPointAtParam ent (+ i 0.5))
              dv (vlax-curve-getFirstDeriv ent (+ i 0.5))
              ang (angle '(0.0 0.0 0.0) dv)
              pt_dim (polar pm (if ccw (- ang (/ pi 2)) (+ ang (/ pi 2))) d_offset))
        (if (> (distance p1 p2) 1e-6)
          (progn
            ;; Diem giua duong cong lech khoi trung diem day cung => cung tron
            (setq ds (distance pm (mapcar '(lambda (u v) (/ (+ u v) 2.0)) p1 p2)))
            (sd:dimchu-small (distance p1 p2))
            (setq e0 (entlast))
            (if (< ds 1e-4)
              (command "_.DIMALIGNED" "_non" (trans p1 0 1) "_non" (trans p2 0 1)
                       "_non" (trans pt_dim 0 1))
              (command "_.DIMARC" (list ent (trans pm 0 1)) "_non" (trans pt_dim 0 1))
            )
            (while (> (getvar "CMDACTIVE") 0) (command ""))   ;; lenh dim dang do do thi huy
            ;; khong co dim moi (DIMARC that bai...) -> thu lai bang dim day cung; van that bai thi bao canh nao
            (if (eq (entlast) e0)
              (progn
                (command "_.DIMALIGNED" "_non" (trans p1 0 1) "_non" (trans p2 0 1) "_non" (trans pt_dim 0 1))
                (while (> (getvar "CMDACTIVE") 0) (command ""))))
            (if (eq (entlast) e0)
              (setq nfail (cons (1+ i) nfail))
              (setq nok (1+ (if nok nok 0))))
            (setvar "DIMTXT" txt0)
          )
        )
        (setq i (1+ i))
      )
      (princ (strcat "\n[SD] Da tao Dim tu dong: " (itoa (if nok nok 0)) " / " (itoa n) " canh."))
      (if nfail (princ (strcat "\n[SD] Canh KHONG dim duoc (so thu tu tu 1): " (vl-princ-to-string (reverse nfail)))))

      (foreach x old_vars (setvar (car x) (cdr x)))
      (if dk (progn (sd:dimkieu-end dk) (setq dk nil)))
      (command "_.UNDO" "_E")
      (setq undo_on nil old_vars nil)
    )
    (princ "\n[SD] Doi tuong duoc chon khong phai la Polyline!")
  )
  (princ)
)

;; Thep thong minh: gan reactor cho ban ve vua mo
(vl-catch-all-apply 'sd:tm-init nil)
(vl-catch-all-apply 'sd:ud-autoload nil)

(princ (strcat "\n[SD] ShopDrawing Tools v" *SD:VER* " da nap. Go SDPANEL (bang lenh) hoac SDHELP; SDMENU de cai menu + toolbar."))
(if (not (vl-catch-all-error-p (vl-catch-all-apply '(lambda () (sd:au-has (sd:au-read (sd:au-file)))) nil)))
  (if (not (sd:au-has (sd:au-read (sd:au-file))))
    (princ "\n[SD] Chua tu nap moi khi mo AutoCAD: go SDTUNAP mot lan (hoac SDMENU).")))
(princ)
