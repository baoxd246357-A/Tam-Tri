;;; LISP DIM TỰ ĐỘNG POLYLINE KÍN (CÓ CHỨA CUNG TRÒN) - v2
;;; Lệnh: DPK (Dim Polyline Kín)
;;; v2: hướng ngoài tính theo diện tích có dấu lấy mẫu cả cung, nhận cung bằng hình học
;;;     (chạy cả POLYLINE 2D/3D), đúng khi UCS xoay, *error* đóng UNDO đúng chỗ.
(vl-load-com)
(defun c:DPK ( / *error* old_vars undo_on ent n i k p1 p2 pm dv ang d_offset
                 ccw pt_dim sum_area pts a b ds)
  (defun *error* (msg)
    (if old_vars (foreach x old_vars (setvar (car x) (cdr x))))
    (if undo_on (progn (command "_.UNDO" "_E") (setq undo_on nil)))
    (if (and msg (not (wcmatch (strcase msg) "*CANCEL*,*QUIT*,*EXIT*")))
      (princ (strcat "\nLỗi: " msg))
    )
    (princ)
  )

  (if (and (setq ent (car (entsel "\nChọn Polyline kín cần Dim tự động: ")))
           (wcmatch (cdr (assoc 0 (entget ent))) "*POLYLINE"))
    (progn
      (setq old_vars (list (cons "DIMATFIT" (getvar "DIMATFIT"))
                           (cons "DIMTIX" (getvar "DIMTIX"))
                           (cons "DIMTMOVE" (getvar "DIMTMOVE"))
                           (cons "OSMODE" (getvar "OSMODE"))
                           (cons "CMDECHO" (getvar "CMDECHO"))))
      (command "_.UNDO" "_BE")
      (setq undo_on T)
      (setvar "DIMATFIT" 1)
      (setvar "DIMTIX" 0)
      (setvar "DIMTMOVE" 0)
      (setvar "OSMODE" 0)
      (setvar "CMDECHO" 0)

      ;; Khoảng cách đặt Dim = 3.5 lần chiều cao chữ
      (setq d_offset (* 3.5 (getvar "DIMTXT")
                        (if (> (getvar "DIMSCALE") 0) (getvar "DIMSCALE") 1.0)))

      ;; Chiều vẽ: diện tích có dấu trên các điểm mẫu (cả điểm trên cung)
      (setq n (fix (+ 0.5 (vlax-curve-getEndParam ent))) i 0 pts nil)
      (while (< i n)
        (foreach k '(0.0 0.25 0.5 0.75)
          (setq pts (cons (vlax-curve-getPointAtParam ent (+ i k)) pts)))
        (setq i (1+ i))
      )
      (setq pts (reverse pts) sum_area 0.0 a (last pts))
      (foreach b pts
        (setq sum_area (+ sum_area (* (- (car b) (car a)) (+ (cadr b) (cadr a)))))
        (setq a b)
      )
      (setq ccw (< sum_area 0)) ;; T nếu ngược chiều kim đồng hồ

      (setq i 0)
      (while (< i n)
        (setq p1 (vlax-curve-getPointAtParam ent i)
              p2 (vlax-curve-getPointAtParam ent (1+ i))
              pm (vlax-curve-getPointAtParam ent (+ i 0.5))
              dv (vlax-curve-getFirstDeriv ent (+ i 0.5))
              ang (angle '(0.0 0.0 0.0) dv)
              pt_dim (polar pm (if ccw (- ang (/ pi 2)) (+ ang (/ pi 2))) d_offset))
        (if (> (distance p1 p2) 1e-6)
          (progn
            ;; Điểm giữa đường cong lệch khỏi trung điểm dây cung => cung tròn
            (setq ds (distance pm (mapcar '(lambda (u v) (/ (+ u v) 2.0)) p1 p2)))
            (if (< ds 1e-4)
              (command "_.DIMALIGNED" "_non" (trans p1 0 1) "_non" (trans p2 0 1)
                       "_non" (trans pt_dim 0 1))
              (command "_.DIMARC" (list ent (trans pm 0 1)) "_non" (trans pt_dim 0 1))
            )
          )
        )
        (setq i (1+ i))
      )
      (princ "\nĐã tạo Dim tự động cho toàn bộ Polyline!")

      (foreach x old_vars (setvar (car x) (cdr x)))
      (command "_.UNDO" "_E")
      (setq undo_on nil old_vars nil)
    )
    (princ "\nĐối tượng được chọn không phải là Polyline!")
  )
  (princ)
)
(princ "\n--- Đã tải Lisp Dim Tự Động Polyline Kín (v2) ---")
(princ "\n--- Gõ lệnh: DPK để sử dụng ---")
(princ)
